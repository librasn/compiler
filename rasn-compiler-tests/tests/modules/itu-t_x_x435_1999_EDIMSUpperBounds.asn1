-- Module EDIMSUpperBounds (X.435:06/1999)
-- See also ITU-T X.435 (06/1999)
-- See also the index of all ASN.1 assignments needed in this document

EDIMSUpperBounds {joint-iso-itu-t mhs(6) edims(7) modules(0) upper-bounds(5)}
DEFINITIONS ::=
BEGIN

--	Prologue
--	Exports everything
IMPORTS -- nothing -- ;

--	Upper bounds
ub-application-reference INTEGER ::= 14

ub-authorization-information INTEGER ::= 10

ub-authorization-information-qualifier INTEGER ::= 2

ub-communications-agreement-id INTEGER ::= 35

ub-edi-association-assigned-code INTEGER ::= 6

ub-edi-application-security-elements INTEGER ::= 8191

ub-edi-controlling-agency INTEGER ::= 2

ub-edi-document-release INTEGER ::= 3

ub-edi-document-version INTEGER ::= 3

ub-edi-message-type INTEGER ::= 6

ub-edi-string-size INTEGER ::= 30 -- please check this value reference name

ub-identification-code-qualifier INTEGER ::= 4

ub-identification-code INTEGER ::= 35

ub-interchange-control-reference INTEGER ::= 14

ub-local-reference INTEGER ::= 64

ub-processing-priority-code INTEGER ::= 1

ub-reason-code INTEGER ::= 32767

ub-recipient-reference-qualifier INTEGER ::= 2

ub-recipient-reference INTEGER ::= 14

ub-recipients INTEGER ::= 32767

ub-routing-address INTEGER ::= 14

ub-syntax-identifier INTEGER ::= 4

ub-syntax-version INTEGER ::= 5

END -- of EDIMSUpperBounds

-- Generated by Asnp, the ASN.1 pretty-printer of France Telecom R&D
