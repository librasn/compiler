-- Module MKMD (X.750:10/1996)
-- See also ITU-T X.750 (1996) Technical Cor. 1 (02/2000)
-- See also the index of all ASN.1 assignments needed in this document

MKMD {joint-iso-itu-t(2) ms(9) function(2) part16(16) asn1Modules(2) 5}
DEFINITIONS IMPLICIT TAGS ::=
BEGIN

dmiAttribute OBJECT IDENTIFIER ::=
  {joint-iso-itu-t(2) ms(9) smi(3) part2(2) attribute(7)}

dmiNotification OBJECT IDENTIFIER ::=
  {joint-iso-itu-t(2) ms(9) smi(3) part2(2) notification(10)}

mkmDirectoryAttributeType OBJECT IDENTIFIER ::=
  {joint-iso-itu-t(2) ms(9) function(2) part16(16) standardSpecificExtension(0)
   directoryAttributeTypes(4)}

mkmDirectoryObjectClass OBJECT IDENTIFIER ::=
  {joint-iso-itu-t(2) ms(9) function(2) part16(16) standardSpecificExtension(0)
   directoryObjectClasses(6)}

mkmDirectoryNameForm OBJECT IDENTIFIER ::=
  {joint-iso-itu-t(2) ms(9) function(2) part16(16) standardSpecificExtension(0)
   directoryNameForms(7)}

mkmMObjectClass OBJECT IDENTIFIER ::=
  {joint-iso-itu-t(2) ms(9) function(2) part16(16) managedObjectClass(3)}

mkmPackage OBJECT IDENTIFIER ::=
  {joint-iso-itu-t(2) ms(9) function(2) part16(16) package(4)}

mkmParameter OBJECT IDENTIFIER ::=
  {joint-iso-itu-t(2) ms(9) function(2) part16(16) parameter(5)}

mkmNameBinding OBJECT IDENTIFIER ::=
  {joint-iso-itu-t(2) ms(9) function(2) part16(16) nameBinding(6)}

mkmAttribute OBJECT IDENTIFIER ::=
  {joint-iso-itu-t(2) ms(9) function(2) part16(16) attribute(7)}

mkmAction OBJECT IDENTIFIER ::=
  {joint-iso-itu-t(2) ms(9) function(2) part16(16) action(9)}

END

-- Generated by Asnp, the ASN.1 pretty-printer of France Telecom R&D
