-- Module COMMAND-RESPONSE-EXAMPLE (X.1080.1:10/2011)
-- See also ITU-T X.1080.1 (10/2011)
-- See also the index of all ASN.1 assignments needed in this document

COMMAND-RESPONSE-EXAMPLE {joint-iso-itu-t(2) telebiometrics(42)
  e-health-protocol(3) modules(0) examples(5) command-response(0)}
  "/Telebiometrics/E_health_Protocol/Modules/Examples/Command_Response"
DEFINITIONS AUTOMATIC TAGS ::=
BEGIN

IMPORTS
  CR-SEQUENCE, INTERACTIVE-MESSAGE, Identified-Command-Response{}
    FROM E-health-command-response {joint-iso-itu-t(2) telebiometrics(42)
      e-health-protocol(3) modules(0) command-response(3) version1(1)};

example-Sequence CR-SEQUENCE ::= {
  INTERACTIVE-SESSION IDENTIFIED BY  {2 42 3 1 3}
  REQUIRING                          none
  WITH VOICE OPTIONS                 {2 42 3 1 1}
  AND VIDEO OPTIONS                  {2 43 3 1 2}
  SPECIFIED BY                       "Example"
  USING                              {Example-Messages}
  BEGINNING WITH                     example-1
}

example-1 INTERACTIVE-MESSAGE ::= {
  STEP         1
  DIRECTION    command
  USING        INTEGER
  RESPONSE     example-2
  FOLLOWED BY  {2,
                3,
                4}
}

example-2 INTERACTIVE-MESSAGE ::= {
  STEP         2
  DIRECTION    response
  USING        BOOLEAN
  FOLLOWED BY  {3,
                4}
}

example-3 INTERACTIVE-MESSAGE ::= {
  STEP         3
  DIRECTION    command
  USING        OCTET STRING
  RESPONSE     example-4
  FOLLOWED BY  {4}
}

example-4 INTERACTIVE-MESSAGE ::= {
  STEP       4
  DIRECTION  response
  USING      BOOLEAN
}

Example-Messages INTERACTIVE-MESSAGE ::=
  {example-1 | example-2 | example-3 | example-4}

Example-Command-Response ::= Identified-Command-Response{{Example-Messages}}

END

-- Generated by Asnp, the ASN.1 pretty-printer of France Telecom R&D
