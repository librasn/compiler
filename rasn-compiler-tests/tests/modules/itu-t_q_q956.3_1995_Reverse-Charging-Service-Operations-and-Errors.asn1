-- Module Reverse-Charging-Service-Operations-and-Errors (Q.956.3:10/1995)
-- See also ITU-T Q.956.3 (10/1995)
-- See also the index of all ASN.1 assignments needed in this document

Reverse-Charging-Service-Operations-and-Errors {itu-t recommendation
  q 956 reverse-charging(3) operations-and-errors(1)} DEFINITIONS ::=
BEGIN

EXPORTS requestREV, rEVIndication, userIgnored, rEVIsAlreadyRunning;

IMPORTS
  OPERATION, ERROR
    FROM Remote-Operations-Information-Objects {joint-iso-itu-t
      remote-operations(4) informationObjects(5) version1(0)}
  userNotSubscribed, rejectedByNetwork, rejectedByUser, notAvailable,
    invalidCallState, basicServiceNotProvided,
    supplementaryServiceInteractionNotAllowed, resourceUnavailable,
    proceduralError
    FROM General-Error-List {itu-t recommendation q 950 general-error-list(1)};

requestREV OPERATION ::= {
  ARGUMENT  Case
  ERRORS
    {userNotSubscribed | rejectedByNetwork | rejectedByUser | notAvailable |
      invalidCallState | basicServiceNotProvided |
      supplementaryServiceInteractionNotAllowed | resourceUnavailable |
      proceduralError | userIgnored | rEVIsAlreadyRunning}
  CODE      local:60
}

rEVIndication OPERATION ::= {CODE  local:61
}

Case ::= ENUMERATED {caseA(1), caseB(2), caseC(3)}

userIgnored ERROR ::= {CODE  local:45
}

rEVIsAlreadyRunning ERROR ::= {CODE  local:49
}

END -- of Reverse-Charging-Service-Operations

-- Generated by Asnp, the ASN.1 pretty-printer of France Telecom R&D
