-- Module CAISDNSSModule (Q.824.2:10/1995)
-- See also ITU-T Q.824.2 (10/1995)
-- See also the index of all ASN.1 assignments needed in this document

CAISDNSSModule {itu-t(0) recommendation(0) q(17) ca(824) dot(127) isdnss(2)
  informationModel(0) asn1Modules(2) cAISDNSSModule(0)} DEFINITIONS IMPLICIT
TAGS ::=
BEGIN

-- EXPORTS Everything;
IMPORTS
  DirectoryNumber, NumberOfBChannels
    FROM CAISDNModule {itu-t(0) recommendation(0) q(17) ca(824) dot(127)
      isdn(1) informationModel(0) asn1Modules(2) cAISDNModule(0)}
  InterceptTreatmentOrigin
    FROM CACommonModule {itu-t(0) recommendation(0) q(17) ca(824) dot(127)
      common(0) informationModel(0) asn1Modules(2) cACommonModule(0)}
  incomingCallsBarred, outgoingCallsBarred
    FROM NLM {joint-iso-itu-t network-layer(13) management(0) nLM(2)
      asn1Module(2) 0}
  ObjectInstance, ObjectClass
    FROM CMIP-1 {joint-iso-itu-t ms(9) cmip(1) modules(0) protocol(3)}
  Boolean, NameType, ObjectList, Pointer, PointerOrNull
    FROM ASN1DefinedTypesModule {itu-t recommendation m(13) gnm(3100)
      informationModel(0) asn1Modules(2) asn1DefinedTypesModule(0)};

q824-2InformationModel OBJECT IDENTIFIER ::=
  {itu-t(0) recommendation(0) q(17) ca(824) dot(127) isdnss(2)
   informationModel(0)}

cAISDNSSObjectClass OBJECT IDENTIFIER ::=
  {q824-2InformationModel managedObjectClass(3)}

cAISDNSSPackage OBJECT IDENTIFIER ::= {q824-2InformationModel package(4)}

cAISDNSSAttribute OBJECT IDENTIFIER ::= {q824-2InformationModel attribute(7)}

cAISDNSSNameBinding OBJECT IDENTIFIER ::=
  {q824-2InformationModel nameBinding(6)}

cAISDNSSAction OBJECT IDENTIFIER ::= {q824-2InformationModel action(9)}

-- default value definitions
false Boolean ::= FALSE

true Boolean ::= TRUE

null NULL ::= NULL

one INTEGER ::= 1

zero INTEGER ::= 0

minusOne INTEGER ::= -1

emptySet NULL ::= NULL

-- supporting productions
ActivationOption ::= ENUMERATED {subscriber(1), operator(2)}

ActivationStatus ::= ENUMERATED {active(1), inactive(2)}

AdviceOfChargeActivation ::= INTEGER {allCalls(0), perCall(1)}

AssocDefaultDN ::= DirectoryNumber

LimitOfReservedChannels ::= NumberOfBChannels

CallForwardCallingNotification ::= INTEGER {
  no(0), yesWithoutNumber(1), yesWithNumber(2)}

CallHoldOptionalGuardTimer ::= INTEGER

CallReferenceBusyLimit ::= INTEGER

CallIdRestrictionOptions ::= SEQUENCE {
  mode     ENUMERATED {permanent(1), temporary(2)},
  default  ENUMERATED {restricted(1), notRestr(2)} OPTIONAL -- for temporary mode only
}

CodeWord ::= GraphicString

DefaultNumberOfPorts ::= INTEGER

MaxNumberOfPorts ::= INTEGER

MaxNumberOfWaitingCalls ::= INTEGER(1..MAX)

NumOfDigitsForCallId ::= INTEGER

NumOfDigitsForTerminalIdentifier ::= INTEGER

NumOfDigitsNotToTransmit ::= INTEGER

OutgoingCallBarringCategory ::= ENUMERATED {general(1), special(2)}

TimePeriod ::= SEQUENCE {beginTime  UTCTime,
                         endTime    UTCTime
}

TransferProcedure ::= BIT STRING {normal(0), singleStep(1), explicit(2)}

UserToUserSignallingServiceCategory ::= ENUMERATED {
  duringSetupInCallControl(1), duringSetupIndepFromCallControl(2),
  duringActive(3)}

CUGBarring ::= ENUMERATED {
  none(1), incomingCallsBarred(2), outgoingCallsBarred(3)}

CUGDataNetworkIdentification ::= OCTET STRING(SIZE (4))

CUGIndex ::= INTEGER(0..32767) -- Recommendation Q.755


CUGInterlockCode ::= OCTET STRING(SIZE (1..2)) -- Recommendation Q.735


InterCUGaccess ::= ENUMERATED {
  none(1), outgoingAccess(2), incomingAccess(3), ougoingAndIncomingAccess(4)
}

PreferredCUGIndex ::= CHOICE {notDefined  [0]  NULL,
                              defined     [1]  CUGIndex
}

END -- Type definitions

-- Generated by Asnp, the ASN.1 pretty-printer of France Telecom R&D
