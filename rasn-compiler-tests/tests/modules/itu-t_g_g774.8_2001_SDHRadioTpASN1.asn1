-- Module SDHRadioTpASN1 (G.774.8:02/2001)
-- See also ITU-T G.774.8 (02/2001)
-- See also the index of all ASN.1 assignments needed in this document

SDHRadioTpASN1 {itu-t(0) recommendation(0) g(7) g774(774) hyphen(127)
  sdhRadioIM(8) informationModel(0) asn1Module(2) sdhRadioTp(0)} DEFINITIONS
IMPLICIT TAGS ::=
BEGIN

-- EXPORTS Everything
IMPORTS
  NameType
    FROM ASN1DefinedTypesModule {itu-t(0) recommendation(0) m(13) gnm(3100)
      informationModel(0) asn1Modules(2) asn1DefinedTypesModule(0)}
  ProbableCause
    FROM Attribute-ASN1Module {joint-iso-itu-t ms(9) smi(3) part2(2)
      asn1Module(2) 1};

RadioFrequency ::=
  SEQUENCE OF
    SEQUENCE {frequencyValue  [0]  INTEGER,
              frequencyUsage  [1]  FrequencyUsage,
              polarization    [2]  Polarization OPTIONAL}

Boolean ::= BOOLEAN

Integer ::= INTEGER

Polarization ::= ENUMERATED {vertical(0), horizontal(1), unspecified(2)}

FrequencyUsage ::= ENUMERATED {receive(0), transmit(1)}

-- The following value assignments specify the Probable Cause value related to
-- Radio-Relay management within the TMN application context. The chosen values
-- are reserved by Recommendation M.3100 for communication alarm-related probable
-- causes.
rxFail ProbableCause ::=
  localValue:30

rxLOS ProbableCause ::= localValue:31

demodulationFail ProbableCause ::= localValue:32

demLOS ProbableCause ::= localValue:33

txFail ProbableCause ::= localValue:34

txLOS ProbableCause ::= localValue:35

modulationFail ProbableCause ::= localValue:36

modLOS ProbableCause ::= localValue:37

END

-- Generated by Asnp, the ASN.1 pretty-printer of France Telecom R&D
