-- Module GulsSecurityExchanges (X.830:04/1995)
-- See also ITU-T X.830 (04/1995)
-- See also the index of all ASN.1 assignments needed in this document

GulsSecurityExchanges {joint-iso-itu-t genericULS(20) modules(1)
  gulsSecurityExchanges(2)} DEFINITIONS AUTOMATIC TAGS ::=
BEGIN

-- EXPORTS All
IMPORTS
  securityExchanges, notation
    FROM ObjectIdentifiers {joint-iso-itu-t genericULS(20) modules(1)
      objectIdentifiers(0)}
  SECURITY-EXCHANGE, SEC-EXCHG-ITEM, SE-ERROR
    FROM Notation {joint-iso-itu-t genericULS(20) modules(1) notation(1)}
  Credentials, SecurityProblem
    FROM DirectoryAbstractService {joint-iso-itu-t ds(5) module(1)
      directoryAbstractService(2) 3};

-- *******************************************
-- Directory Authentication Exchange (One-way)
-- *******************************************
dirAuthenticationOneWay SECURITY-EXCHANGE ::= {
  SE-ITEMS    {credentials}
  IDENTIFIER  global:{securityExchanges dir-authent-one-way(1)}
}

credentials SEC-EXCHG-ITEM ::= {
  ITEM-TYPE  DirectoryAbstractService.Credentials
  ITEM-ID    1
}

-- *******************************************
-- Directory Authentication Exchange (Two-way)
-- *******************************************
dirAuthenticationTwoWay SECURITY-EXCHANGE ::= {
  SE-ITEMS    {initiatorCredentials | responderCredentials}
  IDENTIFIER  global:{securityExchanges dir-authent-two-way(2)}
}

initiatorCredentials SEC-EXCHG-ITEM ::= {
  ITEM-TYPE  DirectoryAbstractService.Credentials
  ITEM-ID    1
  ERRORS     {authenticationFailure}
}

responderCredentials SEC-EXCHG-ITEM ::= {
  ITEM-TYPE  DirectoryAbstractService.Credentials
  ITEM-ID    2
}

authenticationFailure SE-ERROR ::= {
  PARAMETER   DirectoryAbstractService.SecurityProblem
  ERROR-CODE  local:1
}

-- ***************************
-- Simple Negotiation Exchange
-- ***************************
simpleNegotiationSE SECURITY-EXCHANGE ::= {
  SE-ITEMS    {offeredIds | acceptedIds}
  IDENTIFIER  global:{securityExchanges simple-negotiation-se(3)}
}

offeredIds SEC-EXCHG-ITEM ::= {ITEM-TYPE  Negotiation-SEI
                               ITEM-ID    1
}

acceptedIds SEC-EXCHG-ITEM ::= {ITEM-TYPE  Negotiation-SEI
                                ITEM-ID    2
}

Negotiation-SEI ::= SEQUENCE OF OBJECT IDENTIFIER

END

-- Generated by Asnp, the ASN.1 pretty-printer of France Telecom R&D
