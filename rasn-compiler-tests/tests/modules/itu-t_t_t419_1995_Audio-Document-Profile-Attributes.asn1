-- Module Audio-Document-Profile-Attributes (T.419:08/1995)
-- See also ITU-T T.419 (08/1995)
-- See also the index of all ASN.1 assignments needed in this document

Audio-Document-Profile-Attributes {2 8 1 9 1} DEFINITIONS ::=
BEGIN

EXPORTS Reference-recording-level;

Reference-recording-level ::= REAL

END

-- Generated by Asnp, the ASN.1 pretty-printer of France Telecom R&D
