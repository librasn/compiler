-- Module IN-SCF-CUSF-Classes (Q.1248.7:07/2001)
-- See also ITU-T Q.1248.7 (07/2001)
-- See also the index of all ASN.1 assignments needed in this document

IN-SCF-CUSF-Classes {itu-t recommendation q 1248 modules(1)
  in-scf-cusf-classes(25) version1(0)} DEFINITIONS ::=
BEGIN

IMPORTS
  common-classes, ssf-scf-classes
    FROM IN-object-identifiers {itu-t recommendation q 1248 modules(1)
      in-object-identifiers(0) version1(0)}
  COMMON-BOUNDS
    FROM IN-common-classes common-classes
  SCF-SSF-BOUNDS
    FROM IN-SSF-SCF-Classes ssf-scf-classes;

SCF-CUSF-BOUNDS ::= CLASS {
  &minAssReleaseInfoLen    INTEGER OPTIONAL,
  &maxAssReleaseInfoLen    INTEGER OPTIONAL,
  &minCompReceivedInfoLen  INTEGER OPTIONAL,
  &maxCompReceivedInfoLen  INTEGER OPTIONAL,
  &numOfBCUSMEvents        INTEGER OPTIONAL
}
WITH SYNTAX {
  [MINIMUM-FOR-ASS-RELEASE-INFO-LENGTH &minAssReleaseInfoLen]
  [MAXIMUM-FOR-ASS-RELEASE-INFO-LENGTH &maxAssReleaseInfoLen]
  [MINIMUM-FOR-COMP-RECEIVED-INFO-LENGTH &minCompReceivedInfoLen]
  [MAXIMUM-FOR-COMP-RECEIVED-INFO-LENGTH &maxCompReceivedInfoLen]
  [NUM-OF-BCUSM-EVENTS &numOfBCUSMEvents]
}

-- The following definitions of the parameter bounds are an example.
-- Appropriate values will be defined as network specific.
sCFCUSFBoundSet SCF-CUSF-BOUNDS ::= {
  MINIMUM-FOR-ASS-RELEASE-INFO-LENGTH    5
  MAXIMUM-FOR-ASS-RELEASE-INFO-LENGTH    10
  MINIMUM-FOR-COMP-RECEIVED-INFO-LENGTH  5
  MAXIMUM-FOR-COMP-RECEIVED-INFO-LENGTH  10
  NUM-OF-BCUSM-EVENTS                    2
}

sCFSSFBoundSetforCUSF SCF-SSF-BOUNDS ::= {
  HIGH-LAYER-COMPATIBILITY-LENGTH          5 -- example value
  MAXIMUM-FOR-BEARER-CAPABILITY            5 -- example value
  MINIMUM-FOR-CALLED-PARTY-NUMBER          2 -- example value
  MAXIMUM-FOR-CALLED-PARTY-NUMBER          10 -- example value
  MINIMUM-FOR-CALLING-PARTY-NUMBER         2 -- example value
  MAXIMUM-FOR-CALLING-PARTY-NUMBER         10 -- example value
  MINIMUM-FOR-CALLING-PARTY-SUBADDRESS     2 -- example value
  MAXIMUM-FOR-CALLING-PARTY-SUBADDRESS     5 -- example value
  MINIMUM-FOR-CAUSE                        1 -- example value
  MAXIMUM-FOR-CAUSE                        10 -- example value
  MINIMUM-FOR-GENERIC-NUMBER               3 -- example value
  MAXIMUM-FOR-GENERIC-NUMBER               10 -- example value
  MINIMUM-FOR-LOCATION-NUMBER              2 -- example value
  MAXIMUM-FOR-LOCATION-NUMBER              10 -- example value
  MINIMUM-FOR-REQUESTED-UTSI-NUM           1 -- example value
  MAXIMUM-FOR-REQUESTED-UTSI-NUM           5 -- example value
  MINIMUM-FOR-USI-INFORMATION              1 -- example value
  MAXIMUM-FOR-USI-INFORMATION              20 -- example value
  MINIMUM-FOR-USI-SERVICE-INDICATOR        1 -- example value
  MAXIMUM-FOR-USI-SERVICE-INDICATOR        10 -- example value
  NUM-OF-GENERIC-NUMBERS                   5 -- example value
  MINIMUM-FOR-BROADBAND-BEARER-CAPABILITY  1 -- example value
  MAXIMUM-FOR-BROADBAND-BEARER-CAPABILITY  5
 -- example value--}

commonBoundSetforCUSF COMMON-BOUNDS ::= {NUM-OF-EXTENSIONS  1
}

END

-- Generated by Asnp, the ASN.1 pretty-printer of France Telecom R&D
