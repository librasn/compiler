-- Module NUMBER-PORTABILITY (H.460.2:03/2013)
-- See also ITU-T H.460.2 (03/2013)
-- See also the index of all ASN.1 assignments needed in this document

NUMBER-PORTABILITY DEFINITIONS AUTOMATIC TAGS ::=
BEGIN

IMPORTS
  PublicTypeOfNumber, PrivateTypeOfNumber, AliasAddress
    FROM H323-MESSAGES;

NumberPortabilityInfo ::= CHOICE {
  numberPortabilityRejectReason  NumberPortabilityRejectReason,
  nUMBERPORTABILITYDATA
    SEQUENCE {addressTranslated  NULL OPTIONAL,
              portedAddress      PortabilityAddress OPTIONAL,
              routingAddress     PortabilityAddress OPTIONAL,
              regionalParams     RegionalParameters OPTIONAL,
              ...},
  ...
}

NumberPortabilityRejectReason ::= CHOICE {
  unspecified      NULL,
  qorPortedNumber  NULL,
  ...
}

PortabilityAddress ::= SEQUENCE {
  aliasAddress   AliasAddress,
  typeOfAddress  NumberPortabilityTypeOfNumber OPTIONAL,
  ...
}

NumberPortabilityTypeOfNumber ::= CHOICE {
  publicTypeOfNumber       PublicTypeOfNumber,
  privateTypeOfNumber      PrivateTypeOfNumber,
  portabilityTypeOfNumber  PortabilityTypeOfNumber,
  ...
}

PortabilityTypeOfNumber ::= CHOICE {
  portedNumber        NULL,
  routingNumber       NULL,
  concatenatedNumber  NULL,
  ...
}

RegionalParameters ::= SEQUENCE {
  t35CountryCode     INTEGER(0..255),
  t35Extension       INTEGER(0..255),
  variantIdentifier  INTEGER(1..255) OPTIONAL,
  regionalData       OCTET STRING,
  ...
}

END

-- Generated by Asnp, the ASN.1 pretty-printer of France Telecom R&D
