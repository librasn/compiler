-- Module Embedded-DSS2Types (Q.2932.1.:07/1996)
-- See also ITU-T Q.2932.1 (07/1996)
-- See also the index of all ASN.1 assignments needed in this document

Embedded-DSS2Types {itu-t recommendation q 2932 embedded-dSS2-types(7)}
DEFINITIONS EXPLICIT TAGS ::=
BEGIN

EXPORTS DSS2InformationElement;

DSS2InformationElement ::= [APPLICATION 0] IMPLICIT OCTET STRING

END -- of Embedded-dSS2Types

-- Generated by Asnp, the ASN.1 pretty-printer of France Telecom R&D
