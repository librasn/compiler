-- Module CHAT-PROTOCOL (T.134:02/1998)
-- See also ITU-T T.134 (02/1998)
-- See also the index of all ASN.1 assignments needed in this document

--                          Begin CHAT Definitions
--
-- The following base mode ASN.1 definitions are encoded using the BASIC
-- ALIGNED variant of the Packed Encoding Rules of ITU-T Recommendation
-- X.691.
CHAT-PROTOCOL DEFINITIONS AUTOMATIC TAGS ::=
BEGIN

-- NOTE: ===============================================================
-- NOTE: All abstract types defined shall be exported
-- NOTE: ===============================================================
--  H221NonStandardIdentifer
--  Used to specify non-standard objects using H.221 numbering.
--  The first four octets shall designate country code and
--  manufacturer code, assigned as specified in
--  Annex A/H.221 for NS-cap and NS-comm.
H221NonStandardIdentifier ::= OCTET STRING(SIZE (4..255))

Key ::= CHOICE -- Identifier of a standard or non-standard object
         {
  object           OBJECT IDENTIFIER,
  h221NonStandard  H221NonStandardIdentifier
}

--  NonStandardParameter
--  Used to specify non-standard parameters.  This includes a
--  data field which may be used to fill in parameter values
--  of the type indicated by the NonStandardIdentifier
NonStandardParameter ::= SEQUENCE {key    Key,
                                   value  OCTET STRING OPTIONAL
}

ChatString ::= GeneralString(SIZE (0..255)) -- Chat Protocol String


--
--                          Begin CHATPDU Definitions
--
ChatentryPDU ::= SEQUENCE {chatString  ChatString,
                           ...
}

ChatNonStandardPDU ::= SEQUENCE {
  nonStandardTransaction  NonStandardParameter,
  ...
}

ChatPDU ::= CHOICE {
  chatentryPDU        ChatentryPDU,
  chatNonStandardPDU  ChatNonStandardPDU,
  ...
}

--                          End CHAT Definitions
END

-- Generated by Asnp, the ASN.1 pretty-printer of France Telecom R&D
