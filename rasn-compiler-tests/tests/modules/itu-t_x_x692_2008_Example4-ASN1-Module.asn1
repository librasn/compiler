-- Module Example4-ASN1-Module (X.692:11/2008)
-- See also standard
-- See also the index of all ASN.1 assignments needed in this document

Example4-ASN1-Module {joint-iso-itu-t(2) asn1(1) ecn(4) examples(5)
  asn1-module4(15)} DEFINITIONS AUTOMATIC TAGS ::=
BEGIN

ProfileIndication ::=
  SEQUENCE OF
    SEQUENCE {more-bit             BOOLEAN,
              reserved             BIT STRING(SIZE (2)),
              protocol-Profile-ID  INTEGER(0..31)}

profileIndication ProfileIndication ::= {
  {more-bit             FALSE,
   reserved             '00'B,
   protocol-Profile-ID  0},
  {more-bit             TRUE,
   reserved             '00'B,
   protocol-Profile-ID  1}
}

ProfileIndication2 ::= SEQUENCE OF protocol-Profile-ID INTEGER(0..31)

profileIndication2 ProfileIndication2 ::=
  {protocol-Profile-ID 0, protocol-Profile-ID 1}

END

-- Generated by Asnp, the ASN.1 pretty-printer of France Telecom R&D
