-- Module Explicit-Call-Transfer-Operations-and-Errors (Q.952.7:06/1997)
-- See also ITU-T Q.952.7 (06/1997)
-- See also the index of all ASN.1 assignments needed in this document

Explicit-Call-Transfer-Operations-and-Errors {itu-t recommendation q
  952 explicit-call-transfer(7) operations-and-errors(1)} DEFINITIONS ::=
BEGIN

EXPORTS
  ectLinkIdRequest, ectExecute, requestSubaddress, subaddressTransfer,
    explicitEctExecute, linkIdNotAssignedByNetwork, ectLoopTest, ectInform;

IMPORTS
  OPERATION, ERROR
    FROM Remote-Operations-Information-Objects {joint-iso-itu-t
      remote-operations(4) informationObjects(5) version1(0)}
  notAvailable, userNotSubscribed, resourceUnavailable,
    supplementaryServiceInteractionNotAllowed, invalidCallState
    FROM General-Error-List {itu-t recommendation q 950 general-error-list(1)}
  PartySubaddress, PresentedNumberUnscreened
    FROM Addressing-Data-Elements {itu-t recommendation q 932
      addressing-data-elements(7)};

ectLinkIdRequest OPERATION ::= {
  RESULT  LinkId
  ERRORS  {resourceUnavailable}
  CODE    local:93
}

ectExecute OPERATION ::= {
  ERRORS
    {notAvailable | userNotSubscribed | invalidCallState |
      supplementaryServiceInteractionNotAllowed}
  CODE    local:6
}

explicitEctExecute OPERATION ::= {
  ARGUMENT  LinkId
  ERRORS
    {notAvailable | userNotSubscribed | invalidCallState |
      supplementaryServiceInteractionNotAllowed | linkIdNotAssignedByNetwork}
  CODE      local:90
}

requestSubaddress OPERATION ::= {CODE  local:91
}

subaddressTransfer OPERATION ::= {
  ARGUMENT -- transferredToSubaddress --  PartySubaddress
  CODE      local:92
}

ectInform OPERATION ::= {
  ARGUMENT
    SEQUENCE {arg1               ENUMERATED {alerting(0), active(1)},
              redirectionNumber  PresentedNumberUnscreened OPTIONAL}
  CODE      local:94
}

ectLoopTest OPERATION ::= {
  ARGUMENT  CallTransferIdentity
  RESULT    LoopResult
  ERRORS    {notAvailable}
  CODE      local:95
}

LoopResult ::= ENUMERATED {
  insufficientInformation(0), noLoopExists(1), simultaneousTransfer(2)
}

CallTransferIdentity ::= INTEGER(-128..127)

linkIdNotAssignedByNetwork ERROR ::= {CODE  local:61
}

LinkId ::= INTEGER(-32773..32772)

--ectExecute EctExecute						::= 6
--explicitEctExecute ExplicitEctExecute				::= 90
--requestSubaddress RequestSubaddress				::= 91
--subaddressTransfer SubaddressTransfer				::= 92
--ectLinkIdRequest EctLinkIdRequest				::= 93
--ectInform EctInform						::= 94
--ectLoopTest EctLoopTest						::= 95
--linkIdNotAssignedByNetwork LinkIdNotAssignedByNetwork		::= 61
END -- Explicit-Call-Transfer-Operations-and-Errors

-- Generated by Asnp, the ASN.1 pretty-printer of France Telecom R&D
