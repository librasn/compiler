-- Module Q832-2ASN1Module (Q.832.2:03/1999)
-- See also ITU-T Q.832.2 (03/1999)
-- See also the index of all ASN.1 assignments needed in this document

Q832-2ASN1Module {itu-t(0) recommendation(0) q(17) q832(832) dot(127)
  vb52(2) informationModel(0) asn1Modules(2) asn1DefinedTypesModule(0)}
DEFINITIONS IMPLICIT TAGS ::=
BEGIN

-- EXPORTS everything
IMPORTS
  ObjectInstance
    FROM CMIP-1 {joint-iso-itu-t ms(9) cmip(1) modules(0) protocol(3)}
  NameType
    FROM ASN1DefinedTypesModule {ccitt recommendation m 3100
      informationModel(0) asn1Modules(2) asn1DefinedTypesModule(0)}
  ProbableCause
    FROM Attribute-ASN1Module {joint-iso-ccitt ms(9) smi(3) part2(2)
      asn1Module(2) 1} -- X.721
  VciValue
    FROM AtmMIBMod {itu-t(0) recommendation(0) i(9) atmm(751)
      informationModel(0) asn1Module(2) atm(0)};

-- end of imports
-- start of object identifier definitions
q832-2InformationModel OBJECT IDENTIFIER ::=
  {itu-t(0) recommendation(0) q(17) q832(832) dot(127) vb52(2)
   informationModel(0)}

q832-2StandardSpecificExtension OBJECT IDENTIFIER ::=
  {q832-2InformationModel standardSpecificExtension(0)}

q832-2ManagedObjectClass OBJECT IDENTIFIER ::=
  {q832-2InformationModel managedObjectClass(3)}

q832-2Package OBJECT IDENTIFIER ::= {q832-2InformationModel package(4)}

q832-2NameBinding OBJECT IDENTIFIER ::= {q832-2InformationModel nameBinding(6)}

q832-2Attribute OBJECT IDENTIFIER ::= {q832-2InformationModel attribute(7)}

q832-2Action OBJECT IDENTIFIER ::= {q832-2InformationModel action(9)}

q832-2Notification OBJECT IDENTIFIER ::=
  {q832-2InformationModel notification(10)}

vb52ProbableCause OBJECT IDENTIFIER ::= {q832-2StandardSpecificExtension 0}

-- end of object identifier definitions
-- The value assignments for the
-- ProbableCause parameter of the
-- VB5.2 specific TMN communications alarm notification
-- are specified below
bbccProtocolError ProbableCause ::=
  globalValue:{vb52ProbableCause 1}

bbccProtocolSyntaxError ProbableCause ::= globalValue:{vb52ProbableCause 2}

bbccProtocolTimeOutError ProbableCause ::= globalValue:{vb52ProbableCause 3}

-- other ASN.1 definitions in alphabetical order
Boolean ::= BOOLEAN

ConnectionIdentifierFlag ::= INTEGER {
  exclusiveVpciVciCombination(0), preferredVpciVciCombination(1)}

connectionIdentifierFlagDefault ConnectionIdentifierFlag ::=
  exclusiveVpciVciCombination

ResetBbccNotificationResult ::= SEQUENCE {
  resource  ObjectInstance,
  result    ResetBbccResult
}

ResetBbccResult ::= ENUMERATED {notSuccessful(0), successful(1)}

END -- of Q832-2 ASN.1Module

-- Generated by Asnp, the ASN.1 pretty-printer of France Telecom R&D
