LegacyProtocol-EDM-Module {joint-iso-itu-t(2) asn1(1) ecn(4) examples(5)
  edm-module4(13)} ENCODING-DEFINITIONS ::=
BEGIN

EXPORTS LegacyProtocolEncodings;

IMPORTS
  #LegacyProtocolMessages
    FROM LegacyProtocol-ASN1-Module {joint-iso-itu-t(2) asn1(1) ecn(4)
      examples(5) asn1-module4(11)};

LegacyProtocolEncodings #ENCODINGS ::= {
  legacyProtocolMessagesEncoding | message1Encoding}

-- etc.
END
