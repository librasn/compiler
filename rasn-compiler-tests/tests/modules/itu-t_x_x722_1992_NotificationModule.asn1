-- Module NotificationModule (X.722:01/1992)
-- See also ITU-T X.722 (01/1992)
-- See also the index of all ASN.1 assignments needed in this document

NotificationModule {joint-iso-itu-t ms(9) smi(3) part4(4) asn1Module(2)
  notifications(1)} DEFINITIONS ::=
BEGIN

IMPORTS
  ProbableCause, PerceivedSeverity, TrendIndication, BackedUpStatus,
    ProposedRepairActions, ThresholdInfo, ManagementExtension
    FROM Attribute-ASN1Module {joint-iso-itu-t ms(9) smi(3) part2(2)
      asn1Module(2) 1};

ErrorInfo ::= SET {
  probableCause          [0]  ProbableCause OPTIONAL,
  perceivedSeverity      [1]  PerceivedSeverity OPTIONAL,
  trendIndication        [2]  TrendIndication OPTIONAL,
  backedUpStatus         [3]  BackedUpStatus OPTIONAL,
  proposedRepairActions  [4]  ProposedRepairActions OPTIONAL,
  thresholdInfo          [5]  ThresholdInfo OPTIONAL,
  otherInfo              [6]  OtherInfo OPTIONAL
}

ErrorResult ::= NULL

OtherInfo ::= SET OF ManagementExtension

ProtocolError ::= SET OF ManagementExtension

END

-- Generated by Asnp, the ASN.1 pretty-printer of France Telecom R&D
