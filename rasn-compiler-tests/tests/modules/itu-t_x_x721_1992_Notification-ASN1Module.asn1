-- Module Notification-ASN1Module (X.721:02/1992)
-- See also ITU-T X.721 (02/1992)
-- See also the index of all ASN.1 assignments needed in this document

Notification-ASN1Module {joint-iso-itu-t ms(9) smi(3) part2(2) asn1Module(2) 2}
DEFINITIONS IMPLICIT TAGS ::=
BEGIN

IMPORTS
  ProbableCause, SpecificProblems, PerceivedSeverity, BackedUpStatus,
    TrendIndication, ThresholdInfo, NotificationIdentifier,
    CorrelatedNotifications, MonitoredAttributes, ProposedRepairActions,
    AdditionalText, AdditionalInformation, SecurityAlarmCause,
    SecurityAlarmSeverity, SecurityAlarmDetector,
    AttributeValueChangeDefinition, SourceIndicator, AttributeIdentifierList,
    AttributeList, ServiceUser, ServiceProvider
    FROM Attribute-ASN1Module
  ObjectClass, AttributeId, ObjectInstance
    FROM CMIP-1 {joint-iso-itu-t ms(9) cmip(1) modules(0) protocol(3)};

--EXPORTS everything
smi2Notification OBJECT IDENTIFIER ::=
  {joint-iso-itu-t ms(9) smi(3) part2(2) notification(10)}

AlarmInfo ::= SEQUENCE {
  probableCause            ProbableCause,
  specificProblems         [1]  SpecificProblems OPTIONAL,
  perceivedSeverity        PerceivedSeverity,
  backedUpStatus           BackedUpStatus OPTIONAL,
  backUpObject             [2]  ObjectInstance OPTIONAL,
  trendIndication          [3]  TrendIndication OPTIONAL,
  thresholdInfo            [4]  ThresholdInfo OPTIONAL,
  notificationIdentifier   [5]  NotificationIdentifier OPTIONAL,
  correlatedNotifications  [6]  CorrelatedNotifications OPTIONAL,
  stateChangeDefinition    [7]  AttributeValueChangeDefinition OPTIONAL,
  monitoredAttributes      [8]  MonitoredAttributes OPTIONAL,
  proposedRepairActions    [9]  ProposedRepairActions OPTIONAL,
  additionalText           AdditionalText OPTIONAL,
  additionalInformation    [10]  AdditionalInformation OPTIONAL
}

-- backUpObject attribute	backedUpStatus	backUpObject	backUpObject attribute
-- (except in log record	component	component	in log record
--==============================================================================================================================
-- ObjectInstance	T	ObjectInstance	ObjectInstance
-- NULL	F	< absent >	< absent >
-- < absent >	< absent >	< absent >	< absent >
AttributeValueChangeInfo ::= SEQUENCE {
  sourceIndicator                 SourceIndicator OPTIONAL,
  attributeIdentifierList         [1]  AttributeIdentifierList OPTIONAL,
  attributeValueChangeDefinition  AttributeValueChangeDefinition,
  notificationIdentifier          NotificationIdentifier OPTIONAL,
  correlatedNotifications         [2]  CorrelatedNotifications OPTIONAL,
  additionalText                  AdditionalText OPTIONAL,
  additionalInformation           [3]  AdditionalInformation OPTIONAL
}

ObjectInfo ::= SEQUENCE {
  sourceIndicator          SourceIndicator OPTIONAL,
  attributeList            AttributeList OPTIONAL,
  notificationIdentifier   NotificationIdentifier OPTIONAL,
  correlatedNotifications  [1]  CorrelatedNotifications OPTIONAL,
  additionalText           AdditionalText OPTIONAL,
  additionalInformation    [2]  AdditionalInformation OPTIONAL
}

RelationshipChangeInfo ::= SEQUENCE {
  sourceIndicator               SourceIndicator OPTIONAL,
  attributeIdentifierList       [1]  AttributeIdentifierList OPTIONAL,
  relationshipChangeDefinition  AttributeValueChangeDefinition,
  notificationIdentifier        NotificationIdentifier OPTIONAL,
  correlatedNotifications       [2]  CorrelatedNotifications OPTIONAL,
  additionalText                AdditionalText OPTIONAL,
  additionalInformation         [3]  AdditionalInformation OPTIONAL
}

StateChangeInfo ::= SEQUENCE {
  sourceIndicator          SourceIndicator OPTIONAL,
  attributeIdentifierList  [1]  AttributeIdentifierList OPTIONAL,
  stateChangeDefinition    AttributeValueChangeDefinition,
  notificationIdentifier   NotificationIdentifier OPTIONAL,
  correlatedNotifications  [2]  CorrelatedNotifications OPTIONAL,
  additionalText           AdditionalText OPTIONAL,
  additionalInformation    [3]  AdditionalInformation OPTIONAL
}

SecurityAlarmInfo ::= SEQUENCE {
  securityAlarmCause       SecurityAlarmCause,
  securityAlarmSeverity    SecurityAlarmSeverity,
  securityAlarmDetector    SecurityAlarmDetector,
  serviceUser              ServiceUser,
  serviceProvider          ServiceProvider,
  notificationIdentifier   NotificationIdentifier OPTIONAL,
  correlatedNotifications  [1]  CorrelatedNotifications OPTIONAL,
  additionalText           AdditionalText OPTIONAL,
  additionalInformation    [2]  AdditionalInformation OPTIONAL
}

END

-- Generated by Asnp, the ASN.1 pretty-printer of France Telecom R&D
