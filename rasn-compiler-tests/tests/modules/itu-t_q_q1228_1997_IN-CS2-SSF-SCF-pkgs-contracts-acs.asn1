-- Module IN-CS2-SSF-SCF-pkgs-contracts-acs (Q.1228:09/1997)
-- See also ITU-T Q.1228 (09/1997)
-- See also the index of all ASN.1 assignments needed in this document

IN-CS2-SSF-SCF-pkgs-contracts-acs {itu-t recommendation q 1228 modules(0)
  in-cs2-ssf-scf-pkgs-contracts-acs(6) version1(0)} DEFINITIONS ::=
BEGIN

-- This module describes the operation-packages, contracts and application-contexts used
-- over the SSF-SCF interface.
IMPORTS
  PARAMETERS-BOUND, networkSpecificBoundSet
    FROM IN-CS2-classes {itu-t recommendation q 1228 modules(0)
      in-cs2-classes(4) version1(0)}
  ROS-OBJECT-CLASS, CONTRACT, OPERATION-PACKAGE, OPERATION
    FROM Remote-Operations-Information-Objects {joint-iso-itu-t
      remote-operations(4) informationObjects(5) version1(0)}
  TCMessage{}
    FROM TCAPMessages {itu-t recommendation q 773 modules(2) messages(1)
      version3(3)}
  APPLICATION-CONTEXT, dialogue-abstract-syntax
    FROM TC-Notation-Extensions {itu-t recommendation q 775 modules(2)
      notation-extension(4) version1(1)}
  activateServiceFiltering{}, activityTest, analysedInformation{},
    analyseInformation{}, applyCharging{}, applyChargingReport{},
    assistRequestInstructions{}, authorizeTermination{}, callGap{},
    callInformationReport{}, callInformationRequest{}, cancel{},
    cancelStatusReportRequest{}, collectedInformation{}, collectInformation{},
    connect{}, connectToResource{}, continue, continueWithArgument{},
    createCallSegmentAssociation{}, disconnectForwardConnection,
    disconnectForwardConnectionWithArgument{}, disconnectLeg{},
    entityReleased{}, establishTemporaryConnection{},
    eventNotificationCharging{}, eventReportBCSM{}, eventReportFacility{},
    facilitySelectedAndAvailable{}, furnishChargingInformation{},
    holdCallInNetwork, initialDP{}, initiateCallAttempt{}, manageTriggerData{},
    mergeCallSegments{}, moveCallSegments{}, moveLeg{}, oAbandon{}, oAnswer{},
    oCalledPartyBusy{}, oDisconnect{}, oMidCall{}, oNoAnswer{},
    originationAttempt{}, originationAttemptAuthorized{}, oSuspended{},
    reconnect{}, releaseCall{}, reportUTSI{}, requestCurrentStatusReport{},
    requestEveryStatusChangeReport{}, requestFirstStatusMatchReport{},
    requestNotificationChargingEvent{}, requestReportBCSMEvent{},
    requestReportUTSI{}, requestReportFacilityEvent{}, resetTimer{},
    routeSelectFailure{}, selectFacility{}, selectRoute{},
    sendChargingInformation{}, sendFacilityInformation{}, sendSTUI{},
    serviceFilteringResponse{}, splitLeg{}, statusReport{}, tAnswer{},
    tBusy{}, tDisconnect{}, terminationAttempt{}, termAttemptAuthorized{},
    tMidCall{}, tNoAnswer{}, tSuspended{}
    FROM IN-CS2-SSF-SCF-ops-args {itu-t recommendation q 1228 modules(0)
      in-cs2-ssf-scf-ops-args(5) version1(0)}
  playAnnouncement{}, promptAndCollectUserInformation{},
    promptAndReceiveMessage{}, scriptClose{}, scriptEvent{},
    scriptInformation{}, scriptRun{}, specializedResourceReport
    FROM IN-CS2-SCF-SRF-ops-args {itu-t recommendation q 1228 modules(0)
      in-cs2-scf-srf-ops-args(7) version1(0)}
  specializedResourceControlPackage{}, scriptControlPackage{},
    messageControlPackage{}
    FROM IN-CS2-SCF-SRF-pkgs-contracts-acs {itu-t recommendation q 1228
      modules(0) in-cs2-scf-srf-pkgs-contracts-acs(8) version1(0)}
  id-ac-cs2-ssf-scfGenericAC, id-ac-cs2-ssf-scfDPSpecificAC,
    id-ac-cs2-ssf-scfAssistHandoffAC, id-ac-cs2-ssf-scfServiceManagementAC,
    id-ac-cs2-scf-ssfGenericAC, id-ac-cs2-scf-ssfDPSpecificAC,
    id-ac-cs2-scf-ssfTrafficManagementAC, id-ac-cs2-scf-ssfServiceManagementAC,
    id-ac-cs2-scf-ssfStatusReportingAC, id-ac-cs2-scf-ssfTriggerManagementAC,
    id-inCs2SsfToScfGeneric, id-inCs2SsfToScfDpSpecific,
    id-inCs2AssistHandoffSsfToScf, id-inCs2ScfToSsfGeneric,
    id-inCs2ScfToSsfDpSpecific, id-inCs2ScfToSsfTrafficManagement,
    id-inCs2ScfToSsfServiceManagement, id-inCs2SsfToScfServiceManagement,
    id-inCs2ScfToSsfStatusReporting, id-inCs2ScfToSsfTriggerManagement,
    id-as-ssf-scfGenericAS, id-as-ssf-scfDpSpecificAS,
    id-as-assistHandoff-ssf-scfAS, id-as-scf-ssfGenericAS,
    id-as-scf-ssfDpSpecificAS, id-as-scf-ssfTrafficManagementAS,
    id-as-scf-ssfServiceManagementAS, id-as-ssf-scfServiceManagementAS,
    id-as-scf-ssfStatusReportingAS, id-as-scf-ssfTriggerManagementAS,
    id-package-scfActivation, id-package-basicBCPDP, id-package-advancedBCPDP,
    id-package-srf-scfActivationOfAssist,
    id-package-assistConnectionEstablishment,
    id-package-genericDisconnectResource,
    id-package-nonAssistedConnectionEstablishment, id-package-connect,
    id-package-callHandling, id-package-bcsmEventHandling,
    id-package-chargingEventHandling, id-package-ssfCallProcessing,
    id-package-scfCallInitiation, id-package-timer, id-package-billing,
    id-package-charging, id-package-trafficManagement,
    id-package-serviceManagementActivate, id-package-serviceManagementResponse,
    id-package-callReport, id-package-signallingControl,
    id-package-activityTest, id-package-statusReporting, id-package-cancel,
    id-package-cphResponse, id-package-entityReleased,
    id-package-triggerManagement, id-package-uSIHandling,
    id-package-facilityIEHandling, id-package-dpSpecificEventHandling,
    classes, ros-InformationObjects, tc-Messages, tc-NotationExtensions,
    ssf-scf-Operations, scf-srf-Operations, scf-srf-Protocol
    FROM IN-CS2-object-identifiers {itu-t recommendation q 1228 modules(0)
      in-cs2-object-identifiers(17) version1(0)};

-- Application Contexts
cs2ssf-scfGenericAC APPLICATION-CONTEXT ::= {
  CONTRACT                  inCs2SsfToScfGeneric
  DIALOGUE MODE             structured
  ABSTRACT SYNTAXES
    {dialogue-abstract-syntax | ssf-scfGenericAbstractSyntax}
  APPLICATION CONTEXT NAME  id-ac-cs2-ssf-scfGenericAC
}

cs2ssf-scfDPSpecificAC APPLICATION-CONTEXT ::= {
  CONTRACT                  inCs2SsfToScfDpSpecific
  DIALOGUE MODE             structured
  ABSTRACT SYNTAXES
    {dialogue-abstract-syntax | ssf-scfDpSpecificAbstractSyntax}
  APPLICATION CONTEXT NAME  id-ac-cs2-ssf-scfDPSpecificAC
}

cs2ssf-scfAssistHandoffAC APPLICATION-CONTEXT ::= {
  CONTRACT                  inCs2AssistHandoffSsfToScf
  DIALOGUE MODE             structured
  ABSTRACT SYNTAXES
    {dialogue-abstract-syntax | assistHandoff-ssf-scfAbstractSyntax}
  APPLICATION CONTEXT NAME  id-ac-cs2-ssf-scfAssistHandoffAC
}

cs2ssf-scfServiceManagementAC APPLICATION-CONTEXT ::= {
  CONTRACT                  inCs2SsfToScfServiceManagement
  DIALOGUE MODE             structured
  ABSTRACT SYNTAXES
    {dialogue-abstract-syntax | ssf-scfServiceManagementAbstractSyntax}
  APPLICATION CONTEXT NAME  id-ac-cs2-ssf-scfServiceManagementAC
}

cs2scf-ssfGenericAC APPLICATION-CONTEXT ::= {
  CONTRACT                  inCs2ScfToSsfGeneric
  DIALOGUE MODE             structured
  ABSTRACT SYNTAXES
    {dialogue-abstract-syntax | ssf-scfGenericAbstractSyntax}
  APPLICATION CONTEXT NAME  id-ac-cs2-scf-ssfGenericAC
}

cs2scf-ssfDPSpecificAC APPLICATION-CONTEXT ::= {
  CONTRACT                  inCs2ScfToSsfDpSpecific
  DIALOGUE MODE             structured
  ABSTRACT SYNTAXES
    {dialogue-abstract-syntax | scf-ssfDpSpecificAbstractSyntax}
  APPLICATION CONTEXT NAME  id-ac-cs2-scf-ssfDPSpecificAC
}

cs2scf-ssfTrafficManagementAC APPLICATION-CONTEXT ::= {
  CONTRACT                  inCs2ScfToSsfTrafficManagement
  DIALOGUE MODE             structured
  ABSTRACT SYNTAXES
    {dialogue-abstract-syntax | scf-ssfTrafficManagementAbstractSyntax}
  APPLICATION CONTEXT NAME  id-ac-cs2-scf-ssfTrafficManagementAC
}

cs2scf-ssfServiceManagementAC APPLICATION-CONTEXT ::= {
  CONTRACT                  inCs2ScfToSsfServiceManagement
  DIALOGUE MODE             structured
  ABSTRACT SYNTAXES
    {dialogue-abstract-syntax | scf-ssfServiceManagementAbstractSyntax}
  APPLICATION CONTEXT NAME  id-ac-cs2-scf-ssfServiceManagementAC
}

cs2scf-ssfStatusReportingAC APPLICATION-CONTEXT ::= {
  CONTRACT                  inCs2ScfToSsfStatusReporting
  DIALOGUE MODE             structured
  ABSTRACT SYNTAXES
    {dialogue-abstract-syntax | scf-ssfStatusReportingAbstractSyntax}
  APPLICATION CONTEXT NAME  id-ac-cs2-scf-ssfStatusReportingAC
}

cs2scf-ssfTriggerManagementAC APPLICATION-CONTEXT ::= {
  CONTRACT                  inCs2ScfToSsfTriggerManagement
  DIALOGUE MODE             structured
  ABSTRACT SYNTAXES
    {dialogue-abstract-syntax | scf-ssfTriggerManagementAbstractSyntax}
  APPLICATION CONTEXT NAME  id-ac-cs2-scf-ssfTriggerManagementAC
}

-- Contracts
inCs2SsfToScfGeneric CONTRACT ::= {
  -- dialogue initiated by SSF with InitialDP Operation
  INITIATOR CONSUMER OF
    {exceptionInformPackage{networkSpecificBoundSet} |
      scfActivationPackage{networkSpecificBoundSet}}
  RESPONDER CONSUMER OF
    {activityTestPackage |
      assistConnectionEstablishmentPackage{networkSpecificBoundSet} |
      bcsmEventHandlingPackage{networkSpecificBoundSet} |
      billingPackage{networkSpecificBoundSet} |
      callHandlingPackage{networkSpecificBoundSet} |
      callReportPackage{networkSpecificBoundSet} |
      cancelPackage{networkSpecificBoundSet} |
      chargingEventHandlingPackage{networkSpecificBoundSet} |
      chargingPackage{networkSpecificBoundSet} |
      connectPackage{networkSpecificBoundSet} |
      cphResponsePackage{networkSpecificBoundSet} |
      facilityIEHandlingPackage{networkSpecificBoundSet} |
      genericDisconnectResourcePackage{networkSpecificBoundSet} |
      nonAssistedConnectionEstablishmentPackage{networkSpecificBoundSet} |
      signallingControlPackage{networkSpecificBoundSet} |
      specializedResourceControlPackage{networkSpecificBoundSet} |
      scriptControlPackage{networkSpecificBoundSet} |
      messageControlPackage{networkSpecificBoundSet} |
      ssfCallProcessingPackage{networkSpecificBoundSet} |
      statusReportingPackage{networkSpecificBoundSet} |
      timerPackage{networkSpecificBoundSet} |
      trafficManagementPackage{networkSpecificBoundSet} |
      uSIHandlingPackage{networkSpecificBoundSet} |
      scfCallInitiationPackage{networkSpecificBoundSet}}
  ID                     id-inCs2SsfToScfGeneric
}

inCs2SsfToScfDpSpecific CONTRACT ::= {
  -- dialogue initiated by SSF with DP Specific Iniltial Operations
  INITIATOR CONSUMER OF
    {advancedBCPDPPackage{networkSpecificBoundSet} |
      basicBCPDPPackage{networkSpecificBoundSet} |
      exceptionInformPackage{networkSpecificBoundSet}}
  RESPONDER CONSUMER OF
    {activityTestPackage |
      assistConnectionEstablishmentPackage{networkSpecificBoundSet} |
      billingPackage{networkSpecificBoundSet} |
      callHandlingPackage{networkSpecificBoundSet} |
      callReportPackage{networkSpecificBoundSet} |
      cancelPackage{networkSpecificBoundSet} |
      chargingEventHandlingPackage{networkSpecificBoundSet} |
      chargingPackage{networkSpecificBoundSet} |
      connectPackage{networkSpecificBoundSet} |
      cphResponsePackage{networkSpecificBoundSet} |
      dpSpecificEventHandlingPackage{networkSpecificBoundSet} |
      facilityIEHandlingPackage{networkSpecificBoundSet} |
      genericDisconnectResourcePackage{networkSpecificBoundSet} |
      nonAssistedConnectionEstablishmentPackage{networkSpecificBoundSet} |
      signallingControlPackage{networkSpecificBoundSet} |
      specializedResourceControlPackage{networkSpecificBoundSet} |
      scriptControlPackage{networkSpecificBoundSet} |
      messageControlPackage{networkSpecificBoundSet} |
      ssfCallProcessingPackage{networkSpecificBoundSet} |
      statusReportingPackage{networkSpecificBoundSet} |
      timerPackage{networkSpecificBoundSet} |
      trafficManagementPackage{networkSpecificBoundSet} |
      uSIHandlingPackage{networkSpecificBoundSet} |
      scfCallInitiationPackage{networkSpecificBoundSet}}
  ID                     id-inCs2SsfToScfDpSpecific
}

inCs2AssistHandoffSsfToScf CONTRACT ::= {
  -- dialogue initiated by SSF with AssistRequestInstructions
  INITIATOR CONSUMER OF
    {srf-scfActivationOfAssistPackage  {networkSpecificBoundSet}}
  RESPONDER CONSUMER OF
    {activityTestPackage | billingPackage{networkSpecificBoundSet} |
      callHandlingPackage{networkSpecificBoundSet} |
      cancelPackage{networkSpecificBoundSet} |
      chargingPackage{networkSpecificBoundSet} |
      genericDisconnectResourcePackage{networkSpecificBoundSet} |
      nonAssistedConnectionEstablishmentPackage{networkSpecificBoundSet} |
      specializedResourceControlPackage{networkSpecificBoundSet} |
      scriptControlPackage{networkSpecificBoundSet} |
      messageControlPackage{networkSpecificBoundSet} |
      statusReportingPackage{networkSpecificBoundSet} |
      timerPackage{networkSpecificBoundSet}}
  ID                     id-inCs2AssistHandoffSsfToScf
}

inCs2ScfToSsfGeneric CONTRACT ::= {
  -- dialogue initiated by SCF with InitiateCallAttempt, Generic Case
  INITIATOR CONSUMER OF
    {activityTestPackage |
      assistConnectionEstablishmentPackage{networkSpecificBoundSet} |
      bcsmEventHandlingPackage{networkSpecificBoundSet} |
      billingPackage{networkSpecificBoundSet} |
      callHandlingPackage{networkSpecificBoundSet} |
      callReportPackage{networkSpecificBoundSet} |
      cancelPackage{networkSpecificBoundSet} |
      chargingPackage{networkSpecificBoundSet} |
      connectPackage{networkSpecificBoundSet} |
      cphResponsePackage{networkSpecificBoundSet} |
      facilityIEHandlingPackage{networkSpecificBoundSet} |
      genericDisconnectResourcePackage{networkSpecificBoundSet} |
      nonAssistedConnectionEstablishmentPackage{networkSpecificBoundSet} |
      scfCallInitiationPackage{networkSpecificBoundSet} |
      signallingControlPackage{networkSpecificBoundSet} |
      specializedResourceControlPackage{networkSpecificBoundSet} |
      scriptControlPackage{networkSpecificBoundSet} |
      messageControlPackage{networkSpecificBoundSet} |
      ssfCallProcessingPackage{networkSpecificBoundSet} |
      statusReportingPackage{networkSpecificBoundSet} |
      timerPackage{networkSpecificBoundSet} |
      uSIHandlingPackage{networkSpecificBoundSet} |
      scfCallInitiationPackage{networkSpecificBoundSet}}
  RESPONDER CONSUMER OF  {exceptionInformPackage  {networkSpecificBoundSet}}
  ID                     id-inCs2ScfToSsfGeneric
}

inCs2ScfToSsfDpSpecific CONTRACT ::= {
  -- dialogue initiated by SCF with InitiateCallAttempt, DP Specific Case
  INITIATOR CONSUMER OF
    {activityTestPackage |
      assistConnectionEstablishmentPackage{networkSpecificBoundSet} |
      billingPackage{networkSpecificBoundSet} |
      callHandlingPackage{networkSpecificBoundSet} |
      callReportPackage{networkSpecificBoundSet} |
      cancelPackage{networkSpecificBoundSet} |
      chargingEventHandlingPackage{networkSpecificBoundSet} |
      chargingPackage{networkSpecificBoundSet} |
      connectPackage{networkSpecificBoundSet} |
      cphResponsePackage{networkSpecificBoundSet} |
      dpSpecificEventHandlingPackage{networkSpecificBoundSet} |
      facilityIEHandlingPackage{networkSpecificBoundSet} |
      genericDisconnectResourcePackage{networkSpecificBoundSet} |
      nonAssistedConnectionEstablishmentPackage{networkSpecificBoundSet} |
      scfCallInitiationPackage{networkSpecificBoundSet} |
      signallingControlPackage{networkSpecificBoundSet} |
      specializedResourceControlPackage{networkSpecificBoundSet} |
      scriptControlPackage{networkSpecificBoundSet} |
      messageControlPackage{networkSpecificBoundSet} |
      ssfCallProcessingPackage{networkSpecificBoundSet} |
      statusReportingPackage{networkSpecificBoundSet} |
      timerPackage{networkSpecificBoundSet} |
      uSIHandlingPackage{networkSpecificBoundSet} |
      scfCallInitiationPackage{networkSpecificBoundSet}}
  RESPONDER CONSUMER OF  {exceptionInformPackage  {networkSpecificBoundSet}}
  ID                     id-inCs2ScfToSsfDpSpecific
}

inCs2ScfToSsfTrafficManagement CONTRACT ::= {
  -- dialogue initiated by SCF with CallGap
  INITIATOR CONSUMER OF  {trafficManagementPackage  {networkSpecificBoundSet}}
  ID                     id-inCs2ScfToSsfTrafficManagement
}

inCs2ScfToSsfServiceManagement CONTRACT ::= {
  -- dialogue initiated by SCF with ActivateServiceFiltering
  INITIATOR CONSUMER OF
    {serviceManagementActivatePackage  {networkSpecificBoundSet}}
  ID                     id-inCs2ScfToSsfServiceManagement
}

inCs2SsfToScfServiceManagement CONTRACT ::= {
  -- dialogue initiated/ended by SSF with ServiceFilteringResponse
  INITIATOR CONSUMER OF
    {serviceManagementResponsePackage  {networkSpecificBoundSet}}
  ID                     id-inCs2SsfToScfServiceManagement
}

inCs2ScfToSsfStatusReporting CONTRACT ::= {
  -- dialogue initiated by SCF with StatusReporting Operations
  INITIATOR CONSUMER OF
    {cancelPackage{networkSpecificBoundSet} |
      statusReportingPackage{networkSpecificBoundSet}}
  ID                     id-inCs2ScfToSsfStatusReporting
}

inCs2ScfToSsfTriggerManagement CONTRACT ::= {
  -- dialogue initiated by SCF with Manage Trigger Data
  INITIATOR CONSUMER OF  {triggerManagementPackage  {networkSpecificBoundSet}}
  ID                     id-inCs2ScfToSsfTriggerManagement
}

-- Operation Packages
scfActivationPackage{PARAMETERS-BOUND:bound} OPERATION-PACKAGE ::= {
  CONSUMER INVOKES  {initialDP  {bound}}
  ID                id-package-scfActivation
}

basicBCPDPPackage{PARAMETERS-BOUND:bound} OPERATION-PACKAGE ::= {
  CONSUMER INVOKES
    {originationAttemptAuthorized{bound} | collectedInformation{bound} |
      analysedInformation{bound} | routeSelectFailure{bound} |
      facilitySelectedAndAvailable{bound} | oAbandon{bound} |
      originationAttempt{bound} | terminationAttempt{bound} |
      oCalledPartyBusy{bound} | oNoAnswer{bound} | oAnswer{bound} |
      oDisconnect{bound} | termAttemptAuthorized{bound} | tBusy{bound} |
      tNoAnswer{bound} | tAnswer{bound} | tDisconnect{bound}}
  ID                id-package-basicBCPDP
}

advancedBCPDPPackage{PARAMETERS-BOUND:bound} OPERATION-PACKAGE ::= {
  CONSUMER INVOKES
    {oMidCall{bound} | oSuspended{bound} | tMidCall{bound} | tSuspended{bound}}
  ID                id-package-advancedBCPDP
}

srf-scfActivationOfAssistPackage{PARAMETERS-BOUND:bound} OPERATION-PACKAGE ::=
  {
  CONSUMER INVOKES  {assistRequestInstructions{bound}}
  ID                id-package-srf-scfActivationOfAssist
}

assistConnectionEstablishmentPackage{PARAMETERS-BOUND:bound} OPERATION-PACKAGE
  ::= {
  CONSUMER INVOKES  {establishTemporaryConnection{bound}}
  ID                id-package-assistConnectionEstablishment
}

genericDisconnectResourcePackage{PARAMETERS-BOUND:bound} OPERATION-PACKAGE ::=
  {
  CONSUMER INVOKES
    {disconnectForwardConnection |
      disconnectForwardConnectionWithArgument{bound}}
  ID                id-package-genericDisconnectResource
}

nonAssistedConnectionEstablishmentPackage{PARAMETERS-BOUND:bound}
  OPERATION-PACKAGE ::= {
  CONSUMER INVOKES  {connectToResource{bound}}
  ID                id-package-nonAssistedConnectionEstablishment
}

connectPackage{PARAMETERS-BOUND:bound} OPERATION-PACKAGE ::= {
  CONSUMER INVOKES  {connect{bound}}
  ID                id-package-connect
}

callHandlingPackage{PARAMETERS-BOUND:bound} OPERATION-PACKAGE ::= {
  CONSUMER INVOKES  {holdCallInNetwork | releaseCall{bound}}
  ID                id-package-callHandling
}

bcsmEventHandlingPackage{PARAMETERS-BOUND:bound} OPERATION-PACKAGE ::=
{
  CONSUMER INVOKES  {requestReportBCSMEvent{bound}}
  SUPPLIER INVOKES  {eventReportBCSM{bound}}
  ID                id-package-bcsmEventHandling
}

dpSpecificEventHandlingPackage{PARAMETERS-BOUND:bound} OPERATION-PACKAGE ::=
{
  CONSUMER INVOKES  {requestReportBCSMEvent{bound}}
  SUPPLIER INVOKES
    {originationAttemptAuthorized{bound} | collectedInformation{bound} |
      analysedInformation{bound} | routeSelectFailure{bound} |
      facilitySelectedAndAvailable{bound} | oAbandon{bound} |
      originationAttempt{bound} | terminationAttempt{bound} |
      oCalledPartyBusy{bound} | oNoAnswer{bound} | oAnswer{bound} |
      oDisconnect{bound} | termAttemptAuthorized{bound} | tBusy{bound} |
      tNoAnswer{bound} | tAnswer{bound} | tDisconnect{bound} | oMidCall{bound}
      | oSuspended{bound} | tMidCall{bound} | tSuspended{bound}}
  ID                id-package-dpSpecificEventHandling
}

chargingEventHandlingPackage{PARAMETERS-BOUND:bound} OPERATION-PACKAGE ::=
{
  CONSUMER INVOKES  {requestNotificationChargingEvent  {bound}}
  SUPPLIER INVOKES  {eventNotificationCharging  {bound}}
  ID                id-package-chargingEventHandling
}

ssfCallProcessingPackage{PARAMETERS-BOUND:bound} OPERATION-PACKAGE ::=
{
  CONSUMER INVOKES
    {collectInformation{bound} | analyseInformation{bound} |
      authorizeTermination{bound} | selectRoute{bound} | selectFacility{bound}
      | continue}
  ID                id-package-ssfCallProcessing
}

scfCallInitiationPackage{PARAMETERS-BOUND:bound} OPERATION-PACKAGE ::=
{
  CONSUMER INVOKES  {initiateCallAttempt  {bound}}
  ID                id-package-scfCallInitiation
}

timerPackage{PARAMETERS-BOUND:bound} OPERATION-PACKAGE ::= {
  CONSUMER INVOKES  {resetTimer  {bound}}
  ID                id-package-timer
}

billingPackage{PARAMETERS-BOUND:bound} OPERATION-PACKAGE ::= {
  CONSUMER INVOKES  {furnishChargingInformation  {bound}}
  ID                id-package-billing
}

chargingPackage{PARAMETERS-BOUND:bound} OPERATION-PACKAGE ::= {
  CONSUMER INVOKES  {applyCharging  {bound}}
  SUPPLIER INVOKES  {applyChargingReport  {bound}}
  ID                id-package-charging
}

trafficManagementPackage{PARAMETERS-BOUND:bound} OPERATION-PACKAGE ::=
{
  CONSUMER INVOKES  {callGap  {bound}}
  ID                id-package-trafficManagement
}

serviceManagementActivatePackage{PARAMETERS-BOUND:bound} OPERATION-PACKAGE ::=
  {
  CONSUMER INVOKES  {activateServiceFiltering  {bound}}
  ID                id-package-serviceManagementActivate
}

serviceManagementResponsePackage{PARAMETERS-BOUND:bound} OPERATION-PACKAGE ::=
  {
  CONSUMER INVOKES  {serviceFilteringResponse  {bound}}
  ID                id-package-serviceManagementResponse
}

callReportPackage{PARAMETERS-BOUND:bound} OPERATION-PACKAGE ::= {
  CONSUMER INVOKES  {callInformationRequest  {bound}}
  SUPPLIER INVOKES  {callInformationReport  {bound}}
  ID                id-package-callReport
}

signallingControlPackage{PARAMETERS-BOUND:bound} OPERATION-PACKAGE ::=
{
  CONSUMER INVOKES  {sendChargingInformation  {bound}}
  ID                id-package-signallingControl
}

activityTestPackage OPERATION-PACKAGE ::= {
  CONSUMER INVOKES  {activityTest}
  ID                id-package-activityTest
}

statusReportingPackage{PARAMETERS-BOUND:bound} OPERATION-PACKAGE ::=
{
  CONSUMER INVOKES
    {requestCurrentStatusReport{bound} | requestEveryStatusChangeReport{bound}
      | requestFirstStatusMatchReport{bound}}
  SUPPLIER INVOKES  {statusReport{bound}}
  ID                id-package-statusReporting
}

cancelPackage{PARAMETERS-BOUND:bound} OPERATION-PACKAGE ::= {
  CONSUMER INVOKES  {cancel{bound} | cancelStatusReportRequest{bound}}
  ID                id-package-cancel
}

cphResponsePackage{PARAMETERS-BOUND:bound} OPERATION-PACKAGE ::= {
  CONSUMER INVOKES
    {continueWithArgument{bound} | disconnectLeg{bound} |
      mergeCallSegments{bound} | moveCallSegments{bound} | moveLeg{bound} |
      createCallSegmentAssociation{bound} | reconnect{bound} | splitLeg{bound}}
  ID                id-package-cphResponse
}

exceptionInformPackage{PARAMETERS-BOUND:bound} OPERATION-PACKAGE ::=
{
  CONSUMER INVOKES  {entityReleased  {bound}}
  ID                id-package-entityReleased
}

triggerManagementPackage{PARAMETERS-BOUND:bound} OPERATION-PACKAGE ::=
{
  CONSUMER INVOKES  {manageTriggerData  {bound}}
  ID                id-package-triggerManagement
}

uSIHandlingPackage{PARAMETERS-BOUND:bound} OPERATION-PACKAGE ::= {
  CONSUMER INVOKES  {requestReportUTSI{bound} | sendSTUI{bound}}
  SUPPLIER INVOKES  {reportUTSI{bound}}
  ID                id-package-uSIHandling
}

facilityIEHandlingPackage{PARAMETERS-BOUND:bound} OPERATION-PACKAGE ::=
{
  CONSUMER INVOKES
    {requestReportFacilityEvent{bound} | sendFacilityInformation{bound}}
  SUPPLIER INVOKES  {eventReportFacility{bound}}
  ID                id-package-facilityIEHandling
}

-- Abstract Syntaxes
ssf-scfGenericAbstractSyntax ABSTRACT-SYNTAX ::= {
  GenericSSF-SCF-PDUs
  IDENTIFIED BY  id-as-ssf-scfGenericAS
}

GenericSSF-SCF-PDUs ::=
  TCMessage{{SsfToScfGenericInvokable}, {SsfToScfGenericReturnable}}

SsfToScfGenericInvokable OPERATION ::=
  {activateServiceFiltering{networkSpecificBoundSet} | activityTest |
   applyCharging{networkSpecificBoundSet} |
   applyChargingReport{networkSpecificBoundSet} |
   callInformationReport{networkSpecificBoundSet} |
   callInformationRequest{networkSpecificBoundSet} |
   cancel{networkSpecificBoundSet} |
   cancelStatusReportRequest{networkSpecificBoundSet} |
   collectInformation{networkSpecificBoundSet} |
   connect{networkSpecificBoundSet} |
   connectToResource{networkSpecificBoundSet} | disconnectForwardConnection |
   disconnectForwardConnectionWithArgument{networkSpecificBoundSet} |
   disconnectLeg{networkSpecificBoundSet} |
   entityReleased{networkSpecificBoundSet} |
   establishTemporaryConnection{networkSpecificBoundSet} |
   eventNotificationCharging{networkSpecificBoundSet} |
   eventReportBCSM{networkSpecificBoundSet} |
   eventReportFacility{networkSpecificBoundSet} |
   furnishChargingInformation{networkSpecificBoundSet} | holdCallInNetwork |
   initialDP{networkSpecificBoundSet} |
   mergeCallSegments{networkSpecificBoundSet} |
   moveCallSegments{networkSpecificBoundSet} | moveLeg{networkSpecificBoundSet}
   | createCallSegmentAssociation{networkSpecificBoundSet} |
   reconnect{networkSpecificBoundSet} | releaseCall{networkSpecificBoundSet} |
   reportUTSI{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   sendChargingInformation{networkSpecificBoundSet} |
   sendFacilityInformation{networkSpecificBoundSet} |
   sendSTUI{networkSpecificBoundSet} |
   serviceFilteringResponse{networkSpecificBoundSet} |
   splitLeg{networkSpecificBoundSet} | statusReport{networkSpecificBoundSet} |
   playAnnouncement{networkSpecificBoundSet} |
   promptAndCollectUserInformation{networkSpecificBoundSet} |
   scriptClose{networkSpecificBoundSet} | scriptEvent{networkSpecificBoundSet}
   | scriptInformation{networkSpecificBoundSet} |
   scriptRun{networkSpecificBoundSet} | specializedResourceReport |
   promptAndReceiveMessage{networkSpecificBoundSet}}

SsfToScfGenericReturnable OPERATION ::=
  {activateServiceFiltering{networkSpecificBoundSet} | activityTest |
   applyCharging{networkSpecificBoundSet} |
   applyChargingReport{networkSpecificBoundSet} |
   callGap{networkSpecificBoundSet} |
   callInformationRequest{networkSpecificBoundSet} |
   cancel{networkSpecificBoundSet} |
   cancelStatusReportRequest{networkSpecificBoundSet} |
   collectInformation{networkSpecificBoundSet} |
   connect{networkSpecificBoundSet} |
   connectToResource{networkSpecificBoundSet} | continue |
   continueWithArgument{networkSpecificBoundSet} | disconnectForwardConnection
   | disconnectForwardConnectionWithArgument{networkSpecificBoundSet} |
   disconnectLeg{networkSpecificBoundSet} |
   establishTemporaryConnection{networkSpecificBoundSet} |
   furnishChargingInformation{networkSpecificBoundSet} | holdCallInNetwork |
   initialDP{networkSpecificBoundSet} |
   mergeCallSegments{networkSpecificBoundSet} |
   moveCallSegments{networkSpecificBoundSet} | moveLeg{networkSpecificBoundSet}
   | createCallSegmentAssociation{networkSpecificBoundSet} |
   reconnect{networkSpecificBoundSet} | releaseCall{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   sendChargingInformation{networkSpecificBoundSet} |
   sendFacilityInformation{networkSpecificBoundSet} |
   sendSTUI{networkSpecificBoundSet} | splitLeg{networkSpecificBoundSet} |
   playAnnouncement{networkSpecificBoundSet} |
   promptAndCollectUserInformation{networkSpecificBoundSet} |
   scriptClose{networkSpecificBoundSet} |
   scriptInformation{networkSpecificBoundSet} |
   scriptRun{networkSpecificBoundSet} |
   promptAndReceiveMessage{networkSpecificBoundSet}}

ssf-scfDpSpecificAbstractSyntax ABSTRACT-SYNTAX ::= {
  DpSpecificSSF-SCF-PDUs
  IDENTIFIED BY  id-as-ssf-scfDpSpecificAS
}

DpSpecificSSF-SCF-PDUs ::=
  TCMessage{{SsfToScfDpSpecificInvokable}, {SsfToScfDpSpecificReturnable}}

SsfToScfDpSpecificInvokable OPERATION ::=
  {activateServiceFiltering{networkSpecificBoundSet} | activityTest |
   analyseInformation{networkSpecificBoundSet} |
   analysedInformation{networkSpecificBoundSet} |
   applyCharging{networkSpecificBoundSet} |
   applyChargingReport{networkSpecificBoundSet} |
   assistRequestInstructions{networkSpecificBoundSet} |
   callInformationReport{networkSpecificBoundSet} |
   callInformationRequest{networkSpecificBoundSet} |
   cancel{networkSpecificBoundSet} |
   cancelStatusReportRequest{networkSpecificBoundSet} |
   collectedInformation{networkSpecificBoundSet} |
   collectInformation{networkSpecificBoundSet} |
   connect{networkSpecificBoundSet} |
   connectToResource{networkSpecificBoundSet} | disconnectForwardConnection |
   disconnectForwardConnectionWithArgument{networkSpecificBoundSet} |
   disconnectLeg{networkSpecificBoundSet} |
   entityReleased{networkSpecificBoundSet} |
   establishTemporaryConnection{networkSpecificBoundSet} |
   eventNotificationCharging{networkSpecificBoundSet} |
   eventReportFacility{networkSpecificBoundSet} |
   furnishChargingInformation{networkSpecificBoundSet} | holdCallInNetwork |
   initiateCallAttempt{networkSpecificBoundSet} |
   mergeCallSegments{networkSpecificBoundSet} |
   moveCallSegments{networkSpecificBoundSet} | moveLeg{networkSpecificBoundSet}
   | oAbandon{networkSpecificBoundSet} | oAnswer{networkSpecificBoundSet} |
   oCalledPartyBusy{networkSpecificBoundSet} |
   oDisconnect{networkSpecificBoundSet} | oMidCall{networkSpecificBoundSet} |
   oNoAnswer{networkSpecificBoundSet} |
   createCallSegmentAssociation{networkSpecificBoundSet} |
   originationAttemptAuthorized{networkSpecificBoundSet} |
   reconnect{networkSpecificBoundSet} | releaseCall{networkSpecificBoundSet} |
   reportUTSI{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   routeSelectFailure{networkSpecificBoundSet} |
   selectFacility{networkSpecificBoundSet} |
   selectRoute{networkSpecificBoundSet} |
   sendChargingInformation{networkSpecificBoundSet} |
   sendFacilityInformation{networkSpecificBoundSet} |
   sendSTUI{networkSpecificBoundSet} |
   serviceFilteringResponse{networkSpecificBoundSet} |
   splitLeg{networkSpecificBoundSet} | statusReport{networkSpecificBoundSet} |
   tAnswer{networkSpecificBoundSet} | tBusy{networkSpecificBoundSet} |
   tDisconnect{networkSpecificBoundSet} |
   termAttemptAuthorized{networkSpecificBoundSet} |
   tMidCall{networkSpecificBoundSet} | tNoAnswer{networkSpecificBoundSet} |
   playAnnouncement{networkSpecificBoundSet} |
   promptAndCollectUserInformation{networkSpecificBoundSet} |
   scriptClose{networkSpecificBoundSet} | scriptEvent{networkSpecificBoundSet}
   | scriptInformation{networkSpecificBoundSet} |
   scriptRun{networkSpecificBoundSet} | specializedResourceReport |
   promptAndReceiveMessage{networkSpecificBoundSet}}

SsfToScfDpSpecificReturnable OPERATION ::=
  {activateServiceFiltering{networkSpecificBoundSet} | activityTest |
   analyseInformation{networkSpecificBoundSet} |
   analysedInformation{networkSpecificBoundSet} |
   applyCharging{networkSpecificBoundSet} |
   applyChargingReport{networkSpecificBoundSet} |
   assistRequestInstructions{networkSpecificBoundSet} |
   callGap{networkSpecificBoundSet} |
   callInformationRequest{networkSpecificBoundSet} |
   cancel{networkSpecificBoundSet} |
   cancelStatusReportRequest{networkSpecificBoundSet} |
   collectedInformation{networkSpecificBoundSet} |
   collectInformation{networkSpecificBoundSet} |
   connect{networkSpecificBoundSet} |
   connectToResource{networkSpecificBoundSet} | continue |
   continueWithArgument{networkSpecificBoundSet} | disconnectForwardConnection
   | disconnectForwardConnectionWithArgument{networkSpecificBoundSet} |
   disconnectLeg{networkSpecificBoundSet} |
   establishTemporaryConnection{networkSpecificBoundSet} |
   furnishChargingInformation{networkSpecificBoundSet} | holdCallInNetwork |
   initiateCallAttempt{networkSpecificBoundSet} |
   mergeCallSegments{networkSpecificBoundSet} |
   moveCallSegments{networkSpecificBoundSet} | moveLeg{networkSpecificBoundSet}
   | oAbandon{networkSpecificBoundSet} | oAnswer{networkSpecificBoundSet} |
   oCalledPartyBusy{networkSpecificBoundSet} |
   oDisconnect{networkSpecificBoundSet} | oMidCall{networkSpecificBoundSet} |
   oNoAnswer{networkSpecificBoundSet} |
   createCallSegmentAssociation{networkSpecificBoundSet} |
   originationAttemptAuthorized{networkSpecificBoundSet} |
   reconnect{networkSpecificBoundSet} | releaseCall{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   routeSelectFailure{networkSpecificBoundSet} |
   selectFacility{networkSpecificBoundSet} |
   selectRoute{networkSpecificBoundSet} |
   sendChargingInformation{networkSpecificBoundSet} |
   sendFacilityInformation{networkSpecificBoundSet} |
   sendSTUI{networkSpecificBoundSet} | splitLeg{networkSpecificBoundSet} |
   tAnswer{networkSpecificBoundSet} | tBusy{networkSpecificBoundSet} |
   tDisconnect{networkSpecificBoundSet} |
   termAttemptAuthorized{networkSpecificBoundSet} |
   tMidCall{networkSpecificBoundSet} | tNoAnswer{networkSpecificBoundSet} |
   playAnnouncement{networkSpecificBoundSet} |
   promptAndCollectUserInformation{networkSpecificBoundSet} |
   scriptClose{networkSpecificBoundSet} |
   scriptInformation{networkSpecificBoundSet} |
   scriptRun{networkSpecificBoundSet} |
   promptAndReceiveMessage{networkSpecificBoundSet}}

assistHandoff-ssf-scfAbstractSyntax ABSTRACT-SYNTAX ::= {
  AssistHandoffSSF-SCF-PDUs
  IDENTIFIED BY  id-as-assistHandoff-ssf-scfAS
}

AssistHandoffSSF-SCF-PDUs ::=
  TCMessage
    {{AssistHandoffSsfToScfInvokable}, {AssistHandoffSsfToScfReturnable}}

AssistHandoffSsfToScfInvokable OPERATION ::=
  {activityTest | applyCharging{networkSpecificBoundSet} |
   applyChargingReport{networkSpecificBoundSet} |
   assistRequestInstructions{networkSpecificBoundSet} |
   cancel{networkSpecificBoundSet} |
   cancelStatusReportRequest{networkSpecificBoundSet} |
   connectToResource{networkSpecificBoundSet} | disconnectForwardConnection |
   disconnectForwardConnectionWithArgument{networkSpecificBoundSet} |
   furnishChargingInformation{networkSpecificBoundSet} | holdCallInNetwork |
   playAnnouncement{networkSpecificBoundSet} |
   promptAndCollectUserInformation{networkSpecificBoundSet} |
   requestCurrentStatusReport{networkSpecificBoundSet} |
   requestEveryStatusChangeReport{networkSpecificBoundSet} |
   requestFirstStatusMatchReport{networkSpecificBoundSet} |
   resetTimer{networkSpecificBoundSet} | statusReport{networkSpecificBoundSet}
   | scriptClose{networkSpecificBoundSet} |
   scriptEvent{networkSpecificBoundSet} |
   scriptInformation{networkSpecificBoundSet} |
   scriptRun{networkSpecificBoundSet} | specializedResourceReport |
   promptAndReceiveMessage{networkSpecificBoundSet}}

AssistHandoffSsfToScfReturnable OPERATION ::=
  {activityTest | applyCharging{networkSpecificBoundSet} |
   applyChargingReport{networkSpecificBoundSet} |
   assistRequestInstructions{networkSpecificBoundSet} |
   cancel{networkSpecificBoundSet} |
   cancelStatusReportRequest{networkSpecificBoundSet} |
   connectToResource{networkSpecificBoundSet} | disconnectForwardConnection |
   disconnectForwardConnectionWithArgument{networkSpecificBoundSet} |
   furnishChargingInformation{networkSpecificBoundSet} | holdCallInNetwork |
   playAnnouncement{networkSpecificBoundSet} |
   promptAndCollectUserInformation{networkSpecificBoundSet} |
   requestCurrentStatusReport{networkSpecificBoundSet} |
   requestEveryStatusChangeReport{networkSpecificBoundSet} |
   requestFirstStatusMatchReport{networkSpecificBoundSet} |
   resetTimer{networkSpecificBoundSet} | scriptClose{networkSpecificBoundSet} |
   scriptInformation{networkSpecificBoundSet} |
   scriptRun{networkSpecificBoundSet} |
   promptAndReceiveMessage{networkSpecificBoundSet}}

scf-ssfGenericAbstractSyntax ABSTRACT-SYNTAX ::= {
  GenericSCF-SSF-PDUs
  IDENTIFIED BY  id-as-scf-ssfGenericAS
}

GenericSCF-SSF-PDUs ::=
  TCMessage{{ScfToSsfGenericInvokable}, {ScfToSsfGenericReturnable}}

ScfToSsfGenericInvokable OPERATION ::=
  {activateServiceFiltering{networkSpecificBoundSet} | activityTest |
   applyCharging{networkSpecificBoundSet} |
   applyChargingReport{networkSpecificBoundSet} |
   callInformationRequest{networkSpecificBoundSet} |
   cancel{networkSpecificBoundSet} |
   cancelStatusReportRequest{networkSpecificBoundSet} |
   collectInformation{networkSpecificBoundSet} |
   connect{networkSpecificBoundSet} |
   connectToResource{networkSpecificBoundSet} | continue |
   continueWithArgument{networkSpecificBoundSet} | disconnectForwardConnection
   | disconnectForwardConnectionWithArgument{networkSpecificBoundSet} |
   disconnectLeg{networkSpecificBoundSet} |
   establishTemporaryConnection{networkSpecificBoundSet} |
   furnishChargingInformation{networkSpecificBoundSet} | holdCallInNetwork |
   initiateCallAttempt{networkSpecificBoundSet} |
   mergeCallSegments{networkSpecificBoundSet} |
   moveCallSegments{networkSpecificBoundSet} | moveLeg{networkSpecificBoundSet}
   | createCallSegmentAssociation{networkSpecificBoundSet} |
   releaseCall{networkSpecificBoundSet} | reconnect{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   sendChargingInformation{networkSpecificBoundSet} |
   sendFacilityInformation{networkSpecificBoundSet} |
   sendSTUI{networkSpecificBoundSet} | splitLeg{networkSpecificBoundSet} |
   playAnnouncement{networkSpecificBoundSet} |
   promptAndCollectUserInformation{networkSpecificBoundSet} |
   scriptClose{networkSpecificBoundSet} |
   scriptInformation{networkSpecificBoundSet} |
   scriptRun{networkSpecificBoundSet} |
   promptAndReceiveMessage{networkSpecificBoundSet}}

ScfToSsfGenericReturnable OPERATION ::=
  {activateServiceFiltering{networkSpecificBoundSet} | activityTest |
   applyCharging{networkSpecificBoundSet} |
   applyChargingReport{networkSpecificBoundSet} |
   callInformationReport{networkSpecificBoundSet} |
   callInformationRequest{networkSpecificBoundSet} |
   cancel{networkSpecificBoundSet} |
   cancelStatusReportRequest{networkSpecificBoundSet} |
   collectInformation{networkSpecificBoundSet} |
   connect{networkSpecificBoundSet} |
   connectToResource{networkSpecificBoundSet} | disconnectForwardConnection |
   disconnectForwardConnectionWithArgument{networkSpecificBoundSet} |
   disconnectLeg{networkSpecificBoundSet} |
   entityReleased{networkSpecificBoundSet} |
   establishTemporaryConnection{networkSpecificBoundSet} |
   eventNotificationCharging{networkSpecificBoundSet} |
   resetTimer{networkSpecificBoundSet} |
   eventReportBCSM{networkSpecificBoundSet} |
   eventReportFacility{networkSpecificBoundSet} |
   furnishChargingInformation{networkSpecificBoundSet} | holdCallInNetwork |
   initiateCallAttempt{networkSpecificBoundSet} |
   mergeCallSegments{networkSpecificBoundSet} |
   moveCallSegments{networkSpecificBoundSet} | moveLeg{networkSpecificBoundSet}
   | createCallSegmentAssociation{networkSpecificBoundSet} |
   reconnect{networkSpecificBoundSet} | reportUTSI{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   sendChargingInformation{networkSpecificBoundSet} |
   sendFacilityInformation{networkSpecificBoundSet} |
   sendSTUI{networkSpecificBoundSet} |
   serviceFilteringResponse{networkSpecificBoundSet} |
   splitLeg{networkSpecificBoundSet} | statusReport{networkSpecificBoundSet} |
   playAnnouncement{networkSpecificBoundSet} |
   promptAndCollectUserInformation{networkSpecificBoundSet} |
   scriptClose{networkSpecificBoundSet} | scriptEvent{networkSpecificBoundSet}
   | scriptInformation{networkSpecificBoundSet} |
   scriptRun{networkSpecificBoundSet} | specializedResourceReport |
   promptAndReceiveMessage{networkSpecificBoundSet}}

scf-ssfDpSpecificAbstractSyntax ABSTRACT-SYNTAX ::= {
  DpSpecificSCF-SSF-PDUs
  IDENTIFIED BY  id-as-scf-ssfDpSpecificAS
}

DpSpecificSCF-SSF-PDUs ::=
  TCMessage{{ScfToSsfDpSpecificInvokable}, {ScfToSsfDpSpecificReturnable}}

ScfToSsfDpSpecificInvokable OPERATION ::=
  {activateServiceFiltering{networkSpecificBoundSet} | activityTest |
   analyseInformation{networkSpecificBoundSet} |
   analysedInformation{networkSpecificBoundSet} |
   applyCharging{networkSpecificBoundSet} |
   applyChargingReport{networkSpecificBoundSet} |
   callInformationRequest{networkSpecificBoundSet} |
   cancel{networkSpecificBoundSet} |
   cancelStatusReportRequest{networkSpecificBoundSet} |
   collectedInformation{networkSpecificBoundSet} |
   collectInformation{networkSpecificBoundSet} |
   connect{networkSpecificBoundSet} |
   connectToResource{networkSpecificBoundSet} | continue |
   continueWithArgument{networkSpecificBoundSet} | disconnectForwardConnection
   | disconnectForwardConnectionWithArgument{networkSpecificBoundSet} |
   disconnectLeg{networkSpecificBoundSet} |
   establishTemporaryConnection{networkSpecificBoundSet} |
   furnishChargingInformation{networkSpecificBoundSet} | holdCallInNetwork |
   initiateCallAttempt{networkSpecificBoundSet} |
   mergeCallSegments{networkSpecificBoundSet} |
   moveCallSegments{networkSpecificBoundSet} | moveLeg{networkSpecificBoundSet}
   | oAbandon{networkSpecificBoundSet} | oAnswer{networkSpecificBoundSet} |
   oCalledPartyBusy{networkSpecificBoundSet} |
   oDisconnect{networkSpecificBoundSet} | oMidCall{networkSpecificBoundSet} |
   oNoAnswer{networkSpecificBoundSet} |
   createCallSegmentAssociation{networkSpecificBoundSet} |
   originationAttemptAuthorized{networkSpecificBoundSet} |
   reconnect{networkSpecificBoundSet} | releaseCall{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   routeSelectFailure{networkSpecificBoundSet} |
   selectFacility{networkSpecificBoundSet} |
   selectRoute{networkSpecificBoundSet} |
   sendChargingInformation{networkSpecificBoundSet} |
   sendFacilityInformation{networkSpecificBoundSet} |
   sendSTUI{networkSpecificBoundSet} | splitLeg{networkSpecificBoundSet} |
   tAnswer{networkSpecificBoundSet} | tBusy{networkSpecificBoundSet} |
   tDisconnect{networkSpecificBoundSet} |
   termAttemptAuthorized{networkSpecificBoundSet} |
   tMidCall{networkSpecificBoundSet} | tNoAnswer{networkSpecificBoundSet} |
   playAnnouncement{networkSpecificBoundSet} |
   promptAndCollectUserInformation{networkSpecificBoundSet} |
   scriptClose{networkSpecificBoundSet} |
   scriptInformation{networkSpecificBoundSet} |
   scriptRun{networkSpecificBoundSet} |
   promptAndReceiveMessage{networkSpecificBoundSet}}

ScfToSsfDpSpecificReturnable OPERATION ::=
  {activateServiceFiltering{networkSpecificBoundSet} | activityTest |
   analyseInformation{networkSpecificBoundSet} |
   analysedInformation{networkSpecificBoundSet} |
   applyCharging{networkSpecificBoundSet} |
   applyChargingReport{networkSpecificBoundSet} |
   callInformationReport{networkSpecificBoundSet} |
   callInformationRequest{networkSpecificBoundSet} |
   cancel{networkSpecificBoundSet} |
   cancelStatusReportRequest{networkSpecificBoundSet} |
   collectedInformation{networkSpecificBoundSet} |
   collectInformation{networkSpecificBoundSet} |
   connect{networkSpecificBoundSet} |
   connectToResource{networkSpecificBoundSet} | disconnectForwardConnection |
   disconnectForwardConnectionWithArgument{networkSpecificBoundSet} |
   disconnectLeg{networkSpecificBoundSet} |
   entityReleased{networkSpecificBoundSet} |
   establishTemporaryConnection{networkSpecificBoundSet} |
   eventNotificationCharging{networkSpecificBoundSet} |
   eventReportFacility{networkSpecificBoundSet} |
   furnishChargingInformation{networkSpecificBoundSet} | holdCallInNetwork |
   initiateCallAttempt{networkSpecificBoundSet} |
   initiateCallAttempt{networkSpecificBoundSet} |
   mergeCallSegments{networkSpecificBoundSet} |
   moveCallSegments{networkSpecificBoundSet} | moveLeg{networkSpecificBoundSet}
   | oAnswer{networkSpecificBoundSet} |
   oCalledPartyBusy{networkSpecificBoundSet} |
   oDisconnect{networkSpecificBoundSet} | oMidCall{networkSpecificBoundSet} |
   oAbandon{networkSpecificBoundSet} | oNoAnswer{networkSpecificBoundSet} |
   createCallSegmentAssociation{networkSpecificBoundSet} |
   originationAttemptAuthorized{networkSpecificBoundSet} |
   reconnect{networkSpecificBoundSet} | reportUTSI{networkSpecificBoundSet} |
   requestCurrentStatusReport{networkSpecificBoundSet} |
   requestEveryStatusChangeReport{networkSpecificBoundSet} |
   requestFirstStatusMatchReport{networkSpecificBoundSet} |
   requestNotificationChargingEvent{networkSpecificBoundSet} |
   requestReportBCSMEvent{networkSpecificBoundSet} |
   requestReportFacilityEvent{networkSpecificBoundSet} |
   requestReportUTSI{networkSpecificBoundSet} |
   resetTimer{networkSpecificBoundSet} |
   routeSelectFailure{networkSpecificBoundSet} |
   selectFacility{networkSpecificBoundSet} |
   selectRoute{networkSpecificBoundSet} |
   sendChargingInformation{networkSpecificBoundSet} |
   sendFacilityInformation{networkSpecificBoundSet} |
   sendSTUI{networkSpecificBoundSet} |
   serviceFilteringResponse{networkSpecificBoundSet} |
   splitLeg{networkSpecificBoundSet} | statusReport{networkSpecificBoundSet} |
   tAnswer{networkSpecificBoundSet} | tBusy{networkSpecificBoundSet} |
   tDisconnect{networkSpecificBoundSet} |
   termAttemptAuthorized{networkSpecificBoundSet} |
   tMidCall{networkSpecificBoundSet} | tNoAnswer{networkSpecificBoundSet} |
   playAnnouncement{networkSpecificBoundSet} |
   promptAndCollectUserInformation{networkSpecificBoundSet} |
   scriptClose{networkSpecificBoundSet} | scriptEvent{networkSpecificBoundSet}
   | scriptInformation{networkSpecificBoundSet} |
   scriptRun{networkSpecificBoundSet} | specializedResourceReport |
   promptAndReceiveMessage{networkSpecificBoundSet}}

scf-ssfTrafficManagementAbstractSyntax ABSTRACT-SYNTAX ::= {
  TrafficManagementSCF-SSF-PDUs
  IDENTIFIED BY  id-as-scf-ssfTrafficManagementAS
}

TrafficManagementSCF-SSF-PDUs ::=
  TCMessage{{ScfToSsfTrafficManagementInvokable}, {EmptyReturnable}}

ScfToSsfTrafficManagementInvokable OPERATION ::=
  {callGap{networkSpecificBoundSet}}

scf-ssfServiceManagementAbstractSyntax ABSTRACT-SYNTAX ::= {
  ServiceManagementSCF-SSF-PDUs
  IDENTIFIED BY  id-as-scf-ssfServiceManagementAS
}

ServiceManagementSCF-SSF-PDUs ::=
  TCMessage
    {{ScfToSsfServiceManagementInvokable},
    {ScfToSsfServiceManagementReturnable}}

ScfToSsfServiceManagementInvokable OPERATION ::=
  {activateServiceFiltering{networkSpecificBoundSet}}

ScfToSsfServiceManagementReturnable OPERATION ::=
  {activateServiceFiltering{networkSpecificBoundSet}}

ssf-scfServiceManagementAbstractSyntax ABSTRACT-SYNTAX ::= {
  ServiceManagementSSF-SCF-PDUs
  IDENTIFIED BY  id-as-ssf-scfServiceManagementAS
}

ServiceManagementSSF-SCF-PDUs ::=
  TCMessage{{SsfToScfServiceManagementInvokable}, {EmptyReturnable}}

EmptyReturnable OPERATION ::=
  {...}

SsfToScfServiceManagementInvokable OPERATION ::=
  {serviceFilteringResponse{networkSpecificBoundSet}}

scf-ssfStatusReportingAbstractSyntax ABSTRACT-SYNTAX ::= {
  StatusReportingSCF-SSF-PDUs
  IDENTIFIED BY  id-as-scf-ssfStatusReportingAS
}

StatusReportingSCF-SSF-PDUs ::=
  TCMessage
    {{ScfToSsfStatusReportingInvokable}, {ScfToSsfStatusReportingReturnable}}

ScfToSsfStatusReportingInvokable OPERATION ::=
  {cancel{networkSpecificBoundSet} |
   cancelStatusReportRequest{networkSpecificBoundSet} |
   requestCurrentStatusReport{networkSpecificBoundSet} |
   requestEveryStatusChangeReport{networkSpecificBoundSet} |
   requestFirstStatusMatchReport{networkSpecificBoundSet}}

ScfToSsfStatusReportingReturnable OPERATION ::=
  {cancel{networkSpecificBoundSet} |
   cancelStatusReportRequest{networkSpecificBoundSet} |
   requestCurrentStatusReport{networkSpecificBoundSet} |
   requestEveryStatusChangeReport{networkSpecificBoundSet} |
   requestFirstStatusMatchReport{networkSpecificBoundSet} |
   statusReport{networkSpecificBoundSet}}

scf-ssfTriggerManagementAbstractSyntax ABSTRACT-SYNTAX ::= {
  TriggerManagementSCF-SSF-PDUs
  IDENTIFIED BY  id-as-scf-ssfTriggerManagementAS
}

TriggerManagementSCF-SSF-PDUs ::=
  TCMessage
    {{ScfToSsfTriggerManagementInvokable},
    {ScfToSsfTriggerManagementReturnable}}

ScfToSsfTriggerManagementInvokable OPERATION ::=
  {manageTriggerData{networkSpecificBoundSet}}

ScfToSsfTriggerManagementReturnable OPERATION ::=
  {manageTriggerData{networkSpecificBoundSet}}

END

-- Generated by Asnp, the ASN.1 pretty-printer of France Telecom R&D
