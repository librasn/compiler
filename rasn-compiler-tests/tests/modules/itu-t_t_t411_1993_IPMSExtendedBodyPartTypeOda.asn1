-- Module IPMSExtendedBodyPartTypeOda (T.411:03/1993)
-- See also ITU-T T.411 (03/1993)
-- See also the index of all ASN.1 assignments needed in this document

IPMSExtendedBodyPartTypeOda {joint-iso-itu-t(2) oda(8) modules(1) part(0)
  extended-body-part-type-oda(0)} DEFINITIONS IMPLICIT TAGS ::=
BEGIN

-- Prologue
EXPORTS oda-body-part, OdaBodyPartParameters, OdaData;

IMPORTS
  Interchange-Data-Element
    FROM Interchange-Data-Elements {2 8 1 5 5}
  EXTENDED-BODY-PART-TYPE
    FROM IPMSInformationObjects {joint-iso-itu-t(2) mhs-motis(6) ipms(1)
      modules(0) information-objects(2) version-1999(1)};

oda-body-part EXTENDED-BODY-PART-TYPE ::= {
  PARAMETERS  {OdaBodyPartParameters
               IDENTIFIED BY  id-et-oda-param},
  DATA        {OdaData
               IDENTIFIED BY  id-et-oda-data}
}

-- Abstract syntax for ODA body part parameters shall appear in the parameter elements of an IPM
-- ExternallyDefinedBodyPart
OdaBodyPartParameters ::= SET {
  document-application-profile  [0]  OBJECT IDENTIFIER,
  -- This object identifier value shall also be used in the MTS ExternalEncodedInformationType in addition to the
  -- id-et-oda-data object identifier
  document-architecture-class
    [1]  INTEGER {formatted(0), processable(1), formatted-processable(2)}
}

-- Abstract syntax for ODA data shall appear in the data element of an IPM ExternallyDefinedBodyPart
OdaData ::= SEQUENCE OF Interchange-Data-Element

id-et-oda-param OBJECT IDENTIFIER ::= {2 8 1 1 2}

-- identifies the Abstract Syntax for ODA bodypart parameters using the ASN.1 basic encoding rules
id-et-oda-data OBJECT IDENTIFIER ::=
  {2 8 1 1 1}

-- identifies the Abstract Syntax for ODA data using the ASN.1 basic encoding rules
END -- of IPMSExtendedBodyPartTypeOda

-- Generated by Asnp, the ASN.1 pretty-printer of France Telecom R&D
