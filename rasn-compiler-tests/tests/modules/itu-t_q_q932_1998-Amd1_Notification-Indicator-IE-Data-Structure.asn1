-- Module Notification-Indicator-IE-Data-Structure (Q.932:05/1998)
-- See also ITU-T Q.932 (1998) Amend. 1 (06/2000)
-- See also the index of all ASN.1 assignments needed in this document

Notification-Indicator-IE-Data-Structure {itu-t recommendation q 932
  notification-data-structure(6)} DEFINITIONS ::=
BEGIN

EXPORTS NOTIFICATION;

NOTIFICATION ::= CLASS {
  &ArgumentType   OPTIONAL,
  &operationCode  Code UNIQUE OPTIONAL
}WITH SYNTAX {[ARGUMENT &ArgumentType]
              [CODE &operationCode]
}

Code ::= CHOICE {local   INTEGER,
                 global  OBJECT IDENTIFIER
}

NotificationDataStructure ::= SEQUENCE {
  opcode    NOTIFICATION.&operationCode,
  argument  NOTIFICATION.&ArgumentType
}

END -- of Notification-Indicator-IE-Data-Structure

-- Generated by Asnp, the ASN.1 pretty-printer of France Telecom R&D
