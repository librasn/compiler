-- Module STASE-ROSE-Authentication-value (Q.813:06/1998)
-- See also ITU-T Q.813 (06/1998)
-- See also the index of all ASN.1 assignments needed in this document

STASE-ROSE-Authentication-value {itu-t recommendation q(17) q813(813)
  stase(1) abstractSyntax(1) stase-authentication-value(0)} DEFINITIONS
IMPLICIT TAGS ::=
BEGIN

-- EXPORTS everything
IMPORTS
  SenderId, ReceiverId, Signature, SignatureCertificate
    FROM Secure-Remote-Operations-APDUs {itu-t recommendation q(17) q813(813)
      stase(1) stase-pci(0) stase-data(2)};

Authentication-value ::= CHOICE {
  explicit          [0]  ExplicitAuthenticator,
  gssAuthenticator  [1]  GssAuthenticator,
  -- to be used only if the two communicating entities use GSS-API
  ...
}

ExplicitAuthenticator ::= SEQUENCE {
  senderId               [0]  SenderId,
  receiverId             [1]  ReceiverId,
  time                   [3]  GeneralizedTime,
  encryptedSymmetricKey  [4]  INTEGER OPTIONAL,
  -- a symmetric encryption key encrypted with the receiver's public key
  signature              [5]  Signature,
  -- the sender's signature of the preceding fields encoded as ASCII characters
  certificate            [6]  SignatureCertificate OPTIONAL
  -- the sender's public key certificate for the key used for the signature
}

GssAuthenticator ::= SEQUENCE {
  gssMechanism            [0]  OBJECT IDENTIFIER OPTIONAL,
  gssInitialContextToken  [1]  OCTET STRING
}

END

-- Generated by Asnp, the ASN.1 pretty-printer of France Telecom R&D
