-- Module External-References (T.422:08/1995)
-- See also ITU-T T.422 (08/1995)
-- See also the index of all ASN.1 assignments needed in this document

External-References {2 8 1 12 1} DEFINITIONS IMPLICIT TAGS ::=
BEGIN

EXPORTS External-References-List, Reference-Name;

IMPORTS
  Location-Expression
    FROM Location-Expressions {2 8 1 12 0}
  --  see 7.4
  DOR
    FROM DOR-definition {2 4 0}
  --  see ISO/IEC 10031-2
  DistinguishedName
    FROM InformationFramework {joint-iso-itu-t ds(5) module(1)
      informationFramework(1) 3};

--  see ITU-T Rec. X.501 ¦ ISO/IEC 9594-2
External-References-List ::=
  SET OF
    SET {reference-name   [1]  Reference-Name,
         external-entity  [2]  External-Entity,
         location-rule    [3]  Location-Expression OPTIONAL}

Reference-Name ::= PrintableString

External-Entity ::= CHOICE {
  external-info    [0]  External-Information-Name,
  object-id        [1]  OBJECT IDENTIFIER,
  dor              [2]  DOR,
  distinguished    [3]  DistinguishedName,
  associated-info  [4]  Associated-Information-Name
}

External-Information-Name ::= SEQUENCE {
  string     [0]  PrintableString,
  object-id  [1]  OBJECT IDENTIFIER OPTIONAL
}

Associated-Information-Name ::= SEQUENCE {
  string     [0]  PrintableString,
  object-id  [1]  OBJECT IDENTIFIER OPTIONAL
}

END

-- Generated by Asnp, the ASN.1 pretty-printer of France Telecom R&D
