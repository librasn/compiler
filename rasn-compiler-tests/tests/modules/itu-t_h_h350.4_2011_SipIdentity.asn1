-- Module SipIdentity (H.350.4:05/2011)
-- See also ITU-T H.350.4 (05/2011)
-- See also the index of all ASN.1 assignments needed in this document

SipIdentity {itu-t(0) recommendation(0) h(8) 350 1 cr(1) sipIdentity(6)
  module(4)} DEFINITIONS ::=
BEGIN

-- SIPIdentity Object Schema
-- Schema for representing SIPIdentity Object in an LDAP Directory
-- Abstract
-- This document defines the schema for representing SIPIdentity
-- object in an LDAP directory [LDAPv3].  It defines schema elements
-- to represent an SIPIdentity object [SIPIdentity].
--                     .1 = Communication related work
--                     .1.6 = SIPIdentity
--                     .1.6.1 = attributes
--                     .1.6.2 = objectclass
--                     .1.6.3 = syntax
IMPORTS
  -- from Rec. ITU-T H.350
  h350-cr, caseIgnoreIA5Match, caseIgnoreIA5SubstringsMatch,
    userSMIMECertificate
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseExactMatch, caseExactSubstringsMatch,
    caseIgnoreMatch, caseIgnoreSubstringsMatch, octetStringMatch
    FROM SelectedAttributeTypes {joint-iso-itu-t ds(5) module(1)
      selectedAttributeTypes(5) 6};

-- Attribute Type Definitions
--    The following attribute types are defined in this document:
--     SIPIdentitySIPURI
--     SIPIdentityRegistrarAddress
--     SIPIdentityProxyAddress
--     SIPIdentityAddress
--     SIPIdentityPassword
--     SIPIdentityUserName
--     SIPIdentityServiceLevel
sIPIdentitySIPURI ATTRIBUTE ::= {
  WITH SYNTAX               UnboundedDirectoryString
  EQUALITY MATCHING RULE    caseExactMatch
  SUBSTRINGS MATCHING RULE  caseExactSubstringsMatch
  ID                        {at  1}
}

sIPIdentityRegistrarAddress ATTRIBUTE ::= {
  WITH SYNTAX             IA5String
  EQUALITY MATCHING RULE  caseIgnoreIA5Match
  ID                      {at  2}
}

sIPIdentityProxyAddress ATTRIBUTE ::= {
  WITH SYNTAX             IA5String
  EQUALITY MATCHING RULE  caseIgnoreIA5Match
  ID                      {at  3}
}

sIPIdentityAddress ATTRIBUTE ::= {
  WITH SYNTAX             IA5String
  EQUALITY MATCHING RULE  caseIgnoreIA5Match
  ID                      {at  4}
}

sIPIdentityPassword ATTRIBUTE ::= {
  WITH SYNTAX             OCTET STRING
  EQUALITY MATCHING RULE  octetStringMatch
  ID                      {at  5}
}

sIPIdentityUserName ATTRIBUTE ::= {
  WITH SYNTAX               UnboundedDirectoryString
  EQUALITY MATCHING RULE    caseIgnoreMatch
  SUBSTRINGS MATCHING RULE  caseIgnoreSubstringsMatch
  ID                        {at  6}
}

sIPIdentityServiceLevel ATTRIBUTE ::= {
  WITH SYNTAX               IA5String
  EQUALITY MATCHING RULE    caseIgnoreIA5Match
  SUBSTRINGS MATCHING RULE  caseIgnoreIA5SubstringsMatch
  ID                        {at  7}
}

-- Object Class Definitions
--    The following object class is defined in this document:
--        SIPIdentity
-- SIPIdentity
sIPIdentity OBJECT-CLASS ::= {
  SUBCLASS OF  {top}
  MAY CONTAIN
    {sIPIdentitySIPURI | sIPIdentityRegistrarAddress | sIPIdentityProxyAddress
      | sIPIdentityAddress | sIPIdentityPassword | sIPIdentityUserName |
      sIPIdentityServiceLevel | userSMIMECertificate}
  ID           {oc  1}
}

sip-Id OBJECT IDENTIFIER ::= {h350-cr sip-Id(6)}

at OBJECT IDENTIFIER ::= {sip-Id at(1)}

oc OBJECT IDENTIFIER ::= {sip-Id oc(2)}

END -- end of ASN.1

-- Generated by Asnp, the ASN.1 pretty-printer of France Telecom R&D
