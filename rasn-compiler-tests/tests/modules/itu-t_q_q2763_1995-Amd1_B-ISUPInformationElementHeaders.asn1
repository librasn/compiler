-- Module B-ISUPInformationElementHeaders (Q.2763:12/1999)
-- See also ITU-T Q.2763 (1999) Amend. 1 (12/2002)
-- See also the index of all ASN.1 assignments needed in this document

B-ISUPInformationElementHeaders DEFINITIONS IMPLICIT TAGS ::=
BEGIN

MessageInstructionIndicators ::= SEQUENCE {
  sharedCompatibilityInformation   SharedCompatibilityInformation,
  passOnNotPossibleMessageInd      PassOnNotPossibleMessageInd,
  broadbandNarrowbandMessageIWInd  BroadbandNarrowbandMessageIWInd
}

ParameterInstructionIndicators ::= SEQUENCE {
  sharedCompatibilityInformation     SharedCompatibilityInformation,
  discardParameterIndicator          DiscardParameterIndicator,
  passOnNotPossibleParameterInd      PassOnNotPossibleParameterInd,
  broadbandNarrowbandParameterIWInd  BroadbandNarrowbandParameterIWInd
}

SharedCompatibilityInformation ::= SEQUENCE {
  transitAtIntermediateExchangeInd  TransitAtIntermediateExchangeInd,
  releaseCallIndicator              ReleaseCallIndicator,
  sendNotificationIndicator         SendNotificationIndicator,
  discardMessageIndicator           DiscardMessageIndicator
}

TransitAtIntermediateExchangeInd ::= ENUMERATED {
  transitInterpretation(0), endNodeInterpretation(1)}

ReleaseCallIndicator ::= ENUMERATED {doNotReleaseCall(0), releaseCall(1)}

SendNotificationIndicator ::= ENUMERATED {
  doNotSendNotification(0), sendNotification(1)}

DiscardMessageIndicator ::= ENUMERATED {
  doNotDiscardMessage(0), discardMessage(1)}

PassOnNotPossibleMessageInd ::= ENUMERATED {releaseCall(0), discardMessage(1)}

BroadbandNarrowbandMessageIWInd ::= ENUMERATED {
  passOn(0), discardMessage(1), releaseCall(2)
                                --  value 3 is reserved
                                }

DiscardParameterIndicator ::= ENUMERATED {
  doNotDiscardParameter(0), discardParameter(1)}

PassOnNotPossibleParameterInd ::= ENUMERATED {
  releaseCall(0), discardMessage(1), discardParameter(2)
                                     --  value 3 is reserved
                                     }

BroadbandNarrowbandParameterIWInd ::= ENUMERATED {
  passOn(0), discardMessage(1), releaseCall(2), discardParameter(3)}

END

-- Generated by Asnp, the ASN.1 pretty-printer of France Telecom R&D
