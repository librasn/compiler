-- Module GenericIdentity (H.350.5:05/2011)
-- See also ITU-T H.350.5 (05/2011)
-- See also the index of all ASN.1 assignments needed in this document

GenericIdentity {itu-t(0) recommendation(0) h(8) 350 1 cr(1) genericIdentity(7)
  module(4)} DEFINITIONS ::=
BEGIN

-- genericIdentity Object Schema
-- Schema for representing a genericIdentity Protocol Object in an LDAP Directory
-- Abstract
-- This document defines the schema for representing genericIdentity
-- object in an LDAP directory [LDAPv3].  It defines schema elements
-- to represent an genericIdentity object [genericIdentity].
--                     .1 = Communication related work
--                     .1.7 = genericIdentity
--                     .1.7.1 = attributes
--                     .1.7.2 = objectclass
--                     .1.7.3 = syntax
IMPORTS
  -- from Rec. ITU-T H.350
  h350-cr
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseIgnoreMatch, caseIgnoreSubstringsMatch
    FROM SelectedAttributeTypes {joint-iso-itu-t ds(5) module(1)
      selectedAttributeTypes(5) 6};

-- Attribute Type Definitions
genericIdentityProtocolIdentifier ATTRIBUTE ::= {
  WITH SYNTAX               UnboundedDirectoryString
  EQUALITY MATCHING RULE    caseIgnoreMatch
  SUBSTRINGS MATCHING RULE  caseIgnoreSubstringsMatch
  ID                        {at  1}
}

genericIdentityMessage ATTRIBUTE ::= {
  WITH SYNTAX               UnboundedDirectoryString
  EQUALITY MATCHING RULE    caseIgnoreMatch
  SUBSTRINGS MATCHING RULE  caseIgnoreSubstringsMatch
  ID                        {at  2}
}

-- Object Class Definitions
--    The following object class is defined in this document:
--        genericIdentity
-- genericIdentity
genericIdentity OBJECT-CLASS ::= {
  SUBCLASS OF  {top}
  MAY CONTAIN  {genericIdentityProtocolIdentifier | genericIdentityMessage}
  ID           {oc  1}
}

gi OBJECT IDENTIFIER ::= {h350-cr gi(7)}

at OBJECT IDENTIFIER ::= {gi at(1)}

oc OBJECT IDENTIFIER ::= {gi oc(2)}

-- end of ASN.1
END

-- Generated by Asnp, the ASN.1 pretty-printer of France Telecom R&D
