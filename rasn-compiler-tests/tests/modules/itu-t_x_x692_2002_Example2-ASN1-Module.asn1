-- Module Example2-ASN1-Module (X.692:07/2002)
-- See also ITU-T X.692 (03/2002)
-- See also the index of all ASN.1 assignments needed in this document

Example2-ASN1-Module {joint-iso-itu-t(2) asn1(1) ecn(4) examples(5)
  asn1-module2(5)} DEFINITIONS AUTOMATIC TAGS ::=
BEGIN

ExampleMessages ::= CHOICE {
  firstExample   NormallySmallValues,
  secondExample  SparseEvenlyDistributedValueSet
  -- etc.
}

NormallySmallValues ::= INTEGER(0..1024)

SparseEvenlyDistributedValueSet ::= INTEGER(2 | 4 | 6 | 8 | 10 | 12 | 14 | 16)

-- etc.
END

-- Generated by Asnp, the ASN.1 pretty-printer of France Telecom R&D
