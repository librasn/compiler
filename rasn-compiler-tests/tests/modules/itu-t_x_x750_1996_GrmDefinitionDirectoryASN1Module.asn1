-- Module GrmDefinitionDirectoryASN1Module (X.750:10/1996)
-- See also ITU-T X.750 (1996) Technical Cor. 1 (02/2000)
-- See also the index of all ASN.1 assignments needed in this document

GrmDefinitionDirectoryASN1Module {joint-iso-itu-t(2) ms(9) function(2)
  part16(16) asn1Modules(2) 7} DEFINITIONS IMPLICIT TAGS ::=
BEGIN

-- EXPORTS everything;
IMPORTS
  ATTRIBUTE, OBJECT-CLASS, CONTENT-RULE
    FROM InformationFramework {joint-iso-itu-t(2) ds(5) modules(1)
      informationFramework(1) 3}
  -- ITU-T Rec. X.501 | ISO/IEC 9594-2
  TemplateLabel
    FROM DefinitionASN1Module {joint-iso-itu-t(2) ms(9) function(2) part16(16)
      asn1Modules(2) 1}
  -- this Recommendation | International Standard
  behaviour, derivedFrom, managementTemplate, registeredAs,
    registeredInformation
    FROM DefinitionDirectoryASN1Module {joint-iso-itu-t(2) ms(9) function(2)
      part16(16) asn1Modules(2) 4}
  -- this Recommendation | International Standard
  MappedRelationshipClass, MappingPair, RelationshipObject,
    RoleMappingSpecification, RoleSpecifier, SupportedChoice
    FROM GrmAttributeDefinitionModule {joint-iso-itu-t(2) ms(9) function(2)
      part16(16) asn1Modules(2) 6}
  -- this Recommendation | International Standard
  mkmDirectoryObjectClass, mkmDirectoryAttributeType
    FROM MKMD {joint-iso-itu-t(2) ms(9) function(2) part16(16) asn1Modules(2)
      5}-- this Recommendation | International Standard
  ;

managementRelationshipClass OBJECT-CLASS ::= {
  SUBCLASS OF   {managementTemplate}
  KIND          auxiliary
  MUST CONTAIN  {derivedFrom | behaviour}
  MAY CONTAIN   {supports | qualifiedBy | roleSpecifier}
  ID            {mkmDirectoryObjectClass  16}
}

managementRelationshipMapping OBJECT-CLASS ::= {
  SUBCLASS OF   {managementTemplate}
  KIND          auxiliary
  MUST CONTAIN
    {mappedRelationshipClass | behaviour | roleMappingSpecificationSet |
      registeredAs}
  MAY CONTAIN   {relationshipObject | operationsMapping}
  ID            {mkmDirectoryObjectClass  17}
}

-- Definition of DIT content rules
-- Only one of the specified auxiliary object classes can be
-- included in a given entry of class registeredInformation
registeredManagementRelationshipInformationCR CONTENT-RULE ::= {
  STRUCTURAL OBJECT-CLASS   registeredInformation.&id
  AUXILIARY OBJECT-CLASSES
    {managementRelationshipClass | managementRelationshipMapping}
}

-- Definition of used attributes
mappedRelationshipClass ATTRIBUTE ::= {
  WITH SYNTAX   MappedRelationshipClass
  SINGLE VALUE  TRUE
  ID            {mkmDirectoryAttributeType  47}
}

operationsMapping ATTRIBUTE ::= {
  WITH SYNTAX  MappingPair
  ID           {mkmDirectoryAttributeType  48}
}

qualifiedBy ATTRIBUTE ::= {
  WITH SYNTAX  TemplateLabel
  ID           {mkmDirectoryAttributeType  49}
}

relationshipObject ATTRIBUTE ::= {
  WITH SYNTAX   RelationshipObject
  SINGLE VALUE  TRUE
  ID            {mkmDirectoryAttributeType  50}
}

roleMappingSpecificationSet ATTRIBUTE ::= {
  WITH SYNTAX  RoleMappingSpecification
  ID           {mkmDirectoryAttributeType  51}
}

roleSpecifier ATTRIBUTE ::= {
  WITH SYNTAX   RoleSpecifier
  SINGLE VALUE  TRUE
  ID            {mkmDirectoryAttributeType  52}
}

supports ATTRIBUTE ::= {
  WITH SYNTAX  SupportedChoice
  ID           {mkmDirectoryAttributeType  53}
}

END

-- Generated by Asnp, the ASN.1 pretty-printer of France Telecom R&D
