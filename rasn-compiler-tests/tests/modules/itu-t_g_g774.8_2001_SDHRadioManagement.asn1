-- Module SDHRadioManagement (G.774.8:02/2001)
-- See also ITU-T G.774.8 (02/2001)
-- See also the index of all ASN.1 assignments needed in this document

SDHRadioManagement {itu-t(0) recommendation(0) g(7) g774(774) hyphen(127)
  sdhRadioIM(8)} DEFINITIONS IMPLICIT TAGS ::=
BEGIN

-- EXPORTS Everything
sdhRadioManagement OBJECT IDENTIFIER ::=
  {itu-t(0) recommendation(0) g(7) g774(774) hyphen(127) sdhRadioIM(8)
   informationModel(0)}

g774-8ObjectClass OBJECT IDENTIFIER ::=
  {sdhRadioManagement managedObjectClass(3)}

g774-8Attribute OBJECT IDENTIFIER ::= {sdhRadioManagement attribute(7)}

g774-8NameBinding OBJECT IDENTIFIER ::= {sdhRadioManagement nameBinding(6)}

g774-8Action OBJECT IDENTIFIER ::= {sdhRadioManagement action(9)}

g774-8Notification OBJECT IDENTIFIER ::= {sdhRadioManagement notification(10)}

g774-8Package OBJECT IDENTIFIER ::= {sdhRadioManagement package(4)}

g774-8Parameter OBJECT IDENTIFIER ::= {sdhRadioManagement parameter(5)}

END

-- Generated by Asnp, the ASN.1 pretty-printer of France Telecom R&D
