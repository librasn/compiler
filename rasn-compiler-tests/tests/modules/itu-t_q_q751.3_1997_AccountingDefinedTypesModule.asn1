-- Module AccountingDefinedTypesModule (Q.751.3:09/1997)
-- See also ITU-T Q.751.3 (09/1997)
-- See also the index of all ASN.1 assignments needed in this document

AccountingDefinedTypesModule {itu-t(0) recommendation(0) q(17) omap(751)
  accounting(3) informationModel(0) asn1Modules(2)
  accountingDefinedTypesModule(0)} DEFINITIONS IMPLICIT TAGS ::=
BEGIN

IMPORTS
  ObjectInstance, ControlStatus
    FROM Attribute-ASN1Module {joint-iso-itu-t ms(9) smi(3) part2(2)
      asn1Module(2) 1}
  PointerOrNull
    FROM ASN1DefinedTypesModule {itu-t recommendation m gnm(3100)
      informationModel(0) asn1Modules(2) asn1DefinedTypesModule(0)}
  AdditionalName
    FROM MTPDefinedTypesModule {itu-t(0) recommendation q(17) omap(751)
      mtp(1) informationModel(0) asn1Modules(2) mtpDefinedTypesModule(0)};

-- ASN.1 type definitions
DataProblem ::= ENUMERATED {
  noProblem(0), intervalNotComplete(1), configurationChanged(2), notReliable(3)
}

EndOfMeasurementTime ::= GeneralizedTime

MeasurementControlStatus ::= SET OF INTEGER {suspended(3)}

maxNumberReferencesInSelectionGroupSet INTEGER ::=
  8 -- h this number is only for compilability

SelectionGroup ::= SEQUENCE {
  selectionItem          [0]  ObjectInstance,
  optionalSelectionItem  [1]  ObjectInstance OPTIONAL
}

SelectionGroupSet ::=
  SET SIZE (0..maxNumberReferencesInSelectionGroupSet) OF SelectionGroup

-- ASN.1 OBJECT IDENTIFIER definitions
ss7AccountingInformationModel OBJECT IDENTIFIER ::=
  {itu-t recommendation(0) q(17) omap(751) accounting(3)}

accountingAction OBJECT IDENTIFIER ::=
  {ss7AccountingInformationModel action(9)}

accountingAttribute OBJECT IDENTIFIER ::=
  {ss7AccountingInformationModel attribute(7)}

accountingAttributeGroup OBJECT IDENTIFIER ::=
  {ss7AccountingInformationModel attributeGroup(8)}

accountingNameBinding OBJECT IDENTIFIER ::=
  {ss7AccountingInformationModel nameBinding(6)}

accountingNotification OBJECT IDENTIFIER ::=
  {ss7AccountingInformationModel notification(10)}

accountingObjectClass OBJECT IDENTIFIER ::=
  {ss7AccountingInformationModel managedObjectClass(3)}

accountingPackage OBJECT IDENTIFIER ::=
  {ss7AccountingInformationModel package(4)}

accountingParameter OBJECT IDENTIFIER ::=
  {ss7AccountingInformationModel parameter(5)}

accountingOrVerification-AOi OBJECT IDENTIFIER ::=
  {accountingAttribute accountingOrVerification(0)}

endOfMeasurementTime-AOi OBJECT IDENTIFIER ::=
  {accountingAttribute endOfMeasurementTime(7)}

controlPointer-AOi OBJECT IDENTIFIER ::=
  {accountingAttribute controlPointer(1)}

controlPointerPackage-POi OBJECT IDENTIFIER ::=
  {accountingPackage controlPointerPackage(1)}

measurementControlStatus-AOi OBJECT IDENTIFIER ::=
  {accountingAttribute measurementControlStatus(6)}

measurementControlStatusPackage-POi OBJECT IDENTIFIER ::=
  {accountingPackage measurementControlStatusPackage(2)}

operatorName-AOi OBJECT IDENTIFIER ::= {accountingAttribute operatorName(3)}

selectionGroupSetForAccounting-AOi OBJECT IDENTIFIER ::=
  {accountingAttribute selectionGroupSetForAccounting(4)}

selectionGroupSetForVerification-AOi OBJECT IDENTIFIER ::=
  {accountingAttribute selectionGroupSetForVerification(5)}

ss7AccountingAndVerificationControlPackage-POi OBJECT IDENTIFIER ::=
  {accountingPackage ss7AccountingAndVerificationControlPackage(3)}

ss7AccountingAndVerificationControl-OOi OBJECT IDENTIFIER ::=
  {accountingObjectClass ss7AccountingAndVerificationControl(0)}

ss7AccountingAndVerificationControl-managedElement-NBOI OBJECT IDENTIFIER ::=
  {accountingNameBinding ss7AccountingAndVerificationControl-managedElement(0)}

ss7AccountingAndVerificationControl-managedSwitchingElement-NBOI
  OBJECT IDENTIFIER ::=
  {accountingNameBinding
   ss7AccountingAndVerificationControl-managedSwitchingElement(1)}

ss7AccountingLogRecord-OOi OBJECT IDENTIFIER ::=
  {accountingObjectClass ss7AccountingLogRecord(1)}

ss7AccountingLogRecordPackage-POi OBJECT IDENTIFIER ::=
  {accountingPackage ss7AccountingLogRecordPackage(1)}

ss7Accounting-NOI OBJECT IDENTIFIER ::=
  {accountingNotification ss7Accounting(0)}

-- ASN.1 OBJECT IDENTIFIER definitions for specific errors
objectStillReferencedError-OID OBJECT IDENTIFIER ::=
  {accountingParameter objectStillReferencedError(1)}

END

-- Generated by Asnp, the ASN.1 pretty-printer of France Telecom R&D
