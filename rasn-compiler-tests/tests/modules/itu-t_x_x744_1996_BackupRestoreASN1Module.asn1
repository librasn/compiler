-- Module BackupRestoreASN1Module (X.744:10/1996)
-- See also ITU-T X.744 (10/1996)
-- See also the index of all ASN.1 assignments needed in this document

BackupRestoreASN1Module {joint-iso-itu-t ms(9) function(2) part18(18)
  asn1Module(2) 1} DEFINITIONS IMPLICIT TAGS ::=
BEGIN

-- EXPORTS everything
IMPORTS
  ObjectInstance
    FROM CMIP-1 {joint-iso-itu-t ms(9) cmip(1) modules(0) protocol(3)}
  ManagementExtension
    FROM Attribute-ASN1Module {joint-iso-itu-t ms(9) smi(3) part2(2)
      asn1Module(2) 1};

--supporting productions
BackupArgument ::= SEQUENCE {
  backupDestination  [0]  BackupDestination,
  additionalInfo     [1]  SET OF ManagementExtension OPTIONAL
}

BackupDestination ::= CHOICE {
  localObject  ObjectInstance,
  inLine       NULL, -- in-line in the notification in additionalInfo
  offLine      GraphicString -- remote system by, e.g. FTAM
}

BackupReply ::= SEQUENCE {
  reply
    [0]  CHOICE {success  NULL, -- for local or off-line backup --
                 inLine   BIT STRING},
  additionalInfo  [1]  SET OF ManagementExtension OPTIONAL
}

RestoreArgument ::= SEQUENCE {
  restoreSource   [0]  RestoreSource,
  additionalInfo  [1]  SET OF ManagementExtension OPTIONAL
}

RestoreSource ::= CHOICE {
  localObject  ObjectInstance,
  inLine       BIT STRING,
  offLine      GraphicString -- remote system via some other transfer protocol, e.g. FTAM
}

END -- of BackupRestoreASN1Module supporting productions

-- Generated by Asnp, the ASN.1 pretty-printer of France Telecom R&D
