-- Module RepertoireDirectoryASN1Module (X.750:10/1996)
-- See also ITU-T X.750 (1996) Technical Cor. 1 (02/2000)
-- See also the index of all ASN.1 assignments needed in this document

RepertoireDirectoryASN1Module {joint-iso-itu-t(2) ms(9) function(2) part16(16)
  asn1Modules(2) 3} DEFINITIONS IMPLICIT TAGS ::=
BEGIN

-- EXPORTS everything;
IMPORTS
  ATTRIBUTE, OBJECT-CLASS, CONTENT-RULE
    FROM InformationFramework {joint-iso-itu-t(2) ds(5) modules(1)
      informationFramework(1) 3}
  -- ITU-T Rec. X.501 | ISO/IEC 9594-2
  applicationEntity
    FROM SelectedObjectClasses {joint-iso-itu-t(2) ds(5) modules(1)
      selectedObjectClasses(6) 3}
  -- ITU-T Rec. X.521 | ISO/IEC 9594-7
  bitStringMatch, booleanMatch
    FROM SelectedAttributeTypes {joint-iso-itu-t(2) ds(5) modules(1)
      selectedAttributeTypes(5) 3}
  -- ITU-T Rec. X.520 | ISO/IEC 9594-6
  ObjectInstance
    FROM CMIP-1 {joint-iso-itu-t(2) ms(9) cmip(1) modules(0) protocol(3)}
  -- itu-t Rec. X.711 and ISO/IEC 9596-1
  FunctionalUnits, ProtocolVersion
    FROM CMIP-A-ASSOCIATE-Information {joint-iso-itu-t(2) ms(9) cmip(1)
      modules(0) aAssociateUserInfo(1)} -- itu-t Rec. X.711 and ISO/IEC 9596-1
  FunctionalUnitPackage
    FROM SMASE-A-ASSOCIATE-Information {joint-iso-itu-t ms(9) smo(0)
      asn1Modules(2) negotiationDefinitions(0) version1(1)
      } -- itu-t Rec. X.701 | ISO/IEC 10040
  mkmDirectoryObjectClass, mkmDirectoryAttributeType
    FROM MKMD {joint-iso-itu-t(2) ms(9) function(2) part16(16) asn1Modules(2)
      5}
  -- this Recommendation | International Standard
  GdmoObjectClass
    FROM RepertoireASN1Module {joint-iso-itu-t(2) ms(9) function(2) part16(16)
      asn1Modules(2) 0}; -- this Recommendation | International Standard

cMISE OBJECT-CLASS ::= {
  KIND          auxiliary
  MUST CONTAIN
    {supportedCmipVersion | supportedCmipProfiles |
      supportedCmisFunctionalUnits}
  ID            {mkmDirectoryObjectClass  1}
}

sMASE OBJECT-CLASS ::= {
  KIND          auxiliary
  MUST CONTAIN  {supportedSmaseFunctionalUnits}
  MAY CONTAIN   {mitMoList | supportsMKMglobalNames}
  ID            {mkmDirectoryObjectClass  2}
}

-- The "cMISE" and "sMASE" Directory auxiliary object
-- classes should be used together with the Directory
-- structural object class "applicationEntity".
InstanceIdList ::= SET OF ObjectInstance

managementServiceElementsCR CONTENT-RULE ::= {
  STRUCTURAL OBJECT-CLASS   applicationEntity.&id
  AUXILIARY OBJECT-CLASSES  {sMASE | cMISE}
}

mitMoList ATTRIBUTE ::= {
  WITH SYNTAX  MitMo
  ID           {mkmDirectoryAttributeType  1}
}

MitMo ::= SEQUENCE {
  objectClass  GdmoObjectClass,
  instances    InstanceIdList OPTIONAL
}

supportedCmipProfiles ATTRIBUTE ::= {
  WITH SYNTAX             BIT STRING
  EQUALITY MATCHING RULE  bitStringMatch
  SINGLE VALUE            TRUE
  ID                      {mkmDirectoryAttributeType  43}
}

supportedCmipVersion ATTRIBUTE ::= {
  WITH SYNTAX             ProtocolVersion
  EQUALITY MATCHING RULE  bitStringMatch
  SINGLE VALUE            TRUE
  ID                      {mkmDirectoryAttributeType  2}
}

supportedCmisFunctionalUnits ATTRIBUTE ::= {
  WITH SYNTAX             FunctionalUnits
  EQUALITY MATCHING RULE  bitStringMatch
  SINGLE VALUE            TRUE
  ID                      {mkmDirectoryAttributeType  3}
}

supportedSmaseFunctionalUnits ATTRIBUTE ::= {
  WITH SYNTAX  FunctionalUnitPackage
  ID           {mkmDirectoryAttributeType  5}
}

supportsMKMglobalNames ATTRIBUTE ::= {
  WITH SYNTAX             BOOLEAN
  EQUALITY MATCHING RULE  booleanMatch
  SINGLE VALUE            TRUE
  ID                      {mkmDirectoryAttributeType  44}
}

END

-- Generated by Asnp, the ASN.1 pretty-printer of France Telecom R&D
