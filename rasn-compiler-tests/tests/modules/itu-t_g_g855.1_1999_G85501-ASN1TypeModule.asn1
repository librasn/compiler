-- Module G85501-ASN1TypeModule (G.855.1:03/1999)
-- See also ITU-T G.855.1 (03/1999)
-- See also the index of all ASN.1 assignments needed in this document

G85501-ASN1TypeModule {itu-t recommendation g gntm(85501) informationModel(0)
  asn1Modules(2) asn1TypeModule(0)} DEFINITIONS IMPLICIT TAGS ::=
BEGIN

-- EXPORTS everything
IMPORTS
  AdditionalInformation, AdministrativeState, AvailabilityStatus,
    OperationalState, PerceivedSeverity, ProbableCause
    FROM Attribute-ASN1Module {joint-iso-itu-t ms(9) smi(3) part2(2)
      asn1Module(2) 1}
  Directionality, Failed, ObjectList, ProblemCause, UserLabel
    FROM ASN1DefinedTypesModule {itu-t recommendation m(13) gnm(3100)
      informationModel(0) asn1Modules(2) asn1DefinedTypesModule(0)}
  Capacity, Capacities, Count, CTPList, LinkConnectionList, LinkEnd,
    None, UserIdentifier, LinkDirectionality, ConnectivityEndPoint, TPList,
    SignalId
    FROM M3100ASN1TypeModule2 {itu-t recommendation m gnm(3100)
      informationModel(0) asn1Modules(2) asn1Module2(1)}
  -- Note: DistinguishedName, ObjectInstance formerly imported from X.501
  -- InformationFramework, are imported from X.711 CMIP.
  DistinguishedName, ObjectInstance
    FROM CMIP-1 {joint-iso-itu-t ms(9) cmip(1) modules(0) protocol(3)};

g85501ClassLibrary OBJECT IDENTIFIER ::=
  {itu-t recommendation g gntm(85501) informationModel(0)}

g85501MObjectClass OBJECT IDENTIFIER ::=
  {g85501ClassLibrary managedObjectClass(3)}

g85501Attribute OBJECT IDENTIFIER ::= {g85501ClassLibrary attribute(7)}

g85501NameBinding OBJECT IDENTIFIER ::= {g85501ClassLibrary nameBinding(6)}

g85501Package OBJECT IDENTIFIER ::= {g85501ClassLibrary package(4)}

g85501Action OBJECT IDENTIFIER ::= {g85501ClassLibrary action(9)}

g85501Notification OBJECT IDENTIFIER ::= {g85501ClassLibrary notification(10)}

g85501SpecificError OBJECT IDENTIFIER ::=
  {g85501ClassLibrary specificError(12)}

AssociateNetworkTTPWithTopologicalLinkEndInformation ::= SEQUENCE {
  linkEnd     ObjectInstance,
  networkTTP  ObjectInstance,
  ...
}

AssociateNetworkTTPWithTopologicalLinkEndResult ::= SEQUENCE {
  potentialCapacity  Capacity,
  networkCTPs        CTPList,
  ...
}

AssociateTrailWithTopologicalLinkInformation ::= SEQUENCE {
  link   ObjectInstance,
  trail  ObjectInstance,
  ...
}

AssociateTrailWithTopologicalLinkResult ::= SEQUENCE {
  potentialCapacity         Capacity,
  resultingLinkConnections  LinkConnectionList,
  ...
}

DisassociateNWTTPFromTopLinkEndInformation ::= SEQUENCE {
  linkEnd     [1]  ObjectInstance,
  networkTTP  [2]  ObjectInstance OPTIONAL,
  ...
}

DisassociateTrailFromTopLinkInformation ::= SEQUENCE {
  link   [1]  ObjectInstance,
  trail  [2]  ObjectInstance OPTIONAL,
  ...
}

EstablishLogicalLinkAndEndsResult ::= SEQUENCE {
  link  ObjectInstance,
  aEnd  ObjectInstance,
  zEnd  ObjectInstance,
  ...
}

EstablishLogicalLinkInformation ::= SEQUENCE {
  layerNetworkDomain      ObjectInstance,
  aEnd                    LinkEnd,
  zEnd                    LinkEnd,
  suppliedUserIdentifier  [1]  UserIdentifier OPTIONAL,
  suppliedUserLabel       [2]  GraphicString OPTIONAL,
  suppliedDirection       [3]  LinkDirectionality OPTIONAL,
  ...
}

EstablishLogicalLinkResult ::= SEQUENCE {link  ObjectInstance,
                                         ...
}

EstablishTopologicalLinkAndEndsResult ::= SEQUENCE {
  link  ObjectInstance,
  aEnd  ObjectInstance,
  zEnd  ObjectInstance,
  ...
}

EstablishTopologicalLinkInformation ::= SEQUENCE {
  layerNetworkDomain      ObjectInstance,
  aEnd                    LinkEnd,
  zEnd                    LinkEnd,
  suppliedUserIdentifier  [1]  UserIdentifier OPTIONAL,
  suppliedUserLabel       [2]  GraphicString OPTIONAL,
  suppliedDirection       [3]  Directionality OPTIONAL,
  ...
}

EstablishTopologicalLinkResult ::= SEQUENCE {link  ObjectInstance,
                                             ...
}

Implicit ::= BOOLEAN(TRUE)

QofConnectivityService ::= ObjectInstance

ReleaseSncInformation ::= SEQUENCE {
  snc     ObjectInstance,
  userId  UserIdentifier OPTIONAL,
  ...
}

ReleaseTrailInformation ::= SEQUENCE {
  trailId  ObjectInstance,
  userId   UserIdentifier OPTIONAL,
  ...
}

RemoveLogicalLinkInformation ::= SEQUENCE {link  ObjectInstance,
                                           ...
}

RemoveTopologicalLinkInformation ::= SEQUENCE {link  ObjectInstance,
                                               ...
}

RemoveTopLinkAndEndsInformation ::= SEQUENCE {link  ObjectInstance,
                                              ...
}

SetupSncInformation ::= SEQUENCE {
  aEnd                    SET OF ConnectivityEndPoint,
  zEnd                    SET OF ConnectivityEndPoint,
  directionality          Directionality,
  signalid                [1]  SignalId OPTIONAL,
  qofConnectivityService  [2]  QofConnectivityService OPTIONAL,
  implicitTPCreation      [8]  Implicit OPTIONAL,
  ...
}

SetupSncResult ::= SEQUENCE {
  connection  ObjectInstance,
  aEnd        ObjectInstance,
  zEnd        ObjectInstance,
  userId      UserIdentifier OPTIONAL,
  ...
}

SetupTrailInformation ::= SEQUENCE {
  aEnd                    SET OF ConnectivityEndPoint,
  zEnd                    SET OF ConnectivityEndPoint,
  directionality          Directionality,
  additionalInformation   [2]  AdditionalInformation OPTIONAL,
  qofConnectivityService  [3]  QofConnectivityService OPTIONAL,
  userId                  [0]  UserIdentifier OPTIONAL,
  userLabel               [1]  UserLabel OPTIONAL,
  ...
}

SetupTrailResult ::= SEQUENCE {
  trailId  ObjectInstance,
  aEnds    SET OF ObjectInstance,
  zEnds    SET OF ObjectInstance,
  ...
}

END

-- Generated by Asnp, the ASN.1 pretty-printer of France Telecom R&D
