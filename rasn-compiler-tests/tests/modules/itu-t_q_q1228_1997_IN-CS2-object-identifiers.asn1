-- Module IN-CS2-object-identifiers (Q.1228:09/1997)
-- See also ITU-T Q.1228 (09/1997)
-- See also the index of all ASN.1 assignments needed in this document

IN-CS2-object-identifiers {itu-t recommendation q 1228 modules(0)
  in-cs2-object-identifiers(17) version1(0)} DEFINITIONS ::=
BEGIN

-- This module assigns object identifiers for Modules, Packages, Contracts and Application Context
-- for IN CS-2
-- For Modules from TCAP, ROS
tc-Messages OBJECT IDENTIFIER ::=
  {itu-t recommendation q 773 modules(2) messages(1) version2(2)}

tc-NotationExtensions OBJECT IDENTIFIER ::=
  {itu-t recommendation q 775 modules(2) notation-extension(4) version1(1)}

ros-InformationObjects OBJECT IDENTIFIER ::=
  {joint-iso-itu-t remote-operations(4) informationObjects(5) version1(0)}

ros-genericPDUs OBJECT IDENTIFIER ::=
  {joint-iso-itu-t remote-operations(4) generic-ROS-PDUs(6) version1(0)}

ros-UsefulDefinitions OBJECT IDENTIFIER ::=
  {joint-iso-itu-t remote-operations(4) useful-definitions(7) version1(0)}

sese-APDUs OBJECT IDENTIFIER ::=
  {joint-iso-itu-t genericULS(20) modules(1) seseAPDUs(6)}

guls-Notation OBJECT IDENTIFIER ::=
  {joint-iso-itu-t genericULS(20) modules(1) notation(1)}

guls-SecurityTransformations OBJECT IDENTIFIER ::=
  {joint-iso-itu-t genericULS(20) modules(1) gulsSecurityTransformations(3)}

ds-UsefulDefinitions OBJECT IDENTIFIER ::=
  {joint-iso-itu-t ds(5) module(1) usefulDefinitions(0) 3}

spkmGssTokens OBJECT IDENTIFIER ::=
  {iso(1) identified-organization(3) dod(6) internet(1) security(5)
   mechanisms(5) spkm(1) spkmGssTokens(10)}

-- For IN-CS-1 Modules
contexts OBJECT IDENTIFIER ::=
  {itu-t recommendation q 1218 modules(0) contexts(8) selectedContexts(1)
   version(1)}

-- For IN CS-2 Modules
datatypes OBJECT IDENTIFIER ::=
  {itu-t recommendation q 1228 modules(0) in-cs2-datatypes(0) version1(0)}

errortypes OBJECT IDENTIFIER ::=
  {itu-t recommendation q 1228 modules(0) in-cs2-errortypes(1) version1(0)}

operationcodes OBJECT IDENTIFIER ::=
  {itu-t recommendation q 1228 modules(0) in-cs2-operationcodes(2) version1(0)}

errorcodes OBJECT IDENTIFIER ::=
  {itu-t recommendation q 1228 modules(0) in-cs2-errorcodes(3) version1(0)}

classes OBJECT IDENTIFIER ::=
  {itu-t recommendation q 1228 modules(0) in-cs2-classes(4) version1(0)}

ssf-scf-Operations OBJECT IDENTIFIER ::=
  {itu-t recommendation q 1228 modules(0) in-cs2-ssf-scf-ops-args(5)
   version1(0)}

ssf-scf-Protocol OBJECT IDENTIFIER ::=
  {itu-t recommendation q 1228 modules(0) in-cs2-ssf-scf-pkgs-contracts-acs(6)
   version1(0)}

scf-srf-Operations OBJECT IDENTIFIER ::=
  {itu-t recommendation q 1228 modules(0) in-cs2-scf-srf-ops-args(7)
   version1(0)}

scf-srf-Protocol OBJECT IDENTIFIER ::=
  {itu-t recommendation q 1228 modules(0) in-cs2-scf-srf-pkgs-contracts-acs(8)
   version1(0)}

sdf-InformationFramework OBJECT IDENTIFIER ::=
  {itu-t recommendation q 1228 modules(0) sdfInformationFramework(9)
   version1(0)}

sdf-BasicAccessControl OBJECT IDENTIFIER ::=
  {itu-t recommendation q 1228 modules(0) sdfBasicAccessControl(10) version1(0)}

scf-sdf-Operations OBJECT IDENTIFIER ::=
  {itu-t recommendation q 1228 modules(0) scf-sdf-operations(11) version1(0)}

scf-sdf-Protocol OBJECT IDENTIFIER ::=
  {itu-t recommendation q 1218 modules(0) in-scf-sdf-protocol(12) version1(0)}

scf-scf-Operations OBJECT IDENTIFIER ::=
  {itu-t recommendation q 1228 modules(0) in-cs2-scf-scf-ops-args(13)
   version1(0)}

scf-scf-Protocol OBJECT IDENTIFIER ::=
  {itu-t recommendation q 1228 modules(0) in-cs2-scf-scf-pkgs-contracts-acs(14)
   version1(0)}

scf-cusf-Operations OBJECT IDENTIFIER ::=
  {itu-t recommendation q 1228 modules(0) in-cs2-scf-cusf-ops-args(15)
   version1(0)}

scf-cusf-Protocol OBJECT IDENTIFIER ::=
  {itu-t recommendation q 1228 modules(0)
   in-cs2-scf-cusf-pkgs-contracts-acs(16) version1(0)}

object-identifiers OBJECT IDENTIFIER ::=
  {itu-t recommendation q 1228 modules(0) in-cs2-object-identifiers(17)
   version1(0)}

sdf-sdf-Protocol OBJECT IDENTIFIER ::=
  {itu-t recommendation q 1228 modules(0) in-cs2-sdf-sdf-Protocol(18)
   version1(0)}

id-cs2 OBJECT IDENTIFIER ::= {itu-t recommendation q 1228 cs2(2)}

id-ac OBJECT IDENTIFIER ::= {id-cs2 ac(3)}

id-as OBJECT IDENTIFIER ::= {id-cs2 as(5)}

id-rosObject OBJECT IDENTIFIER ::= {id-cs2 rosObject(25)}

id-contract OBJECT IDENTIFIER ::= {id-cs2 contract(26)}

id-package OBJECT IDENTIFIER ::= {id-cs2 package(27)}

-- for ac, as, rosObject, contract and package, the values are identical to Q.1218
id-package-scf-scfConnection OBJECT IDENTIFIER ::=
  {id-package 46}

id-package-dsspConnection OBJECT IDENTIFIER ::= {id-package 47}

-- ROS Objects
id-rosObject-scf OBJECT IDENTIFIER ::= {id-rosObject 4}

id-rosObject-ssf OBJECT IDENTIFIER ::= {id-rosObject 5}

id-rosObject-srf OBJECT IDENTIFIER ::= {id-rosObject 6}

id-rosObject-cusf OBJECT IDENTIFIER ::= {id-rosObject 7}

id-rosObject-dssp OBJECT IDENTIFIER ::= {id-rosObject 8}

id-rosObject-sdf OBJECT IDENTIFIER ::= {id-rosObject 9}

id-rosObject-dua OBJECT IDENTIFIER ::= {id-rosObject 1}

id-rosObject-directory OBJECT IDENTIFIER ::= {id-rosObject 2}

id-rosObject-dapDSA OBJECT IDENTIFIER ::= {id-rosObject 3}

id-rosObject-dspDSA OBJECT IDENTIFIER ::= {id-rosObject 10}

id-rosObject-initiatingConsumerDSA OBJECT IDENTIFIER ::= {id-rosObject 11}

id-rosObject-respondingSupplierDSA OBJECT IDENTIFIER ::= {id-rosObject 12}

id-rosObject-respondingConsumerDSA OBJECT IDENTIFIER ::= {id-rosObject 13}

id-rosObject-initiatingSupplierDSA OBJECT IDENTIFIER ::= {id-rosObject 14}

-- ssf/scf Application Contexts
id-ac-cs2-ssf-scfGenericAC OBJECT IDENTIFIER ::=
  {id-ac 4}

id-ac-cs2-ssf-scfDPSpecificAC OBJECT IDENTIFIER ::= {id-ac 5}

id-ac-cs2-ssf-scfAssistHandoffAC OBJECT IDENTIFIER ::= {id-ac 6}

id-ac-cs2-ssf-scfServiceManagementAC OBJECT IDENTIFIER ::= {id-ac 7}

id-ac-cs2-scf-ssfGenericAC OBJECT IDENTIFIER ::= {id-ac 8}

id-ac-cs2-scf-ssfDPSpecificAC OBJECT IDENTIFIER ::= {id-ac 9}

id-ac-cs2-scf-ssfTrafficManagementAC OBJECT IDENTIFIER ::= {id-ac 10}

id-ac-cs2-scf-ssfServiceManagementAC OBJECT IDENTIFIER ::= {id-ac 11}

id-ac-cs2-scf-ssfStatusReportingAC OBJECT IDENTIFIER ::= {id-ac 12}

id-ac-cs2-scf-ssfTriggerManagementAC OBJECT IDENTIFIER ::= {id-ac 13}

-- srf/scf Application Context
id-ac-srf-scf OBJECT IDENTIFIER ::= {id-ac 14}

-- SCF-SDF Application Contexts
id-ac-indirectoryAccessAC OBJECT IDENTIFIER ::=
  {id-ac 1}

id-ac-indirectoryAccessWith3seAC OBJECT IDENTIFIER ::= {id-ac 2}

id-ac-inExtendedDirectoryAccessAC OBJECT IDENTIFIER ::= {id-ac 3}

id-ac-inExtendedDirectoryAccessWith3seAC OBJECT IDENTIFIER ::= {id-ac 27}

-- SDF-SDF Application Contexts
id-ac-indirectorySystemAC OBJECT IDENTIFIER ::=
  {id-ac 15}

id-ac-inShadowSupplierInitiatedAC OBJECT IDENTIFIER ::= {id-ac 16}

id-ac-inShadowConsumerInitiatedAC OBJECT IDENTIFIER ::= {id-ac 17}

id-ac-indirectorySystemWith3seAC OBJECT IDENTIFIER ::= {id-ac 18}

id-ac-inShadowSupplierInitiatedWith3seAC OBJECT IDENTIFIER ::= {id-ac 19}

id-ac-inShadowConsumerInitiatedWith3seAC OBJECT IDENTIFIER ::= {id-ac 20}

-- scf/scf Application Contexts
id-ac-scf-scfOperationsAC OBJECT IDENTIFIER ::=
  {id-ac 21}

id-ac-distributedSCFSystemAC OBJECT IDENTIFIER ::= {id-ac 22}

id-ac-scf-scfOperationsWith3seAC OBJECT IDENTIFIER ::= {id-ac 23}

id-ac-distributedSCFSystemWith3seAC OBJECT IDENTIFIER ::= {id-ac 24}

-- cusf/scf Application Contexts
id-ac-scf-cusf OBJECT IDENTIFIER ::= {id-ac 25}

id-ac-cusf-scf OBJECT IDENTIFIER ::= {id-ac 26}

-- ssf/scf Contracts
id-inCs2SsfToScfGeneric OBJECT IDENTIFIER ::=
  {id-contract 3}

id-inCs2SsfToScfDpSpecific OBJECT IDENTIFIER ::= {id-contract 4}

id-inCs2AssistHandoffSsfToScf OBJECT IDENTIFIER ::= {id-contract 5}

id-inCs2ScfToSsfGeneric OBJECT IDENTIFIER ::= {id-contract 6}

id-inCs2ScfToSsfDpSpecific OBJECT IDENTIFIER ::= {id-contract 7}

id-inCs2ScfToSsfTrafficManagement OBJECT IDENTIFIER ::= {id-contract 8}

id-inCs2ScfToSsfServiceManagement OBJECT IDENTIFIER ::= {id-contract 9}

id-inCs2SsfToScfServiceManagement OBJECT IDENTIFIER ::= {id-contract 10}

id-inCs2ScfToSsfStatusReporting OBJECT IDENTIFIER ::= {id-contract 11}

id-inCs2ScfToSsfTriggerManagement OBJECT IDENTIFIER ::= {id-contract 12}

-- srf/scf Contracts
id-contract-srf-scf OBJECT IDENTIFIER ::= {id-contract 13}

-- SCF-SDF Contracts
id-contract-dap OBJECT IDENTIFIER ::= {id-contract 1}

id-contract-dapExecute OBJECT IDENTIFIER ::= {id-contract 2}

-- SDF-SDF Contracts
id-contract-indsp OBJECT IDENTIFIER ::= {id-contract 14}

id-contract-shadowConsumer OBJECT IDENTIFIER ::= {id-contract 15}

id-contract-shadowSupplier OBJECT IDENTIFIER ::= {id-contract 17}

-- scf/scf Contracts
id-contract-scf-scf OBJECT IDENTIFIER ::= {id-contract 18}

id-contract-dssp OBJECT IDENTIFIER ::= {id-contract 19}

-- cusf/scf Contracts
id-contract-scf-cusf OBJECT IDENTIFIER ::=
  {id-contract 20}

id-contract-cusf-scf OBJECT IDENTIFIER ::= {id-contract 21}

-- ssf/scf Operation Packages
id-package-scfActivation OBJECT IDENTIFIER ::=
  {id-package 11}

id-package-basicBCPDP OBJECT IDENTIFIER ::= {id-package 12}

id-package-advancedBCPDP OBJECT IDENTIFIER ::= {id-package 14}

id-package-srf-scfActivationOfAssist OBJECT IDENTIFIER ::= {id-package 15}

id-package-assistConnectionEstablishment OBJECT IDENTIFIER ::= {id-package 16}

id-package-genericDisconnectResource OBJECT IDENTIFIER ::= {id-package 17}

id-package-nonAssistedConnectionEstablishment OBJECT IDENTIFIER ::=
  {id-package 18}

id-package-connect OBJECT IDENTIFIER ::= {id-package 19}

id-package-callHandling OBJECT IDENTIFIER ::= {id-package 20}

id-package-bcsmEventHandling OBJECT IDENTIFIER ::= {id-package 21}

id-package-dpSpecificEventHandling OBJECT IDENTIFIER ::= {id-package 22}

id-package-chargingEventHandling OBJECT IDENTIFIER ::= {id-package 23}

id-package-ssfCallProcessing OBJECT IDENTIFIER ::= {id-package 24}

id-package-scfCallInitiation OBJECT IDENTIFIER ::= {id-package 25}

id-package-timer OBJECT IDENTIFIER ::= {id-package 26}

id-package-billing OBJECT IDENTIFIER ::= {id-package 27}

id-package-charging OBJECT IDENTIFIER ::= {id-package 28}

id-package-trafficManagement OBJECT IDENTIFIER ::= {id-package 29}

id-package-serviceManagementActivate OBJECT IDENTIFIER ::= {id-package 30}

id-package-serviceManagementResponse OBJECT IDENTIFIER ::= {id-package 31}

id-package-callReport OBJECT IDENTIFIER ::= {id-package 32}

id-package-signallingControl OBJECT IDENTIFIER ::= {id-package 33}

id-package-activityTest OBJECT IDENTIFIER ::= {id-package 34}

id-package-statusReporting OBJECT IDENTIFIER ::= {id-package 35}

id-package-cancel OBJECT IDENTIFIER ::= {id-package 36}

id-package-cphResponse OBJECT IDENTIFIER ::= {id-package 37}

id-package-entityReleased OBJECT IDENTIFIER ::= {id-package 38}

id-package-triggerManagement OBJECT IDENTIFIER ::= {id-package 39}

id-package-uSIHandling OBJECT IDENTIFIER ::= {id-package 40}

id-package-facilityIEHandling OBJECT IDENTIFIER ::= {id-package 41}

-- srf/scf Operation Packages
id-package-specializedResourceControl OBJECT IDENTIFIER ::=
  {id-package 42}

id-package-srf-scfCancel OBJECT IDENTIFIER ::= {id-package 43}

id-package-messageControl OBJECT IDENTIFIER ::= {id-package 44}

id-package-scriptControl OBJECT IDENTIFIER ::= {id-package 45}

-- SCF-SDF Packages
id-package-search OBJECT IDENTIFIER ::= {id-package 2}

id-package-modify OBJECT IDENTIFIER ::= {id-package 3}

id-package-dapConnection OBJECT IDENTIFIER ::= {id-package 10}

id-package-execute OBJECT IDENTIFIER ::= {id-package 4}

-- SDF-SDF Packages
id-package-dspConnection OBJECT IDENTIFIER ::=
  {id-package 47}

id-package-inchainedModify OBJECT IDENTIFIER ::= {id-package 48}

id-package-inchainedSearch OBJECT IDENTIFIER ::= {id-package 49}

id-package-chainedExecute OBJECT IDENTIFIER ::= {id-package 50}

id-package-dispConnection OBJECT IDENTIFIER ::= {id-package 51}

id-package-shadowConsumer OBJECT IDENTIFIER ::= {id-package 52}

id-package-shadowSupplier OBJECT IDENTIFIER ::= {id-package 53}

-- scf/scf Operation Packages
id-package-handlingInformation OBJECT IDENTIFIER ::=
  {id-package 54}

id-package-notification OBJECT IDENTIFIER ::= {id-package 55}

id-package-chargingInformation OBJECT IDENTIFIER ::= {id-package 56}

id-package-userInformation OBJECT IDENTIFIER ::= {id-package 57}

id-package-networkCapability OBJECT IDENTIFIER ::= {id-package 58}

id-package-chainedSCFOperations OBJECT IDENTIFIER ::= {id-package 59}

-- cusf/scf Operation Packages
id-package-emptyConnection OBJECT IDENTIFIER ::=
  {id-package 60}

id-package-basic-cusf-scf OBJECT IDENTIFIER ::= {id-package 61}

id-package-basic-scf-cusf OBJECT IDENTIFIER ::= {id-package 62}

-- ssf/scf Abstract Syntaxes
id-as-ssf-scfGenericAS OBJECT IDENTIFIER ::=
  {id-as 4}

id-as-ssf-scfDpSpecificAS OBJECT IDENTIFIER ::= {id-as 5}

id-as-assistHandoff-ssf-scfAS OBJECT IDENTIFIER ::= {id-as 6}

id-as-scf-ssfGenericAS OBJECT IDENTIFIER ::= {id-as 7}

id-as-scf-ssfDpSpecificAS OBJECT IDENTIFIER ::= {id-as 8}

id-as-scf-ssfTrafficManagementAS OBJECT IDENTIFIER ::= {id-as 9}

id-as-scf-ssfServiceManagementAS OBJECT IDENTIFIER ::= {id-as 10}

id-as-ssf-scfServiceManagementAS OBJECT IDENTIFIER ::= {id-as 11}

id-as-scf-ssfStatusReportingAS OBJECT IDENTIFIER ::= {id-as 12}

id-as-scf-ssfTriggerManagementAS OBJECT IDENTIFIER ::= {id-as 13}

-- srf/scf Abstract Syntaxes
id-as-basic-srf-scf OBJECT IDENTIFIER ::=
  {id-as 14}

id-as-basic-scf-srf OBJECT IDENTIFIER ::= {id-as 15}

-- SCF-SDF Abstract Syntaxes
id-as-indirectoryOperationsAS OBJECT IDENTIFIER ::=
  {id-as 1}

id-as-indirectoryBindingAS OBJECT IDENTIFIER ::= {id-as 2}

id-as-inExtendedDirectoryOperationsAS OBJECT IDENTIFIER ::= {id-as 3}

id-as-inSESEAS OBJECT IDENTIFIER ::= {id-as 25}

-- SDF-SDF Abstract Syntaxes
id-as-indirectorySystemAS OBJECT IDENTIFIER ::=
  {id-as 16}

id-as-indirectoryDSABindingAS OBJECT IDENTIFIER ::= {id-as 17}

id-as-indirectoryShadowAS OBJECT IDENTIFIER ::= {id-as 18}

id-as-indsaShadowBindingAS OBJECT IDENTIFIER ::= {id-as 19}

-- scf/scf Abstract Syntaxes
id-as-scf-scfOperationsAS OBJECT IDENTIFIER ::=
  {id-as 20}

id-as-distributedSCFSystemAS OBJECT IDENTIFIER ::= {id-as 21}

id-as-scf-scfBindingAS OBJECT IDENTIFIER ::= {id-as 22}

-- cusf/scf Abstract Syntaxes
id-as-basic-cusf-scf OBJECT IDENTIFIER ::=
  {id-as 23}

id-as-basic-scf-cusf OBJECT IDENTIFIER ::= {id-as 24}

-- Object Identifiers for SDF-SDF interface
-- useful definitions
in-ds OBJECT IDENTIFIER ::=
  {itu-t recommendation q 1228 sdf-objects(10)}

id-avc OBJECT IDENTIFIER ::= {in-ds 29}

id-aca OBJECT IDENTIFIER ::= {in-ds 24}

id-soa OBJECT IDENTIFIER ::= {in-ds 21}

-- Object Identifiers for SDF-SDF interface
-- SDF Attributes
id-soa-methodRuleUse OBJECT IDENTIFIER ::=
  {id-soa 1}

id-aca-prescriptiveACI OBJECT IDENTIFIER ::= {id-aca 4}

id-aca-entryACI OBJECT IDENTIFIER ::= {id-aca 5}

id-aca-subentryACI OBJECT IDENTIFIER ::= {id-aca 6}

-- SDF  Attribute Value Contexts
id-avc-assignment OBJECT IDENTIFIER ::=
  {id-avc 1}

END

-- Generated by Asnp, the ASN.1 pretty-printer of France Telecom R&D
