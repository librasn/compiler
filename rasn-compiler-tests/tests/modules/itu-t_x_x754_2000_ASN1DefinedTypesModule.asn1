-- Module ASN1DefinedTypesModule (X.754:02/2000)
-- See also ITU-T X.754 (02/2000)
-- See also the index of all ASN.1 assignments needed in this document

ASN1DefinedTypesModule {itu-t(0) recommendation(0) x(24) eecmod(754)
  informationModel(0) asn1Modules(2) asn1DefinedTypesModule(0)} DEFINITIONS
IMPLICIT TAGS ::=
BEGIN

-- EXPORTS everything
IMPORTS
  TimePeriod
    FROM MetricModule {joint-iso-itu-t ms(9) function(2) part11(11)
      asn1Module(2) 0}
  ObjectClass, ObjectInstance, Attribute
    FROM CMIP-1 {joint-iso-itu-t ms(9) cmip(1) modules(0) protocol(3)}
  -- see ITU-T X.711
  AdministrativeState, OperationalState, ManagementExtension, LogRecordId,
    Destination, CapacityAlarmThreshold, LogFullAction
    FROM Attribute-ASN1Module {joint-iso-itu-t ms(9) smi(3) part2(2)
      asn1Module(2) 1}-- see ITU-T X.721
  ;

-- OBJECT IDENTIFIERS
informationModel OBJECT IDENTIFIER ::=
  {itu-t(0) recommendation(0) x(24) eecmod(754) informationModel(0)}

eecManagedObjectClass OBJECT IDENTIFIER ::=
  {informationModel managedObjectClass(3)}

eecPackage OBJECT IDENTIFIER ::= {informationModel package(4)}

eecNameBinding OBJECT IDENTIFIER ::= {informationModel nameBinding(6)}

eecAttribute OBJECT IDENTIFIER ::= {informationModel attribute(7)}

eecAction OBJECT IDENTIFIER ::= {informationModel action(9)}

eecBehaviour OBJECT IDENTIFIER ::= {informationModel behaviour(11)}

eecNotification OBJECT IDENTIFIER ::= {informationModel notification(10)}

AgingPeriod ::= TimePeriod

SendToList ::= SEQUENCE {
  recordId         LogRecordId,
  destinationList  SET OF Destination
}

GetDestinationArgument ::= SEQUENCE OF LogRecordId

GetDestinationResult ::= SEQUENCE OF SendToList

NonNegativeInteger ::= INTEGER(0..MAX)

QueuingDiscipline ::= ENUMERATED {fifoTransmission(0), lifoTransmission(1)}

QueueSize ::= NonNegativeInteger -- contains a count of the number of records

RecordIdList ::= SEQUENCE OF NonNegativeInteger

END

-- Generated by Asnp, the ASN.1 pretty-printer of France Telecom R&D
