-- Module commURI (H.350:04/2006)
-- See also ITU-T formal description search tool
-- See also the index of all ASN.1 assignments needed in this document

CommURI {itu-t(0) recommendation(0) h(8) 350 1 cr(1) commURI(1) module(4)}
DEFINITIONS ::=
BEGIN

-- Communication Object Schema
-- Schema for Representing Communication Objects in an LDAP Directory
-- Abstract
-- This document defines the schema for representing Communication
-- objects in an LDAP directory [LDAPv3].  It defines schema elements
-- to represent a communication object URI [commURIObject].
--                     .1 = Communication related work
--                     .1.1 = commURIObject
--                     .1.1.1 = attributes
--                     .1.1.2 = objectclass
--                     .1.1.3 = syntax
IMPORTS
  -- from ITU-T Rec. X.501 | ISO/IEC 9594-2
  ATTRIBUTE, OBJECT-CLASS, MATCHING-RULE, top
    FROM InformationFramework {joint-iso-itu-t ds(5) module(1)
      informationFramework(1) 4}
  -- from ITU-T Rec. X.520 | ISO/IEC 9594-6
  DirectoryString{}, caseExactMatch
    FROM SelectedAttributeTypes {joint-iso-itu-t ds(5) module(1)
      selectedAttributeTypes(5) 4};

-- Attribute Type Definitions
--    The following attribute types are defined in this document:
--        commURI
commURI ATTRIBUTE ::= {
  WITH SYNTAX             DirectoryString {256}
  EQUALITY MATCHING RULE  caseExactMatch
  ID                      {at  1}
}

-- Object Class Definitions
--    The following object classes are defined in this document:
--        commURIObject
-- commURIObject
--
--    This auxiliary object class represents a URI attribute type
commURIObject OBJECT-CLASS ::= {
  SUBCLASS OF  {top}
  MAY CONTAIN  {commURI}
  ID           {oc  1}
}

h350-cr OBJECT IDENTIFIER ::= {itu-t(0) recommendation(0) h(8) 350 1 cr(1)}

cu OBJECT IDENTIFIER ::= {h350-cr cu(1)}

at OBJECT IDENTIFIER ::= {cu at(1)}

oc OBJECT IDENTIFIER ::= {cu oc(2)}

caseIgnoreIA5Match MATCHING-RULE ::= {
  SYNTAX  IA5String
  ID      {1 3 6 1 4 1 1466 109 114 2}
}

caseIgnoreIA5SubstringsMatch MATCHING-RULE ::= {
  SYNTAX  IA5String
  ID      {1 3 6 1 4 1 1466 109 114 3}
}

userSMIMECertificate ATTRIBUTE ::= {
  WITH SYNTAX  OCTET STRING
  ID           {2 16 840 1 113730 3 1 40}
}

END -- end of ASN.1

-- Generated by Asnp, the ASN.1 pretty-printer of France Telecom R&D
