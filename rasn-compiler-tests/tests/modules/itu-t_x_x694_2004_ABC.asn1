-- Module ABC (X.694:01/2004)
-- See also ITU-T X.694 (01/2004)
-- See also the index of all ASN.1 assignments needed in this document

ABC -- The module reference is not standardized
DEFINITIONS AUTOMATIC TAGS ::=
BEGIN

IMPORTS
  Xyz-type
    FROM XYZ
  String, Token
    FROM XSD {joint-iso-itu-t asn1(1) specification(0) modules(0) xsd-module(1)};

Abc-elem ::= [NAME AS UNCAPITALIZED] Xyz-type

Sub1-elem ::= [NAME AS UNCAPITALIZED] XSD.String

Sub2-elem ::= [NAME AS UNCAPITALIZED] XSD.String

Sub2-attr ::= [NAME AS UNCAPITALIZED] [ATTRIBUTE] XSD.Token

ENCODING-CONTROL XER
	GLOBAL-DEFAULTS MODIFIED-ENCODINGS
	GLOBAL-DEFAULTS CONTROL-NAMESPACE
		"http://www.w3.org/2001/XMLSchema-instance"
END

-- Generated by Asnp, the ASN.1 pretty-printer of France Telecom R&D
