-- Module Audio-Coding-Attributes (T.419:08/1995)
-- See also ITU-T T.419 (08/1995)
-- See also the index of all ASN.1 assignments needed in this document

Audio-Coding-Attributes {2 8 1 9 3} DEFINITIONS ::=
BEGIN

EXPORTS Audio-Coding-Attributes;

IMPORTS
  Character-Data
    FROM Document-Profile-Descriptor {2 8 1 5 6}; --  see ITU-T Rec. T.415 | ISO/IEC 8613-5

Audio-Coding-Attributes ::= SET {
  marker  [0] IMPLICIT SEQUENCE OF Marker OPTIONAL
}

Marker ::= SEQUENCE {
  time-offset   [0] IMPLICIT INTEGER,
  marker-label
    CHOICE {unique-label  [0] IMPLICIT OBJECT IDENTIFIER,
            description   [1] IMPLICIT Character-Data}
}

END

-- Generated by Asnp, the ASN.1 pretty-printer of France Telecom R&D
