-- Module IN-CS3-SCF-CUSF-Datatypes (Q.1238.7:06/2000)
-- See also ITU-T Q.1238.7 (06/2000)
-- See also the index of all ASN.1 assignments needed in this document

-- 13	ASN.1 DEFINITIONS
--
-- 13.1	DATA TYPES
-- This clause specifies the data type definitions of parameters used in CUSF-SCF relationship.
-- Refer to the other parts of this Recommendation for the other data type definitions
-- not specified in this clause.
IN-CS3-SCF-CUSF-Datatypes {itu-t recommendation q 1238 modules(1)
  in-cs3-scf-cusf-datatypes(24) version1(0)} DEFINITIONS IMPLICIT TAGS ::=
BEGIN

IMPORTS
  ros-InformationObjects, common-classes, common-datatypes, ssf-scf-classes,
    scf-cusf-classes, ssf-scf-datatypes
    FROM IN-CS3-object-identifiers {itu-t recommendation q 1238 modules(1)
      in-cs3-object-identifiers(0) version1(0)}
  COMMON-BOUNDS
    FROM IN-CS3-common-classes {itu-t recommendation q 1238 modules(1)
      in-cs3-common-classes(5) version1(0)}
  Extensions{}
    FROM IN-CS3-common-datatypes {itu-t recommendation q 1238 modules(1)
      in-cs3-common-datatypes(1) version1(0)}
  SCF-SSF-BOUNDS
    FROM IN-CS3-SSF-SCF-Classes {itu-t recommendation q 1238 modules(1)
      in-cs3-ssf-scf-classes(7) version1(0)}
  SCF-CUSF-BOUNDS
    FROM IN-CS3-SCF-CUSF-Classes {itu-t recommendation q 1238 modules(1)
      in-cs3-scf-cusf-classes(25) version1(0)}
  BearerCapability{}, CalledPartyNumber{}, CallingPartyNumber{},
    CallingPartySubaddress{}, Cause{}, GenericNumbers{},
    HighLayerCompatibility, LocationNumber{}, MonitorMode,
    ServiceAddressInformation, TerminalType, USIInformation{},
    USIServiceIndicator{}
    FROM IN-CS3-SSF-SCF-datatypes {itu-t recommendation q 1238 modules(1)
      in-cs3-ssf-scf-datatypes(6) version1(0)};

-- The following three definitions are local short-hand notation for convenience.
B1 ::=
  COMMON-BOUNDS --defined in Recommendation Q.1238.1

B2 ::= SCF-SSF-BOUNDS --defined in Recommendation Q.1238.2

B7 ::= SCF-CUSF-BOUNDS --defined in Recommendation Q.1238.7

BCUSMEvent ::= SEQUENCE {
  eventType    [0]  EventTypeBCUSM,
  monitorMode  [1]  MonitorMode,
  ...
}

CallUnrelatedDpSpecificCommonParameters{B1:b1, B2:b2} ::= SEQUENCE {
  serviceAddressInformation  [0]  ServiceAddressInformation,
  callingPartyNumber         [1]  CallingPartyNumber{b2} OPTIONAL,
  locationNumber             [2]  LocationNumber{b2} OPTIONAL,
  terminalType               [3]  TerminalType DEFAULT isdn,
  extensions                 [4]  Extensions{b1} OPTIONAL,
  uSIServiceIndicator        [5]  USIServiceIndicator{b2} OPTIONAL,
  uSIInformation             [6]  USIInformation{b2} OPTIONAL,
  cUApplicationInd           [7]  CUApplicationInd OPTIONAL,
  calledPartyNumber          [8]  CalledPartyNumber{b2} OPTIONAL,
  callingPartySubadress      [9]  CallingPartySubaddress{b2} OPTIONAL,
  highLayerCompatibility     [10]  HighLayerCompatibility OPTIONAL,
  bearerCapability           [11]  BearerCapability{b2} OPTIONAL,
  genericNumbers             [12]  GenericNumbers{b2} OPTIONAL,
  ...
}

CUApplicationInd ::= CHOICE {
  localValue   [0]  INTEGER,
  globalValue  [1]  OBJECT IDENTIFIER
}

EventSpecificInformationBCUSM{B2:b2, B7:b7} ::= CHOICE {
  componentReceivedSpecificInfo
    [0]  SEQUENCE {componentReceivedInfo
                     [0]  OCTET STRING
                            (SIZE (b7.&minCompReceivedInfoLen..
                                     b7.&maxCompReceivedInfoLen)) OPTIONAL,
                   ...},
  associationReleaseRequestedSpecificInfo
    [1]  SEQUENCE {associationReleaseInfo
                     [0]  OCTET STRING
                            (SIZE (b7.&minAssReleaseInfoLen..
                                     b7.&maxAssReleaseInfoLen)) OPTIONAL,
                   releaseCause            [1]  Cause{b2} OPTIONAL,
                   ...}
}

-- For the OCTET STRING type parameters (componentReceivedInfo and associationReleaseInfo),
-- its content is network operator specific. The internal coding of this parameter can be defined using ASN.1 and
-- the related Basic Encoding Rules (BER). In such a case the value of this parameter (after the first tag and length
-- information) is the BER encoding of the defined ASN.1 internal structure. The tag of this parameter as defined by
-- ITU-T is never replaced.
EventTypeBCUSM ::= ENUMERATED {
  componentReceived(127), associationReleaseRequested(126),
  activationReceivedAndAuthorized(125)}

Message ::= ENUMERATED {rELease(77), rELeaseCOMPlete(90), fACility(98)}

END

-- Generated by Asnp, the ASN.1 pretty-printer of France Telecom R&D
