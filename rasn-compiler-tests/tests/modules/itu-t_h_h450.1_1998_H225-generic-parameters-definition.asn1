-- Module H225-generic-parameters-definition (H.450.1:02/1998)
-- See also ITU-T H.450.1 (02/1998)
-- See also the index of all ASN.1 assignments needed in this document

H225-generic-parameters-definition {itu-t recommendation h 450 1 version1(0)
  h225-generic-parameters(6)} DEFINITIONS AUTOMATIC TAGS ::=
BEGIN

H225InformationElement ::= OCTET STRING

END -- of H225 Generic parameters definition

-- Generated by Asnp, the ASN.1 pretty-printer of France Telecom R&D
