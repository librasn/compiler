-- Module SecurityAuditTrailDefinitions (:)
-- See also ITU-T X.740 (09/1992)
-- See also the index of all ASN.1 assignments needed in this document

SecurityAuditTrailDefinitions {joint-iso-itu-t ms(9) function(2) part8(8)
  asn1Module(2) 1} DEFINITIONS ::=
BEGIN

IMPORTS
  ServiceReportCause
    FROM SecurityAuditTrail-ASN1Module {joint-iso-itu-t ms(9) function(2)
      part8(8) asn1Module(2) 2};

securityAuditTrail-Object OBJECT IDENTIFIER ::=
  {joint-iso-itu-t ms(9) function(2) part8(8) managedObjectClass(3)}

securityAuditTrail-Package OBJECT IDENTIFIER ::=
  {joint-iso-itu-t ms(9) function(2) part8(8) package(4)}

securityAuditTrail-Attribute OBJECT IDENTIFIER ::=
  {joint-iso-itu-t ms(9) function(2) part8(8) attribute(7)}

securityAuditTrail-Notification OBJECT IDENTIFIER ::=
  {joint-iso-itu-t ms(9) function(2) part8(8) notification(10)}

serviceReportCause OBJECT IDENTIFIER ::=
  {joint-iso-itu-t ms(9) function(2) part8(8) standardSpecificExtension(0) 1}

-- the following OBJECT IDENTIFIER values can be used as values for the service report cause parameter in A.5.
serviceRequest ServiceReportCause ::=
  {serviceReportCause  1}

serviceDenial ServiceReportCause ::= {serviceReportCause  2}

serviceResponse ServiceReportCause ::= {serviceReportCause  3}

serviceFailure ServiceReportCause ::= {serviceReportCause  4}

serviceRecovery ServiceReportCause ::= {serviceReportCause  5}

otherReason ServiceReportCause ::= {serviceReportCause  6}

END

-- Generated by Asnp, the ASN.1 pretty-printer of France Telecom R&D
