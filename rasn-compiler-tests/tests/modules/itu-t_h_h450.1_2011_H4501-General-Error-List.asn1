-- Module H4501-General-Error-List (H.450.1:05/2011)
-- See also ITU-T H.450.1 (05/2011)
-- See also the index of all ASN.1 assignments needed in this document

H4501-General-Error-List {itu-t recommendation h 450 1 version2(1)
  general-error-list(1)} DEFINITIONS AUTOMATIC TAGS ::=
BEGIN

IMPORTS
  ERROR
    FROM Remote-Operations-Information-Objects {joint-iso-itu-t
      remote-operations(4) informationObjects(5) version2(1)};

-- The following errors are based on the error definitions of Recommendation Q.950.
userNotSubscribed ERROR ::= {CODE  local:0
}

-- is an indication that the user has not subscribed to this service.
rejectedByNetwork ERROR ::= {CODE  local:1
}

-- is an indication that the requested service is rejected by the network
-- (e.g., gatekeeper).
rejectedByUser ERROR ::= {CODE  local:2
}

-- is an indication that the remote user has rejected this service request.
notAvailable ERROR ::= {CODE  local:3
}

-- is an indication that the requested service is not available under the specific circumstances
insufficientInformation ERROR ::= {CODE  local:5
}

-- is an indication that the content of operation argument is
-- incomplete, or absent entirely.
invalidServedUserNumber ERROR ::= {CODE  local:6
}

-- is an indication that the requested service cannot be performed
-- because of the usage of an invalid served user number.
invalidCallState ERROR ::= {CODE  local:7
}

-- is an indication that the service request is
-- incompatible with the current H.225.0 call state
basicServiceNotProvided ERROR ::= {CODE  local:8
}

-- is an indication that the service request refers to an unsupported
-- terminal capability.
notIncomingCall ERROR ::= {CODE  local:9
}

-- is an indication that the service request has been invoked for an
-- outgoing call, which is not permitted for that service.
supplementaryServiceInteractionNotAllowed ERROR ::= {CODE  local:10
}

-- is an indication that the service request is not permitted in
-- combination with either a further requested or active supplementary
-- service.
resourceUnavailable ERROR ::= {CODE  local:11
}

-- is an indication that the service provider has temporarily no
-- resource available for the provision of the requested service.
callFailure ERROR ::= {CODE  local:25
}

-- is an indication that the requested supplementary service was not executable by virtue
-- of a Basic Call Failure.
proceduralError ERROR ::= {CODE  local:43
}

-- is an indication that a received operation APDU is incompatible with the procedural
-- context in which it is received.
END --  of H4501-General-Error-List

-- Generated by Asnp, the ASN.1 pretty-printer of France Telecom R&D
