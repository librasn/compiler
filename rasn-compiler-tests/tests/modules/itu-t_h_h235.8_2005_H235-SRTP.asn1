-- Module H235-SRTP (H.235.8:09/2005)
-- See also ITU-T H.235.8 (09/2005)
-- See also the index of all ASN.1 assignments needed in this Recommendation

H235-SRTP DEFINITIONS AUTOMATIC TAGS ::=
BEGIN

IMPORTS GenericData
          FROM H323-MESSAGES;

SrtpCryptoCapability ::=
  SEQUENCE OF SrtpCryptoInfo -- used in H.245 genericH235SecurityCapability

SrtpCryptoInfo ::= SEQUENCE {
  cryptoSuite    OBJECT IDENTIFIER OPTIONAL,
  sessionParams  SrtpSessionParameters OPTIONAL,
  allowMKI       BOOLEAN OPTIONAL,
  ...
}

SrtpKeys ::= SEQUENCE OF SrtpKeyParameters -- used in H.235 V3KeySyncMaterial

SrtpKeyParameters ::= SEQUENCE {
  masterKey   OCTET STRING,
  masterSalt  OCTET STRING,
  lifetime    CHOICE {powerOfTwo  INTEGER,
                      specific    INTEGER,
                      ...} OPTIONAL,
  mki         SEQUENCE {length  INTEGER(1..128),
                        value   OCTET STRING,
                        ...} OPTIONAL,
  ...
}

SrtpSessionParameters ::= SEQUENCE {
  kdr                  INTEGER(0..24) OPTIONAL, -- power of 2
  unencryptedSrtp      BOOLEAN OPTIONAL,
  unencryptedSrtcp     BOOLEAN OPTIONAL,
  unauthenticatedSrtp  BOOLEAN OPTIONAL,
  fecOrder             FecOrder OPTIONAL,
  windowSizeHint       INTEGER(64..65535) OPTIONAL,
  newParameter         SEQUENCE OF GenericData OPTIONAL,
  ...
}

FecOrder ::= SEQUENCE {
  fecBeforeSrtp  NULL OPTIONAL,
  fecAfterSrtp   NULL OPTIONAL,
  ...
}

END

-- Generated by Asnp, the ASN.1 pretty-printer of France Telecom R&D
