-- Module H323Identity (H.350.1:05/2011)
-- See also ITU-T H.350.1 (05/2011)
-- See also the index of all ASN.1 assignments needed in this document

H323Identity {itu-t(0) recommendation(0) h(8) 350 1 cr(1) h323Identity(3)
  module(4)} DEFINITIONS ::=
BEGIN

-- h323Identity Object Schema
-- Schema for representing h323Identity Object in an LDAP Directory
-- Abstract
-- This document defines the schema for representing h323Identity
-- object in an LDAP directory [LDAPv3].  It defines schema elements
-- to represent an h323Identity object [h323Identity].
--                     .1 = Communication related work
--                     .1.3 = h323Identity
--                     .1.3.1 = attributes
--                     .1.3.2 = objectclass
--                     .1.3.3 = syntax
IMPORTS
  -- from Rec. ITU-T H.350
  h350-cr, caseIgnoreIA5Match, caseIgnoreIA5SubstringsMatch
    FROM CommURI {itu-t(0) recommendation(0) h(8) 350 1 cr(1) commURI(1)
      module(4)}
  -- from Rec. ITU-T X.501 | ISO/IEC 9594-2
  ATTRIBUTE, OBJECT-CLASS, top
    FROM InformationFramework {joint-iso-itu-t ds(5) module(1)
      informationFramework(1) 6}
  -- from Rec. ITU-T X.520 | ISO/IEC 9594-6
  UnboundedDirectoryString, caseExactMatch, caseExactSubstringsMatch,
    caseIgnoreMatch, caseIgnoreSubstringsMatch
    FROM SelectedAttributeTypes {joint-iso-itu-t ds(5) module(1)
      selectedAttributeTypes(5) 6};

-- Attribute Type Definitions
--    The following attribute types are defined in this document:
--        h323IdentityGKDomain
--        h323Identityh323-ID
--        h323IdentitydialedDigits
--        h323Identityemail-ID
--        h323IdentityURL-ID
--        h323IdentitytransportID
--        h323IdentitypartyNumber
--        h323IdentitymobileUIM
--        h323IdentityEndpointType
--        h323IdentityServiceLevel
h323IdentityGKDomain ATTRIBUTE ::= {
  WITH SYNTAX             IA5String
  EQUALITY MATCHING RULE  caseIgnoreIA5Match
  ID                      {at  1}
}

h323Identityh323-ID ATTRIBUTE ::= {
  WITH SYNTAX               IA5String
  EQUALITY MATCHING RULE    caseIgnoreIA5Match
  SUBSTRINGS MATCHING RULE  caseIgnoreIA5SubstringsMatch
  ID                        {at  2}
}

h323IdentitydialedDigits ATTRIBUTE ::= {
  WITH SYNTAX               IA5String
  EQUALITY MATCHING RULE    caseIgnoreIA5Match
  SUBSTRINGS MATCHING RULE  caseIgnoreIA5SubstringsMatch
  ID                        {at  3}
}

h323Identityemail-ID ATTRIBUTE ::= {
  WITH SYNTAX               IA5String
  EQUALITY MATCHING RULE    caseIgnoreIA5Match
  SUBSTRINGS MATCHING RULE  caseIgnoreIA5SubstringsMatch
  ID                        {at  4}
}

h323IdentityURL-ID ATTRIBUTE ::= {
  WITH SYNTAX               UnboundedDirectoryString
  EQUALITY MATCHING RULE    caseExactMatch
  SUBSTRINGS MATCHING RULE  caseExactSubstringsMatch
  ID                        {at  5}
}

h323IdentitytransportID ATTRIBUTE ::= {
  WITH SYNTAX               IA5String
  EQUALITY MATCHING RULE    caseIgnoreIA5Match
  SUBSTRINGS MATCHING RULE  caseIgnoreIA5SubstringsMatch
  ID                        {at  6}
}

h323IdentitypartyNumber ATTRIBUTE ::= {
  WITH SYNTAX               IA5String
  EQUALITY MATCHING RULE    caseIgnoreIA5Match
  SUBSTRINGS MATCHING RULE  caseIgnoreIA5SubstringsMatch
  ID                        {at  7}
}

h323IdentitymobileUIM ATTRIBUTE ::= {
  WITH SYNTAX               IA5String
  EQUALITY MATCHING RULE    caseIgnoreIA5Match
  SUBSTRINGS MATCHING RULE  caseIgnoreIA5SubstringsMatch
  ID                        {at  8}
}

h323IdentityEndpointType ATTRIBUTE ::= {
  WITH SYNTAX               UnboundedDirectoryString
  EQUALITY MATCHING RULE    caseIgnoreMatch
  SUBSTRINGS MATCHING RULE  caseIgnoreSubstringsMatch
  ID                        {at  9}
}

h323IdentityServiceLevel ATTRIBUTE ::= {
  WITH SYNTAX               UnboundedDirectoryString
  EQUALITY MATCHING RULE    caseIgnoreMatch
  SUBSTRINGS MATCHING RULE  caseIgnoreSubstringsMatch
  ID                        {at  10}
}

-- Object Class Definitions
--    The following object class is defined in this document:
--
--        h323Identity
-- h323Identity
h323Identity OBJECT-CLASS ::= {
  SUBCLASS OF  {top}
  MAY CONTAIN
    {h323IdentityGKDomain | h323Identityh323-ID | h323IdentitydialedDigits |
      h323Identityemail-ID | h323IdentityURL-ID | h323IdentitytransportID |
      h323IdentitypartyNumber | h323IdentitymobileUIM |
      h323IdentityEndpointType | h323IdentityServiceLevel}
  ID           {oc  1}
}

h323-Id OBJECT IDENTIFIER ::= {h350-cr h323-Id(3)}

at OBJECT IDENTIFIER ::= {h323-Id at(1)}

oc OBJECT IDENTIFIER ::= {h323-Id oc(2)}

END -- end of ASN.1

-- Generated by Asnp, the ASN.1 pretty-printer of France Telecom R&D
