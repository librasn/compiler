-- Module Embedded-Q931-Types (Q.932:05/1998)
-- See also ITU-T Q.932 (1998) Amend. 1 (06/2000)
-- See also the index of all ASN.1 assignments needed in this document

Embedded-Q931-Types {itu-t recommendation q 932 embedded-q931-types(5)}
DEFINITIONS EXPLICIT TAGS ::=
BEGIN

EXPORTS Q931InformationElement;

Q931InformationElement ::= [APPLICATION 0] IMPLICIT OCTET STRING

END -- of Embedded-Q931-Types

-- Generated by Asnp, the ASN.1 pretty-printer of France Telecom R&D
