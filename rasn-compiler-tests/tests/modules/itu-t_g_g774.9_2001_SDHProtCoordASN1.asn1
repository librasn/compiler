-- Module SDHProtCoordASN1 (G.774.9:02/2001)
-- See also ITU-T G.774.9 (02/2001)
-- See also the index of all ASN.1 assignments needed in this document

SDHProtCoordASN1 {itu-t(0) recommendation(0) g(7) g774(774) hyphen(127)
  protCoord(9) informationModel(0) asn1Module(2) sdhmspcoord(0)} DEFINITIONS
IMPLICIT TAGS ::=
BEGIN

-- EXPORTS everything
IMPORTS
  AdditionalInformation, AdministrativeState
    FROM Attribute-ASN1Module {joint-iso-itu-t ms(9) smi(3) part2(2)
      asn1Module(2) 1}
  ObjectInstance
    FROM CMIP-1 {joint-iso-itu-t ms(9) cmip(1) modules(0) protocol(3)}
  NameType
    FROM ASN1DefinedTypesModule {itu-t(0) recommendation(0) m(13) gnm(3100)
      informationModel(0) asn1Modules(2) asn1DefinedTypesModule(0)}
  ProtectionGroupType, ProtectionSwitchMode, ResourcePointer, SDHMSPriority
    FROM SDHProtASN1 {itu-t(0) recommendation(0) g(7) g774(774) hyphen(127)
      prot(3) informationModel(0) asn1Module(2) sdhmsp(0)};

sdhProtCoord OBJECT IDENTIFIER ::=
  {itu-t(0) recommendation(0) g(7) g774(774) hyphen(127) protCoord(9)
   informationModel(0)}

g774-09MObjectClass OBJECT IDENTIFIER ::= {sdhProtCoord managedObjectClass(3)}

g774-09NameBinding OBJECT IDENTIFIER ::= {sdhProtCoord nameBinding(6)}

g774-09Attribute OBJECT IDENTIFIER ::= {sdhProtCoord attribute(7)}

g774-09Action OBJECT IDENTIFIER ::= {sdhProtCoord action(9)}

g774-09Parameter OBJECT IDENTIFIER ::= {sdhProtCoord parameter(5)}

AddedProtectionUnits ::= ProtectionUnits

DismissedProtectionGroup ::= ObjectInstance

DismissProtectionInfo ::= DismissedProtectionGroup

EstablishProtectionInfo ::= SEQUENCE {
  protectionUnits          ProtectionUnits,
  protectionGroupType      ProtectionGroupType OPTIONAL,
  revertiveInformation     RevertiveInformation OPTIONAL,
  specificPGConfiguration  AdditionalInformation OPTIONAL
}

IncompatibleWithNEConfig ::= CHOICE {
  alreadyProtected      [0]  ObjectInstance,
  otherIncompatibility  [1]  NULL
}

InconsistentData ::= ENUMERATED {
  exceedingProtectingUnits(0), exceedingUnitsFor1Plus1(1),
  duplicateUnreliable(2), nonRevertiveIncompatibleWith1ToN(3),
  incompletePriorityAssignment(4), otherError(5)}

ModifiedProtectionGroup ::= ObjectInstance

ModifyProtectionInfo ::= SEQUENCE {
  modifiedProtectionGroup  ModifiedProtectionGroup,
  addedProtectionUnits     [0]  AddedProtectionUnits OPTIONAL,
  removedProtectionUnits   [1]  RemovedProtectionUnits OPTIONAL
}

MSPConfigurationError ::= ENUMERATED {
  protectionSwitchModeNotSupported(0), aPSProtocolNotSupported(1),
  invalidChannelNumber(2), notSupportedSDHPriority(3),
  extraTrafficControlNotSupported(4), otherError(5)}

MSPGroupConfigurationParameter ::= SEQUENCE {
  protectionSwitchMode  ProtectionSwitchMode,
  aPSProtocolPresent    BOOLEAN
}

MSPUnitConfigurationParameter ::= SEQUENCE {
  channelNumber        INTEGER,
  sdhPriority          SDHMSPriority OPTIONAL,
  extraTrafficControl  AdministrativeState OPTIONAL
}

OperatorCommandPresent ::= SET OF ResourcePointer

ProtectionConfigurationError ::= CHOICE {
  inconsistentData              [0]  InconsistentData,
  unsupportedProtConfiguration  [1]  UnsupportedProtConfiguration,
  incompatibleWithNEConfig      [2]  IncompatibleWithNEConfig
}

ProtectionResource ::= SEQUENCE {
  unreliableObjects        ResourcePointer,
  protecting               BOOLEAN,
  priority                 INTEGER OPTIONAL,
  specificPUConfiguration  AdditionalInformation OPTIONAL
}

ProtectionUnits ::= SET OF ProtectionResource

RemoveProtectionError ::= OperatorCommandPresent

RemovedProtectionUnits ::= SET OF ObjectInstance

RevertiveInformation ::= SEQUENCE {
  revertive          BOOLEAN,
  waitToRestoreTime  INTEGER OPTIONAL
}

UnsupportedProtConfiguration ::= ENUMERATED {
  notSupportedProtConfig(0), notSupportedPGType(1),
  notSupportedRevertiveMode(2), invalidWTRTime(3), invalidPriority(4),
  otherError(5)}

END -- end of SDHProtCoordASN1

-- Generated by Asnp, the ASN.1 pretty-printer of France Telecom R&D
