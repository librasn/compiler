-- Module h235Identity (H.350:04/2006)
-- See also ITU-T formal description search tool
-- See also the index of all ASN.1 assignments needed in this document

H235Identity {itu-t(0) recommendation(0) h(8) 350 1 cr(1) h235Identity(4)
  module(4)} DEFINITIONS ::=
BEGIN

-- h235Identity Object Schema
-- Schema for representing h235Identity Object in an LDAP Directory
-- Abstract
-- This document defines the schema for representing h235Identity
-- object in an LDAP directory [LDAPv3].  It defines schema elements
-- to represent an h235Identity object [h235Identity].
--                     .1 = Communication related work
--                     .1.4 = h235Identity
--                     .1.4.1 = attributes
--                     .1.4.2 = objectclass
--                     .1.4.3 = syntax
IMPORTS
  -- from ITU-T Rec. H.350
  h350-cr
    FROM CommURI {itu-t(0) recommendation(0) h(8) 350 1 cr(1) commURI(1)
      module(4)}
  -- from ITU-T Rec. X.501 | ISO/IEC 9594-2
  ATTRIBUTE, OBJECT-CLASS, top
    FROM InformationFramework {joint-iso-itu-t ds(5) module(1)
      informationFramework(1) 4}
  -- from ITU-T Rec. X.509 | ISO/IEC 9594-8
  userCertificate, cACertificate, authorityRevocationList,
    certificateRevocationList, crossCertificatePair
    FROM AuthenticationFramework {joint-iso-itu-t ds(5) module(1)
      authenticationFramework(7) 4}
  -- from ITU-T Rec. X.520 | ISO/IEC 9594-6
  DirectoryString{}, caseIgnoreMatch, caseIgnoreSubstringsMatch,
    octetStringMatch
    FROM SelectedAttributeTypes {joint-iso-itu-t ds(5) module(1)
      selectedAttributeTypes(5) 4};

-- Attribute Type Definitions
--   The following attribute types are defined in this document:
--        h235IdentityEndpointID
--        h235IdentityPassword
h235IdentityEndpointID ATTRIBUTE ::= {
  WITH SYNTAX               DirectoryString {256}
  EQUALITY MATCHING RULE    caseIgnoreMatch
  SUBSTRINGS MATCHING RULE  caseIgnoreSubstringsMatch
  ID                        {at  1}
}

h235IdentityPassword ATTRIBUTE ::= {
  WITH SYNTAX             OCTET STRING
  EQUALITY MATCHING RULE  octetStringMatch
  ID                      {at  2}
}

-- Object Class Definitions
--    The following object class is defined in this document:
--       h235Identity
h235Identity OBJECT-CLASS ::= {
  SUBCLASS OF  {top}
  MAY CONTAIN
    {h235IdentityEndpointID | h235IdentityPassword | userCertificate |
      cACertificate | authorityRevocationList | certificateRevocationList |
      crossCertificatePair}
  ID           {oc  1}
}

h235-Id OBJECT IDENTIFIER ::= {h350-cr h235-Id(4)}

at OBJECT IDENTIFIER ::= {h235-Id at(1)}

oc OBJECT IDENTIFIER ::= {h235-Id oc(2)}

END -- end of ASN.1

-- Generated by Asnp, the ASN.1 pretty-printer of France Telecom R&D
