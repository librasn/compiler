-- Module McidOperations (Q.951.7:06/1997)
-- See also ITU-T Q.951.7 (06/1997)
-- See also the index of all ASN.1 assignments needed in this document

McidOperations {itu-t recommendation q 951 mcid(7) operations-and-errors(1)}
DEFINITIONS ::=
BEGIN

EXPORTS mcidRequest;

IMPORTS
  OPERATION
    FROM Remote-Operations-Information-Objects {joint-iso-itu-t
      remote-operations(4) informationObjects(5) version1(0)}
  notAvailable, userNotSubscribed, invalidCallState, notIncomingCall,
    supplementaryServiceInteractionNotAllowed
    FROM General-Error-List {itu-t recommendation q 950 general-error-list(1)};

mcidRequest OPERATION ::= {
  ERRORS
    {notAvailable | userNotSubscribed | invalidCallState |
      supplementaryServiceInteractionNotAllowed | notIncomingCall}
  CODE    local:3
}

END

-- Generated by Asnp, the ASN.1 pretty-printer of France Telecom R&D
