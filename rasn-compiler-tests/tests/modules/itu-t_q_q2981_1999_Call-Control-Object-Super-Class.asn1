-- Module Call-Control-Object-Super-Class (Q.2981:12/1999)
-- See also ITU-T Q.2981 (12/1999)
-- See also the index of all ASN.1 assignments needed in this document

Call-Control-Object-Super-Class {itu-t recommendation q 2981
  call-control-object-super-class(4)} DEFINITIONS AUTOMATIC TAGS ::=
BEGIN

EXPORTS CALLCONTROLOBJECTCLASS;

CALLCONTROLOBJECTCLASS ::= CLASS {
  &ArgumentType           OPTIONAL,
  &argumentTypeOptional   BOOLEAN OPTIONAL,
  &objectClassIdentifier  OBJECT IDENTIFIER UNIQUE
}
WITH SYNTAX {
  [ARGUMENT &ArgumentType
   [OPTIONAL &argumentTypeOptional]]
  IDENTIFIER &objectClassIdentifier
}

END -- Call-Control-Object-Super-Class

-- Generated by Asnp, the ASN.1 pretty-printer of France Telecom R&D
