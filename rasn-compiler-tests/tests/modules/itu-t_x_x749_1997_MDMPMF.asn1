-- Module MDMPMF (X.749:08/1997)
-- See also ITU-T X.749 (08/1997)
-- See also the index of all ASN.1 assignments needed in this document

MDMPMF {joint-iso-itu-t ms(9) function(2) part19(19) asn1Module(2) 1}
DEFINITIONS ::=
BEGIN

mdmpmfFunctionalUnitPackage OBJECT IDENTIFIER ::=
  {joint-iso-itu-t ms(9) function(2) part19(19) functionalUnitPackage(1)}

mdmpmfManagedObject OBJECT IDENTIFIER ::=
  {joint-iso-itu-t ms(9) function(2) part19(19) managedObject(3)}

mdmpmfPackage OBJECT IDENTIFIER ::=
  {joint-iso-itu-t ms(9) function(2) part19(19) package(4)}

mdmpmfParameter OBJECT IDENTIFIER ::=
  {joint-iso-itu-t ms(9) function(2) part19(19) parameter(5)}

mdmpmfNameBinding OBJECT IDENTIFIER ::=
  {joint-iso-itu-t ms(9) function(2) part19(19) nameBinding(6)}

mdmpmfAttribute OBJECT IDENTIFIER ::=
  {joint-iso-itu-t ms(9) function(2) part19(19) attribute(7)}

mdmpmfAction OBJECT IDENTIFIER ::=
  {joint-iso-itu-t ms(9) function(2) part19(19) action(8)}

mdmpmfNotification OBJECT IDENTIFIER ::=
  {joint-iso-itu-t ms(9) function(2) part19(19) notification(10)}

mdmpmfRelationship OBJECT IDENTIFIER ::=
  {joint-iso-itu-t ms(9) function(2) part19(19) relationship(11)}

mdmpmfRelationshipMapping OBJECT IDENTIFIER ::=
  {joint-iso-itu-t ms(9) function(2) part19(19) relationshipMapping(12)}

--
--		The following arcs support the defined policy classes.
--
assertedValueIdentifier OBJECT IDENTIFIER ::=
  {joint-iso-itu-t ms(9) function(2) part19(19) assertedValueIdentifier(13)}

operationType OBJECT IDENTIFIER ::=
  {joint-iso-itu-t ms(9) function(2) part19(19) assertedValueIdentifier(13)
   operationType(1)}

errorType OBJECT IDENTIFIER ::=
  {joint-iso-itu-t ms(9) function(2) part19(19) assertedValueIdentifier(13)
   errorType(2)}

notificationType OBJECT IDENTIFIER ::=
  {joint-iso-itu-t ms(9) function(2) part19(19) assertedValueIdentifier(13)
   notificationType(3)}

actionType OBJECT IDENTIFIER ::=
  {joint-iso-itu-t ms(9) function(2) part19(19) assertedValueIdentifier(13)
   actionType(4)}

eventInfo OBJECT IDENTIFIER ::=
  {joint-iso-itu-t ms(9) function(2) part19(19) assertedValueIdentifier(13)
   eventInfo(5)}

eventReply OBJECT IDENTIFIER ::=
  {joint-iso-itu-t ms(9) function(2) part19(19) assertedValueIdentifier(13)
   eventReply(6)}

actionInfo OBJECT IDENTIFIER ::=
  {joint-iso-itu-t ms(9) function(2) part19(19) assertedValueIdentifier(13)
   actionInfo(7)}

actionReply OBJECT IDENTIFIER ::=
  {joint-iso-itu-t ms(9) function(2) part19(19) assertedValueIdentifier(13)
   actionReply(8)}

OneToOne ::= INTEGER(1..1)

END

-- Generated by Asnp, the ASN.1 pretty-printer of France Telecom R&D
