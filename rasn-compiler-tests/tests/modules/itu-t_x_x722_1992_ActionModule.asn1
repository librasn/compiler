-- Module ActionModule (X.722:01/1992)
-- See also ITU-T X.722 (01/1992)
-- See also the index of all ASN.1 assignments needed in this document

ActionModule {joint-iso-itu-t ms(9) smi(3) part4(4) asn1Module(2) actions(2)}
DEFINITIONS ::=
BEGIN

IMPORTS
  OperationalState, ManagementExtension
    FROM Attribute-ASN1Module {joint-iso-itu-t ms(9) smi(3) part2(2)
      asn1Module(2) 1};

ActivateReply ::= SEQUENCE {
  operationalStatus  [0]  OperationalState,
  responseCode
    [1]  INTEGER {successResponse(0), serviceProviderErrorResponse(1)},
  responseParams     [2]  SET OF ManagementExtension OPTIONAL
}

END

-- Generated by Asnp, the ASN.1 pretty-printer of France Telecom R&D
