-- Module CIRCUIT-STATUS-MAP (H.460.3:11/2002)
-- See also ITU-T H.460.3 (11/2002)
-- See also the index of all ASN.1 assignments needed in this document

CIRCUIT-STATUS-MAP DEFINITIONS AUTOMATIC TAGS ::=
BEGIN

IMPORTS CircuitIdentifier
          FROM H323-MESSAGES;

CircuitStatus ::= SEQUENCE -- root for Circuit Status Map ASN.1
                   {
  circuitStatusMap  SEQUENCE OF CircuitStatusMap OPTIONAL,
  ...
}

CircuitStatusMap ::= SEQUENCE {
  statusType     CircuitStatusType,
  baseCircuitID  CircuitIdentifier,
  range          INTEGER(0..4095),
  status         OCTET STRING,
  ...
}

CircuitStatusType ::= CHOICE {
  serviceStatus  NULL, -- status: 0 = out-of-service, 1 = in-service
  busyStatus     NULL, -- status: 0 = free, 1 = in-use
  ...
}

END

-- Generated by Asnp, the ASN.1 pretty-printer of France Telecom R&D
