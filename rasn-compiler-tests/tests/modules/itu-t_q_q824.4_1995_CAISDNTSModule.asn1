-- Module CAISDNTSModule (Q.824.4:10/1995)
-- See also ITU-T Q.824.4 (10/1995)
-- See also the index of all ASN.1 assignments needed in this document

CAISDNTSModule {itu-t(0) recommendation(0) q(17) ca(824) dot(127) isdnts(4)
  informationModel(0) ans1Modules(2) cAISDNTSModule(0)} DEFINITIONS IMPLICIT
TAGS ::=
BEGIN

-- EXPORTS Everything;
IMPORTS
  ObjectInstance, ObjectClass
    FROM CMIP-1 {joint-iso-itu-t ms(9) cmip(1) modules(0) protocol(3)}
  AlarmStatus, Boolean, NameType, ObjectList, Pointer, PointerOrNull
    FROM ASN1DefinedTypesModule {itu-t recommendation m(13) gnm(3100)
      informationModel(0) asn1Modules(2) asn1DefinedTypesModule(0)};

q824-4InformationModel OBJECT IDENTIFIER ::=
  {itu-t(0) recommendation(0) q(17) ca(824) dot(127) isdnts(4)
   informationModel(0)}

cAISDNTSObjectClass OBJECT IDENTIFIER ::=
  {q824-4InformationModel managedObjectClass(3)}

cAISDNTSPackage OBJECT IDENTIFIER ::= {q824-4InformationModel package(4)}

cAISDNTSAttribute OBJECT IDENTIFIER ::= {q824-4InformationModel attribute(7)}

cAISDNTSNameBinding OBJECT IDENTIFIER ::=
  {q824-4InformationModel nameBinding(6)}

cAISDNTSAction OBJECT IDENTIFIER ::= {q824-4InformationModel action(9)}

-- default value definitions
false Boolean ::= FALSE

true Boolean ::= TRUE

null NULL ::= NULL

one INTEGER ::= 1

zero INTEGER ::= 0

minusOne INTEGER ::= -1

emptySet NULL ::= NULL

-- supporting productions
DetailedNumber ::= SEQUENCE {
  incoming  INTEGER,
  outgoing  INTEGER,
  bothWay   INTEGER
}

MaxNumber ::= CHOICE {detailed  [1]  DetailedNumber,
                      total     [2]  INTEGER
}

TelefaxClass ::= ENUMERATED {
  telefaxClassI(1), telefaxClassII(2), telefaxClassIII(3)}

TeletexMode ::= BIT STRING {
  virtualDialogueMode(1), processableMode(2), mixedMode(3)}

END -- Type definitions

-- Generated by Asnp, the ASN.1 pretty-printer of France Telecom R&D
