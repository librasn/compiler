-- Module Q824-7Asn1Module (Q.824.7:02/2000)
-- See also ITU-T Q.824.7 (02/2000)
-- See also the index of all ASN.1 assignments needed in this document

Q824-7Asn1Module {itu-t(0) recommendation(0) q(17) ca(824) dot(127) ebs(7)
  q824-7informationModel(0) asn1Modules(2) asn1DefinedTypesModule(0)}
DEFINITIONS IMPLICIT TAGS ::=
BEGIN

-- EXPORTS everything
IMPORTS
  ObjectInstance
    FROM CMIP-1 {joint-iso-itu-t ms(9) cmip(1) modules(0) protocol(3)}
  VciValue
    FROM AtmMIBMod {itu-t(0) recommendation(0) i(9) atmm(751)
      informationModel(0) asn1Module(2) atm(0)}
  NameType, PointerOrNull
    FROM ASN1DefinedTypesModule {itu-t recommendation m 3100
      informationModel(0) asn1Modules(2) asn1DefinedTypesModule(0)}
  DirectoryNumber, VpciValue
    FROM Q824-6ASN1DefinedTypesModule {itu-t(0) recommendation(0) q(17)
      ca(824) dot(127) bsm(6) informationModel(0) asn1Module(2)
      asn1TypeModule(0)}; -- end of imports

-- start of object identifier definitions
q824-7InformationModel OBJECT IDENTIFIER ::=
  {itu-t(0) recommendation(0) q(17) ca(824) dot(127) ebs(7)
   q824-7informationModel(0)}

q824-7StandardSpecificExtension OBJECT IDENTIFIER ::=
  {itu-t(0) recommendation(0) q(17) ca(824) dot(127) ebs(7)
   q824-7informationModel(0) q824-7StandardSpecificExtension(0)}

q824-7ManagedObjectClass OBJECT IDENTIFIER ::=
  {itu-t(0) recommendation(0) q(17) ca(824) dot(127) ebs(7)
   q824-7informationModel(0) q824-7ManagedObjectClass(3)}

q824-7Package OBJECT IDENTIFIER ::=
  {itu-t(0) recommendation(0) q(17) ca(824) dot(127) ebs(7)
   q824-7informationModel(0) q824-7Package(4)}

q824-7NameBinding OBJECT IDENTIFIER ::=
  {itu-t(0) recommendation(0) q(17) ca(824) dot(127) ebs(7)
   q824-7informationModel(0) q824-7NameBinding(6)}

q824-7Attribute OBJECT IDENTIFIER ::=
  {itu-t(0) recommendation(0) q(17) ca(824) dot(127) ebs(7)
   q824-7informationModel(0) q824-7Attribute(7)}

q824-7Action OBJECT IDENTIFIER ::=
  {itu-t(0) recommendation(0) q(17) ca(824) dot(127) ebs(7)
   q824-7informationModel(0) q824-7Action(9)}

q824-7Notification OBJECT IDENTIFIER ::=
  {itu-t(0) recommendation(0) q(17) ca(824) dot(127) ebs(7)
   q824-7informationModel(0) q824-7Notification(10)}

-- end of object identifier definitions
-- other ASN1 definitions in alphabetical order
CalledPartySelectionType ::= ENUMERATED {anyValue(0), requiredValue(1)
}

EgressBandwidth ::= INTEGER

IngressBandwidth ::= INTEGER

RetryInterval ::= INTEGER(0..3600)

RetryLimit ::= INTEGER

SoftPvcCause ::= SEQUENCE {
  softPvcCauseIndication  [0]  SoftPvcCauseIndication,
  softPvcCauseValue       [1]  SoftPvcCauseValue
}

SoftPvcCauseIndication ::= ENUMERATED {
  noCause(0), -- no failure detected
  firstCause(1), -- failure detected, trying to re-establish
  lastCause(2) -- not or no longer attempting to re-establish--}

SoftPvcCauseValue ::= INTEGER(0..127)

SwitchingModes ::= SEQUENCE {
  channelSwitching  BOOLEAN,
  pathSwitching     BOOLEAN
}

switchingModesDefault SwitchingModes ::=
  {channelSwitching TRUE, pathSwitching FALSE}

VpiRange ::= SEQUENCE {lowerLimit  INTEGER,
                       upperLimit  INTEGER
}

VpPoolAndVpciPtrList ::=
  SET OF SEQUENCE {vpPool          ObjectInstance,
                   lowerVpciLimit  VpciValue}

END -- of Q824-7Asn1Module

-- Generated by Asnp, the ASN.1 pretty-printer of France Telecom R&D
