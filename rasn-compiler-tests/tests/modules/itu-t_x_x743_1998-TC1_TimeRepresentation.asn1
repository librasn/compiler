-- Module TimeRepresentation (X.743:06/1998)
-- See also ITU-T X.743 (1998) Technical Cor. 1 (03/2001)
-- See also the index of all ASN.1 assignments needed in this document

-- <ASN1.Version 1990,1994 TimeRepresentation
-- {joint-iso-itu-t ms(9) function(2) part20(20) asn1Module(2)
-- timeRepresentation(2) }>
TimeRepresentation {joint-iso-itu-t ms(9) function(2) part20(20) asn1Module(2)
  timeRepresentation(2)} DEFINITIONS ::=
BEGIN

Epochs ::= INTEGER(-128..127)

Seconds ::= INTEGER(0..4294967295)

Nanoseconds ::= INTEGER(0..999999999)

MaximumErrorInNanoseconds ::= INTEGER {noEstimate(281474976710655)
}(0..281474976710655)

CumLeapSeconds ::= INTEGER(0..65536)

TimeZone ::= INTEGER {unknown(781)}(-780..781)

-- Represents minutes east of GMT.
TimeStamp ::= SEQUENCE {
  epoch         Epochs,
  second        Seconds,
  nanosecond    Nanoseconds,
  maximumError  MaximumErrorInNanoseconds
}

ClockTime ::= SEQUENCE {
  time           TimeStamp,
  leapSeconds    CumLeapSeconds,
  localTimeZone  TimeZone
}

TimeInterval ::= SEQUENCE {
  epochs       Epochs,
  seconds      Seconds,
  nanoseconds  Nanoseconds
}

TimeDifference ::= SEQUENCE {
  sign          ENUMERATED {positive(0), negative(1)},
  epochs        Epochs,
  seconds       Seconds,
  nanoseconds   Nanoseconds,
  maximumError  MaximumErrorInNanoseconds
}

END

-- Generated by Asnp, the ASN.1 pretty-printer of France Telecom R&D
