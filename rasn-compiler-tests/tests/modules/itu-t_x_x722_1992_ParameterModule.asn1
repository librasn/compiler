-- Module ParameterModule (X.722:01/1992)
-- See also ITU-T X.722 (01/1992)
-- See also the index of all ASN.1 assignments needed in this document

ParameterModule {joint-iso-itu-t ms(9) smi(3) part4(4) asn1Module(2)
  parameters(3)} DEFINITIONS ::=
BEGIN

ErrorInfo1 ::= INTEGER

ServiceProviderErrorResponseReason ::= ENUMERATED {
  insufficientResources(0), providerDoesNotExist(1), providerNotAvailable(2),
  requiredServiceNotAvailable(3)}

PDUString ::= OCTET STRING

END

-- Generated by Asnp, the ASN.1 pretty-printer of France Telecom R&D
