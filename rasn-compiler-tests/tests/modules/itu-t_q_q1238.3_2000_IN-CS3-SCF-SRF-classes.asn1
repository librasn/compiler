-- Module IN-CS3-SCF-SRF-classes (Q.1238.3:06/2000)
-- See also ITU-T Q.1238.3 (06/2000)
-- See also the index of all ASN.1 assignments needed in this document

IN-CS3-SCF-SRF-classes {itu-t recommendation q 1238 modules(1)
  in-cs3-scf-srf-classes(11) version1(0)} DEFINITIONS ::=
BEGIN

IMPORTS
  id-package-emptyConnection, id-rosObject-srf, id-rosObject-ssf,
    ros-InformationObjects, ros-UsefulDefinitions, scf-srf-Protocol,
    scf-srf-datatypes, ssf-scf-datatypes
    FROM IN-CS3-object-identifiers {itu-t recommendation q 1238 modules(1)
      in-cs3-object-identifiers(0) version1(0)}
  ROS-OBJECT-CLASS, CONTRACT, OPERATION-PACKAGE, Code, OPERATION,
    CONNECTION-PACKAGE
    FROM Remote-Operations-Information-Objects {joint-iso-itu-t
      remote-operations(4) informationObjects(5) version1(0)}
  emptyBind, emptyUnbind
    FROM Remote-Operations-Useful-Definitions {joint-iso-itu-t
      remote-operations(4) useful-definitions(7) version1(0)};

UISCRIPT ::= CLASS {
  &SpecificInfo  OPTIONAL,
  &Result        OPTIONAL,
  &id            Code
}
WITH SYNTAX {
  [WITH-SPECIFICINFO &SpecificInfo]
  [WITH-RESULT &Result]
  IDENTIFIED BY &id
}

-- SpecificInfo is used for ScriptRun and ScriptInformation and ScriptClose
--Result is used for ScritEvent
firstScript UISCRIPT ::= {IDENTIFIED BY  local:1
}

-- firstScript is just an example.
SupportedUIScripts UISCRIPT ::=
  {firstScript, ...
  --full set of User Interaction script
  }

-- SupportedUIScripts is the full set of User Interaction scripts.
SCF-SRF-BOUNDS ::= CLASS {
  &minAttributesLength           INTEGER OPTIONAL,
  &maxAttributesLength           INTEGER OPTIONAL,
  &minMailBoxIDLength            INTEGER OPTIONAL,
  &maxMailBoxIDLength            INTEGER OPTIONAL,
  &minMessageContentLength       INTEGER OPTIONAL,
  &maxMessageContentLength       INTEGER OPTIONAL,
  &minReceivedInformationLength  INTEGER OPTIONAL,
  &maxReceivedInformationLength  INTEGER OPTIONAL,
  &maxRecordingTime              INTEGER OPTIONAL,
  &numOfMessageIDs               INTEGER OPTIONAL,
  &maxRecordedMessageUnits       INTEGER OPTIONAL,
  &maxVariableParts              INTEGER OPTIONAL
}
WITH SYNTAX {
  [MINIMUM-FOR-ATTRIBUTES &minAttributesLength]
  [MAXIMUM-FOR-ATTRIBUTES &maxAttributesLength]
  [MINIMUM-FOR-MAIL-BOX-ID &minMailBoxIDLength]
  [MAXIMUM-FOR-MAIL-BOX-ID &maxMailBoxIDLength]
  [MINIMUM-FOR-MESSAGE-CONTENT &minMessageContentLength]
  [MAXIMUM-FOR-MESSAGE-CONTENT &maxMessageContentLength]
  [MINIMUM-FOR-RECEIVED-INFORMATION &minReceivedInformationLength]
  [MAXIMUM-FOR-RECEIVED-INFORMATION &maxReceivedInformationLength]
  [MAXIMUM-FOR-RECORDING-TIME &maxRecordingTime]
  [NUM-OF-MESSAGE-IDS &numOfMessageIDs]
  [MAXIMUM-FOR-RECORDED-MESSAGE-UNITS &maxRecordedMessageUnits]
  [NUM-OF-VARIABLE-PARTS &maxVariableParts]
}

-- The following instance of the parameter bound is just an example
networkSpecificSCFSRFBoundSet SCF-SRF-BOUNDS ::= {
  MINIMUM-FOR-ATTRIBUTES              1
  MAXIMUM-FOR-ATTRIBUTES              5
  MINIMUM-FOR-MAIL-BOX-ID             1
  MAXIMUM-FOR-MAIL-BOX-ID             5
  MINIMUM-FOR-MESSAGE-CONTENT         1
  MAXIMUM-FOR-MESSAGE-CONTENT         5
  MINIMUM-FOR-RECEIVED-INFORMATION    1
  MAXIMUM-FOR-RECEIVED-INFORMATION    5
  MAXIMUM-FOR-RECORDING-TIME          5
  NUM-OF-MESSAGE-IDS                  2
  MAXIMUM-FOR-RECORDED-MESSAGE-UNITS  5
  NUM-OF-VARIABLE-PARTS               5 -- must be 5 or

-- greater.
}

END

-- Generated by Asnp, the ASN.1 pretty-printer of France Telecom R&D
