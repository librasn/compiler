-- Module H4501-Supplementary-ServiceAPDU-Structure (H.450.1:02/1998)
-- See also ITU-T H.450.1 (02/1998)
-- See also the index of all ASN.1 assignments needed in this document

H4501-Supplementary-ServiceAPDU-Structure {itu-t recommendation h 450
  1 version1(0) h4501-facility-information-structure(2)} DEFINITIONS AUTOMATIC
TAGS ::=
BEGIN

IMPORTS
  AliasAddress
    FROM H323-MESSAGES -- see H.225.0 V2

  OPERATION, ROS{}, InvokeId
    FROM Remote-Operations-Apdus {itu-t recommendation h 450 1 version1(0)
      remote-operations-apdus(11)};

H4501SupplementaryService ::= SEQUENCE {
  networkFacilityExtension  NetworkFacilityExtension OPTIONAL, -- see 8.1
  interpretationApdu        InterpretationApdu OPTIONAL, -- see 8.2
  serviceApdu               ServiceApdus, -- H.450.x supplementary services
  ...
}

NetworkFacilityExtension ::= SEQUENCE {
  sourceEntity              EntityType,
  sourceEntityAddress       AddressInformation OPTIONAL,
  destinationEntity         EntityType,
  destinationEntityAddress  AddressInformation OPTIONAL,
  ...
}

EntityType ::= CHOICE {endpoint   NULL,
                       anyEntity  NULL,
                       ...
}

AddressInformation ::= AliasAddress

InterpretationApdu ::= CHOICE {
  discardAnyUnrecognizedInvokePdu       NULL,
  clearCallIfAnyInvokePduNotRecognized  NULL,
  -- this value also applies to Call independent signalling connections
  rejectAnyUnrecognizedInvokePdu        NULL,
  -- this coding is implied by the absence of an interpretation APDU.
  ...
}

ServiceApdus ::= CHOICE {
  rosApdus
    SEQUENCE SIZE (1..MAX) OF
      ROS{{InvokeIdSet}, {OperationSet}, {OperationSet}},
  -- see 8.3; other alternatives may be defined in future versions
  ...
}

InvokeIdSet INTEGER ::= {InvokeIDs, ...}

InvokeIDs ::= INTEGER(0..65535)

OperationSet OPERATION ::=
  {...}

-- actual values are defined by individual supplementary service specifications
-- (e.g. H.450.x or manufacturer specific)
END -- of H4501- Supplementary-ServiceAPDU-Structure

-- Generated by Asnp, the ASN.1 pretty-printer of France Telecom R&D
