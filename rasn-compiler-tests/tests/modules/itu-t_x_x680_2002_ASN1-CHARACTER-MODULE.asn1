-- CAUSES STACK OVERFLOW







-- -- Module ASN1-CHARACTER-MODULE (X.680:07/2002)
-- -- See also ITU-T X.680 (07/2002)
-- -- See also the index of all ASN.1 assignments needed in this document

-- ASN1-CHARACTER-MODULE {joint-iso-itu-t asn1(1) specification(0) modules(0)
--   iso10646(0)} DEFINITIONS ::=
-- BEGIN

-- -- All of the value references and type references defined within this
-- -- module are implicitly exported, and are available for import by
-- -- any module
-- -- ISO 646 control characters
-- nul IA5String ::=
--   {0, 0}

-- soh IA5String ::= {0, 1}

-- stx IA5String ::= {0, 2}

-- etx IA5String ::= {0, 3}

-- eot IA5String ::= {0, 4}

-- enq IA5String ::= {0, 5}

-- ack IA5String ::= {0, 6}

-- bel IA5String ::= {0, 7}

-- bs IA5String ::= {0, 8}

-- ht IA5String ::= {0, 9}

-- lf IA5String ::= {0, 10}

-- vt IA5String ::= {0, 11}

-- ff IA5String ::= {0, 12}

-- cr IA5String ::= {0, 13}

-- so IA5String ::= {0, 14}

-- si IA5String ::= {0, 15}

-- dle IA5String ::= {1, 0}

-- dc1 IA5String ::= {1, 1}

-- dc2 IA5String ::= {1, 2}

-- dc3 IA5String ::= {1, 3}

-- dc4 IA5String ::= {1, 4}

-- nak IA5String ::= {1, 5}

-- syn IA5String ::= {1, 6}

-- etb IA5String ::= {1, 7}

-- can IA5String ::= {1, 8}

-- em IA5String ::= {1, 9}

-- sub IA5String ::= {1, 10}

-- esc IA5String ::= {1, 11}

-- is4 IA5String ::= {1, 12}

-- is3 IA5String ::= {1, 13}

-- is2 IA5String ::= {1, 14}

-- is1 IA5String ::= {1, 15}

-- del IA5String ::= {7, 15}

-- -- Characters defined in ISO/IEC 10646-1 Basic Multilingual Plane
-- null BMPString ::=
--   {0, 0, 0, 0}

-- startOfHeading BMPString ::= {0, 0, 0, 1}

-- startOfText BMPString ::= {0, 0, 0, 2}

-- endOfText BMPString ::= {0, 0, 0, 3}

-- endOfTransmission BMPString ::= {0, 0, 0, 4}

-- enquiry BMPString ::= {0, 0, 0, 5}

-- acknowledge BMPString ::= {0, 0, 0, 6}

-- bell BMPString ::= {0, 0, 0, 7}

-- backspace BMPString ::= {0, 0, 0, 8}

-- characterTabulation BMPString ::= {0, 0, 0, 9}

-- lineFeed BMPString ::= {0, 0, 0, 10}

-- lineTabulation BMPString ::= {0, 0, 0, 11}

-- formFeed BMPString ::= {0, 0, 0, 12}

-- carriageReturn BMPString ::= {0, 0, 0, 13}

-- shiftOut BMPString ::= {0, 0, 0, 14}

-- shiftIn BMPString ::= {0, 0, 0, 15}

-- dataLinkEscape BMPString ::= {0, 0, 0, 16}

-- deviceControlOne BMPString ::= {0, 0, 0, 17}

-- deviceControlTwo BMPString ::= {0, 0, 0, 18}

-- deviceControlThree BMPString ::= {0, 0, 0, 19}

-- deviceControlFour BMPString ::= {0, 0, 0, 20}

-- negativeAcknowledge BMPString ::= {0, 0, 0, 21}

-- synchronousIdle BMPString ::= {0, 0, 0, 22}

-- endOfTransmissionBlock BMPString ::= {0, 0, 0, 23}

-- cancel BMPString ::= {0, 0, 0, 24}

-- endOfMedium BMPString ::= {0, 0, 0, 25}

-- substitute BMPString ::= {0, 0, 0, 26}

-- escape BMPString ::= {0, 0, 0, 27}

-- informationSeparatorFour BMPString ::= {0, 0, 0, 28}

-- informationSeparatorThree BMPString ::= {0, 0, 0, 29}

-- informationSeparatorTwo BMPString ::= {0, 0, 0, 30}

-- informationSeparatorOne BMPString ::= {0, 0, 0, 31}

-- space BMPString ::= {0, 0, 0, 32}

-- exclamationMark BMPString ::= {0, 0, 0, 33}

-- quotationMark BMPString ::= {0, 0, 0, 34}

-- numberSign BMPString ::= {0, 0, 0, 35}

-- dollarSign BMPString ::= {0, 0, 0, 36}

-- percentSign BMPString ::= {0, 0, 0, 37}

-- ampersand BMPString ::= {0, 0, 0, 38}

-- apostrophe BMPString ::= {0, 0, 0, 39}

-- leftParenthesis BMPString ::= {0, 0, 0, 40}

-- rightParenthesis BMPString ::= {0, 0, 0, 41}

-- asterisk BMPString ::= {0, 0, 0, 42}

-- plusSign BMPString ::= {0, 0, 0, 43}

-- comma BMPString ::= {0, 0, 0, 44}

-- hyphen-minus BMPString ::= {0, 0, 0, 45}

-- fullStop BMPString ::= {0, 0, 0, 46}

-- solidus BMPString ::= {0, 0, 0, 47}

-- digitZero BMPString ::= {0, 0, 0, 48}

-- digitOne BMPString ::= {0, 0, 0, 49}

-- digitTwo BMPString ::= {0, 0, 0, 50}

-- digitThree BMPString ::= {0, 0, 0, 51}

-- digitFour BMPString ::= {0, 0, 0, 52}

-- digitFive BMPString ::= {0, 0, 0, 53}

-- digitSix BMPString ::= {0, 0, 0, 54}

-- digitSeven BMPString ::= {0, 0, 0, 55}

-- digitEight BMPString ::= {0, 0, 0, 56}

-- digitNine BMPString ::= {0, 0, 0, 57}

-- colon BMPString ::= {0, 0, 0, 58}

-- semicolon BMPString ::= {0, 0, 0, 59}

-- less-thanSign BMPString ::= {0, 0, 0, 60}

-- equalsSign BMPString ::= {0, 0, 0, 61}

-- greater-thanSign BMPString ::= {0, 0, 0, 62}

-- questionMark BMPString ::= {0, 0, 0, 63}

-- commercialAt BMPString ::= {0, 0, 0, 64}

-- latinCapitalLetterA BMPString ::= {0, 0, 0, 65}

-- latinCapitalLetterB BMPString ::= {0, 0, 0, 66}

-- latinCapitalLetterC BMPString ::= {0, 0, 0, 67}

-- latinCapitalLetterD BMPString ::= {0, 0, 0, 68}

-- latinCapitalLetterE BMPString ::= {0, 0, 0, 69}

-- latinCapitalLetterF BMPString ::= {0, 0, 0, 70}

-- latinCapitalLetterG BMPString ::= {0, 0, 0, 71}

-- latinCapitalLetterH BMPString ::= {0, 0, 0, 72}

-- latinCapitalLetterI BMPString ::= {0, 0, 0, 73}

-- latinCapitalLetterJ BMPString ::= {0, 0, 0, 74}

-- latinCapitalLetterK BMPString ::= {0, 0, 0, 75}

-- latinCapitalLetterL BMPString ::= {0, 0, 0, 76}

-- latinCapitalLetterM BMPString ::= {0, 0, 0, 77}

-- latinCapitalLetterN BMPString ::= {0, 0, 0, 78}

-- latinCapitalLetterO BMPString ::= {0, 0, 0, 79}

-- latinCapitalLetterP BMPString ::= {0, 0, 0, 80}

-- latinCapitalLetterQ BMPString ::= {0, 0, 0, 81}

-- latinCapitalLetterR BMPString ::= {0, 0, 0, 82}

-- latinCapitalLetterS BMPString ::= {0, 0, 0, 83}

-- latinCapitalLetterT BMPString ::= {0, 0, 0, 84}

-- latinCapitalLetterU BMPString ::= {0, 0, 0, 85}

-- latinCapitalLetterV BMPString ::= {0, 0, 0, 86}

-- latinCapitalLetterW BMPString ::= {0, 0, 0, 87}

-- latinCapitalLetterX BMPString ::= {0, 0, 0, 88}

-- latinCapitalLetterY BMPString ::= {0, 0, 0, 89}

-- latinCapitalLetterZ BMPString ::= {0, 0, 0, 90}

-- leftSquareBracket BMPString ::= {0, 0, 0, 91}

-- reverseSolidus BMPString ::= {0, 0, 0, 92}

-- rightSquareBracket BMPString ::= {0, 0, 0, 93}

-- circumflexAccent BMPString ::= {0, 0, 0, 94}

-- lowLine BMPString ::= {0, 0, 0, 95}

-- graveAccent BMPString ::= {0, 0, 0, 96}

-- latinSmallLetterA BMPString ::= {0, 0, 0, 97}

-- latinSmallLetterB BMPString ::= {0, 0, 0, 98}

-- latinSmallLetterC BMPString ::= {0, 0, 0, 99}

-- latinSmallLetterD BMPString ::= {0, 0, 0, 100}

-- latinSmallLetterE BMPString ::= {0, 0, 0, 101}

-- latinSmallLetterF BMPString ::= {0, 0, 0, 102}

-- latinSmallLetterG BMPString ::= {0, 0, 0, 103}

-- latinSmallLetterH BMPString ::= {0, 0, 0, 104}

-- latinSmallLetterI BMPString ::= {0, 0, 0, 105}

-- latinSmallLetterJ BMPString ::= {0, 0, 0, 106}

-- latinSmallLetterK BMPString ::= {0, 0, 0, 107}

-- latinSmallLetterL BMPString ::= {0, 0, 0, 108}

-- latinSmallLetterM BMPString ::= {0, 0, 0, 109}

-- latinSmallLetterN BMPString ::= {0, 0, 0, 110}

-- latinSmallLetterO BMPString ::= {0, 0, 0, 111}

-- latinSmallLetterP BMPString ::= {0, 0, 0, 112}

-- latinSmallLetterQ BMPString ::= {0, 0, 0, 113}

-- latinSmallLetterR BMPString ::= {0, 0, 0, 114}

-- latinSmallLetterS BMPString ::= {0, 0, 0, 115}

-- latinSmallLetterT BMPString ::= {0, 0, 0, 116}

-- latinSmallLetterU BMPString ::= {0, 0, 0, 117}

-- latinSmallLetterV BMPString ::= {0, 0, 0, 118}

-- latinSmallLetterW BMPString ::= {0, 0, 0, 119}

-- latinSmallLetterX BMPString ::= {0, 0, 0, 120}

-- latinSmallLetterY BMPString ::= {0, 0, 0, 121}

-- latinSmallLetterZ BMPString ::= {0, 0, 0, 122}

-- leftCurlyBracket BMPString ::= {0, 0, 0, 123}

-- verticalLine BMPString ::= {0, 0, 0, 124}

-- rightCurlyBracket BMPString ::= {0, 0, 0, 125}

-- tilde BMPString ::= {0, 0, 0, 126}

-- delete BMPString ::= {0, 0, 0, 127}

-- breakPermittedHere BMPString ::= {0, 0, 0, 130}

-- noBreakHere BMPString ::= {0, 0, 0, 131}

-- nextLine BMPString ::= {0, 0, 0, 133}

-- startOfSelectedArea BMPString ::= {0, 0, 0, 134}

-- endOfSelectedArea BMPString ::= {0, 0, 0, 135}

-- characterTabulationSet BMPString ::= {0, 0, 0, 136}

-- characterTabulationWithJustification BMPString ::= {0, 0, 0, 137}

-- lineTabulationSet BMPString ::= {0, 0, 0, 138}

-- partialLineForward BMPString ::= {0, 0, 0, 139}

-- partialLineBackward BMPString ::= {0, 0, 0, 140}

-- reverseLineFeed BMPString ::= {0, 0, 0, 141}

-- singleShiftTwo BMPString ::= {0, 0, 0, 142}

-- singleShiftThree BMPString ::= {0, 0, 0, 143}

-- deviceControlString BMPString ::= {0, 0, 0, 144}

-- privateUseOne BMPString ::= {0, 0, 0, 145}

-- privateUseTwo BMPString ::= {0, 0, 0, 146}

-- setTransmitState BMPString ::= {0, 0, 0, 147}

-- cancelCharacter BMPString ::= {0, 0, 0, 148}

-- messageWaiting BMPString ::= {0, 0, 0, 149}

-- startOfGuardedArea BMPString ::= {0, 0, 0, 150}

-- endOfGuardedArea BMPString ::= {0, 0, 0, 151}

-- startOfString BMPString ::= {0, 0, 0, 152}

-- singleCharacterIntroducer BMPString ::= {0, 0, 0, 154}

-- controlSequenceIntroducer BMPString ::= {0, 0, 0, 155}

-- stringTerminator BMPString ::= {0, 0, 0, 156}

-- operatingSystemCommand BMPString ::= {0, 0, 0, 157}

-- privacyMessage BMPString ::= {0, 0, 0, 158}

-- applicationProgramCommand BMPString ::= {0, 0, 0, 159}

-- no-breakSpace BMPString ::= {0, 0, 0, 160}

-- invertedExclamationMark BMPString ::= {0, 0, 0, 161}

-- centSign BMPString ::= {0, 0, 0, 162}

-- poundSign BMPString ::= {0, 0, 0, 163}

-- currencySign BMPString ::= {0, 0, 0, 164}

-- yenSign BMPString ::= {0, 0, 0, 165}

-- brokenBar BMPString ::= {0, 0, 0, 166}

-- sectionSign BMPString ::= {0, 0, 0, 167}

-- diaeresis BMPString ::= {0, 0, 0, 168}

-- copyrightSign BMPString ::= {0, 0, 0, 169}

-- feminineOrdinalIndicator BMPString ::= {0, 0, 0, 170}

-- left-pointingDoubleAngleQuotationMark BMPString ::= {0, 0, 0, 171}

-- notSign BMPString ::= {0, 0, 0, 172}

-- softHyphen BMPString ::= {0, 0, 0, 173}

-- registeredSign BMPString ::= {0, 0, 0, 174}

-- macron BMPString ::= {0, 0, 0, 175}

-- degreeSign BMPString ::= {0, 0, 0, 176}

-- plus-minusSign BMPString ::= {0, 0, 0, 177}

-- superscriptTwo BMPString ::= {0, 0, 0, 178}

-- superscriptThree BMPString ::= {0, 0, 0, 179}

-- acuteAccent BMPString ::= {0, 0, 0, 180}

-- microSign BMPString ::= {0, 0, 0, 181}

-- pilcrowSign BMPString ::= {0, 0, 0, 182}

-- middleDot BMPString ::= {0, 0, 0, 183}

-- cedilla BMPString ::= {0, 0, 0, 184}

-- superscriptOne BMPString ::= {0, 0, 0, 185}

-- masculineOrdinalIndicator BMPString ::= {0, 0, 0, 186}

-- right-pointingDoubleAngleQuotationMark BMPString ::= {0, 0, 0, 187}

-- vulgarFractionOneQuarter BMPString ::= {0, 0, 0, 188}

-- vulgarFractionOneHalf BMPString ::= {0, 0, 0, 189}

-- vulgarFractionThreeQuarters BMPString ::= {0, 0, 0, 190}

-- invertedQuestionMark BMPString ::= {0, 0, 0, 191}

-- latinCapitalLetterAWithGrave BMPString ::= {0, 0, 0, 192}

-- latinCapitalLetterAWithAcute BMPString ::= {0, 0, 0, 193}

-- latinCapitalLetterAWithCircumflex BMPString ::= {0, 0, 0, 194}

-- latinCapitalLetterAWithTilde BMPString ::= {0, 0, 0, 195}

-- latinCapitalLetterAWithDiaeresis BMPString ::= {0, 0, 0, 196}

-- latinCapitalLetterAWithRingAbove BMPString ::= {0, 0, 0, 197}

-- latinCapitalLetterAe BMPString ::= {0, 0, 0, 198}

-- latinCapitalLetterCWithCedilla BMPString ::= {0, 0, 0, 199}

-- latinCapitalLetterEWithGrave BMPString ::= {0, 0, 0, 200}

-- latinCapitalLetterEWithAcute BMPString ::= {0, 0, 0, 201}

-- latinCapitalLetterEWithCircumflex BMPString ::= {0, 0, 0, 202}

-- latinCapitalLetterEWithDiaeresis BMPString ::= {0, 0, 0, 203}

-- latinCapitalLetterIWithGrave BMPString ::= {0, 0, 0, 204}

-- latinCapitalLetterIWithAcute BMPString ::= {0, 0, 0, 205}

-- latinCapitalLetterIWithCircumflex BMPString ::= {0, 0, 0, 206}

-- latinCapitalLetterIWithDiaeresis BMPString ::= {0, 0, 0, 207}

-- latinCapitalLetterEth BMPString ::= {0, 0, 0, 208}

-- latinCapitalLetterNWithTilde BMPString ::= {0, 0, 0, 209}

-- latinCapitalLetterOWithGrave BMPString ::= {0, 0, 0, 210}

-- latinCapitalLetterOWithAcute BMPString ::= {0, 0, 0, 211}

-- latinCapitalLetterOWithCircumflex BMPString ::= {0, 0, 0, 212}

-- latinCapitalLetterOWithTilde BMPString ::= {0, 0, 0, 213}

-- latinCapitalLetterOWithDiaeresis BMPString ::= {0, 0, 0, 214}

-- multiplicationSign BMPString ::= {0, 0, 0, 215}

-- latinCapitalLetterOWithStroke BMPString ::= {0, 0, 0, 216}

-- latinCapitalLetterUWithGrave BMPString ::= {0, 0, 0, 217}

-- latinCapitalLetterUWithAcute BMPString ::= {0, 0, 0, 218}

-- latinCapitalLetterUWithCircumflex BMPString ::= {0, 0, 0, 219}

-- latinCapitalLetterUWithDiaeresis BMPString ::= {0, 0, 0, 220}

-- latinCapitalLetterYWithAcute BMPString ::= {0, 0, 0, 221}

-- latinCapitalLetterThorn BMPString ::= {0, 0, 0, 222}

-- latinSmallLetterSharpS BMPString ::= {0, 0, 0, 223}

-- latinSmallLetterAWithGrave BMPString ::= {0, 0, 0, 224}

-- latinSmallLetterAWithAcute BMPString ::= {0, 0, 0, 225}

-- latinSmallLetterAWithCircumflex BMPString ::= {0, 0, 0, 226}

-- latinSmallLetterAWithTilde BMPString ::= {0, 0, 0, 227}

-- latinSmallLetterAWithDiaeresis BMPString ::= {0, 0, 0, 228}

-- latinSmallLetterAWithRingAbove BMPString ::= {0, 0, 0, 229}

-- latinSmallLetterAe BMPString ::= {0, 0, 0, 230}

-- latinSmallLetterCWithCedilla BMPString ::= {0, 0, 0, 231}

-- latinSmallLetterEWithGrave BMPString ::= {0, 0, 0, 232}

-- latinSmallLetterEWithAcute BMPString ::= {0, 0, 0, 233}

-- latinSmallLetterEWithCircumflex BMPString ::= {0, 0, 0, 234}

-- latinSmallLetterEWithDiaeresis BMPString ::= {0, 0, 0, 235}

-- latinSmallLetterIWithGrave BMPString ::= {0, 0, 0, 236}

-- latinSmallLetterIWithAcute BMPString ::= {0, 0, 0, 237}

-- latinSmallLetterIWithCircumflex BMPString ::= {0, 0, 0, 238}

-- latinSmallLetterIWithDiaeresis BMPString ::= {0, 0, 0, 239}

-- latinSmallLetterEth BMPString ::= {0, 0, 0, 240}

-- latinSmallLetterNWithTilde BMPString ::= {0, 0, 0, 241}

-- latinSmallLetterOWithGrave BMPString ::= {0, 0, 0, 242}

-- latinSmallLetterOWithAcute BMPString ::= {0, 0, 0, 243}

-- latinSmallLetterOWithCircumflex BMPString ::= {0, 0, 0, 244}

-- latinSmallLetterOWithTilde BMPString ::= {0, 0, 0, 245}

-- latinSmallLetterOWithDiaeresis BMPString ::= {0, 0, 0, 246}

-- divisionSign BMPString ::= {0, 0, 0, 247}

-- latinSmallLetterOWithStroke BMPString ::= {0, 0, 0, 248}

-- latinSmallLetterUWithGrave BMPString ::= {0, 0, 0, 249}

-- latinSmallLetterUWithAcute BMPString ::= {0, 0, 0, 250}

-- latinSmallLetterUWithCircumflex BMPString ::= {0, 0, 0, 251}

-- latinSmallLetterUWithDiaeresis BMPString ::= {0, 0, 0, 252}

-- latinSmallLetterYWithAcute BMPString ::= {0, 0, 0, 253}

-- latinSmallLetterThorn BMPString ::= {0, 0, 0, 254}

-- latinSmallLetterYWithDiaeresis BMPString ::= {0, 0, 0, 255}

-- latinCapitalLetterAWithMacron BMPString ::= {0, 0, 1, 0}

-- latinSmallLetterAWithMacron BMPString ::= {0, 0, 1, 1}

-- latinCapitalLetterAWithBreve BMPString ::= {0, 0, 1, 2}

-- latinSmallLetterAWithBreve BMPString ::= {0, 0, 1, 3}

-- latinCapitalLetterAWithOgonek BMPString ::= {0, 0, 1, 4}

-- latinSmallLetterAWithOgonek BMPString ::= {0, 0, 1, 5}

-- latinCapitalLetterCWithAcute BMPString ::= {0, 0, 1, 6}

-- latinSmallLetterCWithAcute BMPString ::= {0, 0, 1, 7}

-- latinCapitalLetterCWithCircumflex BMPString ::= {0, 0, 1, 8}

-- latinSmallLetterCWithCircumflex BMPString ::= {0, 0, 1, 9}

-- latinCapitalLetterCWithDotAbove BMPString ::= {0, 0, 1, 10}

-- latinSmallLetterCWithDotAbove BMPString ::= {0, 0, 1, 11}

-- latinCapitalLetterCWithCaron BMPString ::= {0, 0, 1, 12}

-- latinSmallLetterCWithCaron BMPString ::= {0, 0, 1, 13}

-- latinCapitalLetterDWithCaron BMPString ::= {0, 0, 1, 14}

-- latinSmallLetterDWithCaron BMPString ::= {0, 0, 1, 15}

-- latinCapitalLetterDWithStroke BMPString ::= {0, 0, 1, 16}

-- latinSmallLetterDWithStroke BMPString ::= {0, 0, 1, 17}

-- latinCapitalLetterEWithMacron BMPString ::= {0, 0, 1, 18}

-- latinSmallLetterEWithMacron BMPString ::= {0, 0, 1, 19}

-- latinCapitalLetterEWithBreve BMPString ::= {0, 0, 1, 20}

-- latinSmallLetterEWithBreve BMPString ::= {0, 0, 1, 21}

-- latinCapitalLetterEWithDotAbove BMPString ::= {0, 0, 1, 22}

-- latinSmallLetterEWithDotAbove BMPString ::= {0, 0, 1, 23}

-- latinCapitalLetterEWithOgonek BMPString ::= {0, 0, 1, 24}

-- latinSmallLetterEWithOgonek BMPString ::= {0, 0, 1, 25}

-- latinCapitalLetterEWithCaron BMPString ::= {0, 0, 1, 26}

-- latinSmallLetterEWithCaron BMPString ::= {0, 0, 1, 27}

-- latinCapitalLetterGWithCircumflex BMPString ::= {0, 0, 1, 28}

-- latinSmallLetterGWithCircumflex BMPString ::= {0, 0, 1, 29}

-- latinCapitalLetterGWithBreve BMPString ::= {0, 0, 1, 30}

-- latinSmallLetterGWithBreve BMPString ::= {0, 0, 1, 31}

-- latinCapitalLetterGWithDotAbove BMPString ::= {0, 0, 1, 32}

-- latinSmallLetterGWithDotAbove BMPString ::= {0, 0, 1, 33}

-- latinCapitalLetterGWithCedilla BMPString ::= {0, 0, 1, 34}

-- latinSmallLetterGWithCedilla BMPString ::= {0, 0, 1, 35}

-- latinCapitalLetterHWithCircumflex BMPString ::= {0, 0, 1, 36}

-- latinSmallLetterHWithCircumflex BMPString ::= {0, 0, 1, 37}

-- latinCapitalLetterHWithStroke BMPString ::= {0, 0, 1, 38}

-- latinSmallLetterHWithStroke BMPString ::= {0, 0, 1, 39}

-- latinCapitalLetterIWithTilde BMPString ::= {0, 0, 1, 40}

-- latinSmallLetterIWithTilde BMPString ::= {0, 0, 1, 41}

-- latinCapitalLetterIWithMacron BMPString ::= {0, 0, 1, 42}

-- latinSmallLetterIWithMacron BMPString ::= {0, 0, 1, 43}

-- latinCapitalLetterIWithBreve BMPString ::= {0, 0, 1, 44}

-- latinSmallLetterIWithBreve BMPString ::= {0, 0, 1, 45}

-- latinCapitalLetterIWithOgonek BMPString ::= {0, 0, 1, 46}

-- latinSmallLetterIWithOgonek BMPString ::= {0, 0, 1, 47}

-- latinCapitalLetterIWithDotAbove BMPString ::= {0, 0, 1, 48}

-- latinSmallLetterDotlessI BMPString ::= {0, 0, 1, 49}

-- latinCapitalLigatureIj BMPString ::= {0, 0, 1, 50}

-- latinSmallLigatureIj BMPString ::= {0, 0, 1, 51}

-- latinCapitalLetterJWithCircumflex BMPString ::= {0, 0, 1, 52}

-- latinSmallLetterJWithCircumflex BMPString ::= {0, 0, 1, 53}

-- latinCapitalLetterKWithCedilla BMPString ::= {0, 0, 1, 54}

-- latinSmallLetterKWithCedilla BMPString ::= {0, 0, 1, 55}

-- latinSmallLetterKra BMPString ::= {0, 0, 1, 56}

-- latinCapitalLetterLWithAcute BMPString ::= {0, 0, 1, 57}

-- latinSmallLetterLWithAcute BMPString ::= {0, 0, 1, 58}

-- latinCapitalLetterLWithCedilla BMPString ::= {0, 0, 1, 59}

-- latinSmallLetterLWithCedilla BMPString ::= {0, 0, 1, 60}

-- latinCapitalLetterLWithCaron BMPString ::= {0, 0, 1, 61}

-- latinSmallLetterLWithCaron BMPString ::= {0, 0, 1, 62}

-- latinCapitalLetterLWithMiddleDot BMPString ::= {0, 0, 1, 63}

-- latinSmallLetterLWithMiddleDot BMPString ::= {0, 0, 1, 64}

-- latinCapitalLetterLWithStroke BMPString ::= {0, 0, 1, 65}

-- latinSmallLetterLWithStroke BMPString ::= {0, 0, 1, 66}

-- latinCapitalLetterNWithAcute BMPString ::= {0, 0, 1, 67}

-- latinSmallLetterNWithAcute BMPString ::= {0, 0, 1, 68}

-- latinCapitalLetterNWithCedilla BMPString ::= {0, 0, 1, 69}

-- latinSmallLetterNWithCedilla BMPString ::= {0, 0, 1, 70}

-- latinCapitalLetterNWithCaron BMPString ::= {0, 0, 1, 71}

-- latinSmallLetterNWithCaron BMPString ::= {0, 0, 1, 72}

-- latinSmallLetterNPrecededByApostrophe BMPString ::= {0, 0, 1, 73}

-- latinCapitalLetterEng BMPString ::= {0, 0, 1, 74}

-- latinSmallLetterEng BMPString ::= {0, 0, 1, 75}

-- latinCapitalLetterOWithMacron BMPString ::= {0, 0, 1, 76}

-- latinSmallLetterOWithMacron BMPString ::= {0, 0, 1, 77}

-- latinCapitalLetterOWithBreve BMPString ::= {0, 0, 1, 78}

-- latinSmallLetterOWithBreve BMPString ::= {0, 0, 1, 79}

-- latinCapitalLetterOWithDoubleAcute BMPString ::= {0, 0, 1, 80}

-- latinSmallLetterOWithDoubleAcute BMPString ::= {0, 0, 1, 81}

-- latinCapitalLigatureOe BMPString ::= {0, 0, 1, 82}

-- latinSmallLigatureOe BMPString ::= {0, 0, 1, 83}

-- latinCapitalLetterRWithAcute BMPString ::= {0, 0, 1, 84}

-- latinSmallLetterRWithAcute BMPString ::= {0, 0, 1, 85}

-- latinCapitalLetterRWithCedilla BMPString ::= {0, 0, 1, 86}

-- latinSmallLetterRWithCedilla BMPString ::= {0, 0, 1, 87}

-- latinCapitalLetterRWithCaron BMPString ::= {0, 0, 1, 88}

-- latinSmallLetterRWithCaron BMPString ::= {0, 0, 1, 89}

-- latinCapitalLetterSWithAcute BMPString ::= {0, 0, 1, 90}

-- latinSmallLetterSWithAcute BMPString ::= {0, 0, 1, 91}

-- latinCapitalLetterSWithCircumflex BMPString ::= {0, 0, 1, 92}

-- latinSmallLetterSWithCircumflex BMPString ::= {0, 0, 1, 93}

-- latinCapitalLetterSWithCedilla BMPString ::= {0, 0, 1, 94}

-- latinSmallLetterSWithCedilla BMPString ::= {0, 0, 1, 95}

-- latinCapitalLetterSWithCaron BMPString ::= {0, 0, 1, 96}

-- latinSmallLetterSWithCaron BMPString ::= {0, 0, 1, 97}

-- latinCapitalLetterTWithCedilla BMPString ::= {0, 0, 1, 98}

-- latinSmallLetterTWithCedilla BMPString ::= {0, 0, 1, 99}

-- latinCapitalLetterTWithCaron BMPString ::= {0, 0, 1, 100}

-- latinSmallLetterTWithCaron BMPString ::= {0, 0, 1, 101}

-- latinCapitalLetterTWithStroke BMPString ::= {0, 0, 1, 102}

-- latinSmallLetterTWithStroke BMPString ::= {0, 0, 1, 103}

-- latinCapitalLetterUWithTilde BMPString ::= {0, 0, 1, 104}

-- latinSmallLetterUWithTilde BMPString ::= {0, 0, 1, 105}

-- latinCapitalLetterUWithMacron BMPString ::= {0, 0, 1, 106}

-- latinSmallLetterUWithMacron BMPString ::= {0, 0, 1, 107}

-- latinCapitalLetterUWithBreve BMPString ::= {0, 0, 1, 108}

-- latinSmallLetterUWithBreve BMPString ::= {0, 0, 1, 109}

-- latinCapitalLetterUWithRingAbove BMPString ::= {0, 0, 1, 110}

-- latinSmallLetterUWithRingAbove BMPString ::= {0, 0, 1, 111}

-- latinCapitalLetterUWithDoubleAcute BMPString ::= {0, 0, 1, 112}

-- latinSmallLetterUWithDoubleAcute BMPString ::= {0, 0, 1, 113}

-- latinCapitalLetterUWithOgonek BMPString ::= {0, 0, 1, 114}

-- latinSmallLetterUWithOgonek BMPString ::= {0, 0, 1, 115}

-- latinCapitalLetterWWithCircumflex BMPString ::= {0, 0, 1, 116}

-- latinSmallLetterWWithCircumflex BMPString ::= {0, 0, 1, 117}

-- latinCapitalLetterYWithCircumflex BMPString ::= {0, 0, 1, 118}

-- latinSmallLetterYWithCircumflex BMPString ::= {0, 0, 1, 119}

-- latinCapitalLetterYWithDiaeresis BMPString ::= {0, 0, 1, 120}

-- latinCapitalLetterZWithAcute BMPString ::= {0, 0, 1, 121}

-- latinSmallLetterZWithAcute BMPString ::= {0, 0, 1, 122}

-- latinCapitalLetterZWithDotAbove BMPString ::= {0, 0, 1, 123}

-- latinSmallLetterZWithDotAbove BMPString ::= {0, 0, 1, 124}

-- latinCapitalLetterZWithCaron BMPString ::= {0, 0, 1, 125}

-- latinSmallLetterZWithCaron BMPString ::= {0, 0, 1, 126}

-- latinSmallLetterLongS BMPString ::= {0, 0, 1, 127}

-- latinSmallLetterBWithStroke BMPString ::= {0, 0, 1, 128}

-- latinCapitalLetterBWithHook BMPString ::= {0, 0, 1, 129}

-- latinCapitalLetterBWithTopbar BMPString ::= {0, 0, 1, 130}

-- latinSmallLetterBWithTopbar BMPString ::= {0, 0, 1, 131}

-- latinCapitalLetterToneSix BMPString ::= {0, 0, 1, 132}

-- latinSmallLetterToneSix BMPString ::= {0, 0, 1, 133}

-- latinCapitalLetterOpenO BMPString ::= {0, 0, 1, 134}

-- latinCapitalLetterCWithHook BMPString ::= {0, 0, 1, 135}

-- latinSmallLetterCWithHook BMPString ::= {0, 0, 1, 136}

-- latinCapitalLetterAfricanD BMPString ::= {0, 0, 1, 137}

-- latinCapitalLetterDWithHook BMPString ::= {0, 0, 1, 138}

-- latinCapitalLetterDWithTopbar BMPString ::= {0, 0, 1, 139}

-- latinSmallLetterDWithTopbar BMPString ::= {0, 0, 1, 140}

-- latinSmallLetterTurnedDelta BMPString ::= {0, 0, 1, 141}

-- latinCapitalLetterReversedE BMPString ::= {0, 0, 1, 142}

-- latinCapitalLetterSchwa BMPString ::= {0, 0, 1, 143}

-- latinCapitalLetterOpenE BMPString ::= {0, 0, 1, 144}

-- latinCapitalLetterFWithHook BMPString ::= {0, 0, 1, 145}

-- latinSmallLetterFWithHook BMPString ::= {0, 0, 1, 146}

-- latinCapitalLetterGWithHook BMPString ::= {0, 0, 1, 147}

-- latinCapitalLetterGamma BMPString ::= {0, 0, 1, 148}

-- latinSmallLetterHv BMPString ::= {0, 0, 1, 149}

-- latinCapitalLetterIota BMPString ::= {0, 0, 1, 150}

-- latinCapitalLetterIWithStroke BMPString ::= {0, 0, 1, 151}

-- latinCapitalLetterKWithHook BMPString ::= {0, 0, 1, 152}

-- latinSmallLetterKWithHook BMPString ::= {0, 0, 1, 153}

-- latinSmallLetterLWithBar BMPString ::= {0, 0, 1, 154}

-- latinSmallLetterLambdaWithStroke BMPString ::= {0, 0, 1, 155}

-- latinCapitalLetterTurnedM BMPString ::= {0, 0, 1, 156}

-- latinCapitalLetterNWithLeftHook BMPString ::= {0, 0, 1, 157}

-- latinSmallLetterNWithLongRightLeg BMPString ::= {0, 0, 1, 158}

-- latinCapitalLetterOWithMiddleTilde BMPString ::= {0, 0, 1, 159}

-- latinCapitalLetterOWithHorn BMPString ::= {0, 0, 1, 160}

-- latinSmallLetterOWithHorn BMPString ::= {0, 0, 1, 161}

-- latinCapitalLetterOi BMPString ::= {0, 0, 1, 162}

-- latinSmallLetterOi BMPString ::= {0, 0, 1, 163}

-- latinCapitalLetterPWithHook BMPString ::= {0, 0, 1, 164}

-- latinSmallLetterPWithHook BMPString ::= {0, 0, 1, 165}

-- latinLetterYr BMPString ::= {0, 0, 1, 166}

-- latinCapitalLetterToneTwo BMPString ::= {0, 0, 1, 167}

-- latinSmallLetterToneTwo BMPString ::= {0, 0, 1, 168}

-- latinCapitalLetterEsh BMPString ::= {0, 0, 1, 169}

-- latinLetterReversedEshLoop BMPString ::= {0, 0, 1, 170}

-- latinSmallLetterTWithPalatalHook BMPString ::= {0, 0, 1, 171}

-- latinCapitalLetterTWithHook BMPString ::= {0, 0, 1, 172}

-- latinSmallLetterTWithHook BMPString ::= {0, 0, 1, 173}

-- latinCapitalLetterTWithRetroflexHook BMPString ::= {0, 0, 1, 174}

-- latinCapitalLetterUWithHorn BMPString ::= {0, 0, 1, 175}

-- latinSmallLetterUWithHorn BMPString ::= {0, 0, 1, 176}

-- latinCapitalLetterUpsilon BMPString ::= {0, 0, 1, 177}

-- latinCapitalLetterVWithHook BMPString ::= {0, 0, 1, 178}

-- latinCapitalLetterYWithHook BMPString ::= {0, 0, 1, 179}

-- latinSmallLetterYWithHook BMPString ::= {0, 0, 1, 180}

-- latinCapitalLetterZWithStroke BMPString ::= {0, 0, 1, 181}

-- latinSmallLetterZWithStroke BMPString ::= {0, 0, 1, 182}

-- latinCapitalLetterEzh BMPString ::= {0, 0, 1, 183}

-- latinCapitalLetterEzhReversed BMPString ::= {0, 0, 1, 184}

-- latinSmallLetterEzhReversed BMPString ::= {0, 0, 1, 185}

-- latinSmallLetterEzhWithTail BMPString ::= {0, 0, 1, 186}

-- latinLetterTwoWithStroke BMPString ::= {0, 0, 1, 187}

-- latinCapitalLetterToneFive BMPString ::= {0, 0, 1, 188}

-- latinSmallLetterToneFive BMPString ::= {0, 0, 1, 189}

-- latinLetterInvertedGlottalStopWithStroke BMPString ::= {0, 0, 1, 190}

-- latinLetterWynn BMPString ::= {0, 0, 1, 191}

-- latinLetterDentalClick BMPString ::= {0, 0, 1, 192}

-- latinLetterLateralClick BMPString ::= {0, 0, 1, 193}

-- latinLetterAlveolarClick BMPString ::= {0, 0, 1, 194}

-- latinLetterRetroflexClick BMPString ::= {0, 0, 1, 195}

-- latinCapitalLetterDzWithCaron BMPString ::= {0, 0, 1, 196}

-- latinCapitalLetterDWithSmallLetterZWithCaron BMPString ::= {0, 0, 1, 197}

-- latinSmallLetterDzWithCaron BMPString ::= {0, 0, 1, 198}

-- latinCapitalLetterLj BMPString ::= {0, 0, 1, 199}

-- latinCapitalLetterLWithSmallLetterJ BMPString ::= {0, 0, 1, 200}

-- latinSmallLetterLj BMPString ::= {0, 0, 1, 201}

-- latinCapitalLetterNj BMPString ::= {0, 0, 1, 202}

-- latinCapitalLetterNWithSmallLetterJ BMPString ::= {0, 0, 1, 203}

-- latinSmallLetterNj BMPString ::= {0, 0, 1, 204}

-- latinCapitalLetterAWithCaron BMPString ::= {0, 0, 1, 205}

-- latinSmallLetterAWithCaron BMPString ::= {0, 0, 1, 206}

-- latinCapitalLetterIWithCaron BMPString ::= {0, 0, 1, 207}

-- latinSmallLetterIWithCaron BMPString ::= {0, 0, 1, 208}

-- latinCapitalLetterOWithCaron BMPString ::= {0, 0, 1, 209}

-- latinSmallLetterOWithCaron BMPString ::= {0, 0, 1, 210}

-- latinCapitalLetterUWithCaron BMPString ::= {0, 0, 1, 211}

-- latinSmallLetterUWithCaron BMPString ::= {0, 0, 1, 212}

-- latinCapitalLetterUWithDiaeresisAndMacron BMPString ::= {0, 0, 1, 213}

-- latinSmallLetterUWithDiaeresisAndMacron BMPString ::= {0, 0, 1, 214}

-- latinCapitalLetterUWithDiaeresisAndAcute BMPString ::= {0, 0, 1, 215}

-- latinSmallLetterUWithDiaeresisAndAcute BMPString ::= {0, 0, 1, 216}

-- latinCapitalLetterUWithDiaeresisAndCaron BMPString ::= {0, 0, 1, 217}

-- latinSmallLetterUWithDiaeresisAndCaron BMPString ::= {0, 0, 1, 218}

-- latinCapitalLetterUWithDiaeresisAndGrave BMPString ::= {0, 0, 1, 219}

-- latinSmallLetterUWithDiaeresisAndGrave BMPString ::= {0, 0, 1, 220}

-- latinSmallLetterTurnedE BMPString ::= {0, 0, 1, 221}

-- latinCapitalLetterAWithDiaeresisAndMacron BMPString ::= {0, 0, 1, 222}

-- latinSmallLetterAWithDiaeresisAndMacron BMPString ::= {0, 0, 1, 223}

-- latinCapitalLetterAWithDotAboveAndMacron BMPString ::= {0, 0, 1, 224}

-- latinSmallLetterAWithDotAboveAndMacron BMPString ::= {0, 0, 1, 225}

-- latinCapitalLetterAeWithMacron BMPString ::= {0, 0, 1, 226}

-- latinSmallLetterAeWithMacron BMPString ::= {0, 0, 1, 227}

-- latinCapitalLetterGWithStroke BMPString ::= {0, 0, 1, 228}

-- latinSmallLetterGWithStroke BMPString ::= {0, 0, 1, 229}

-- latinCapitalLetterGWithCaron BMPString ::= {0, 0, 1, 230}

-- latinSmallLetterGWithCaron BMPString ::= {0, 0, 1, 231}

-- latinCapitalLetterKWithCaron BMPString ::= {0, 0, 1, 232}

-- latinSmallLetterKWithCaron BMPString ::= {0, 0, 1, 233}

-- latinCapitalLetterOWithOgonek BMPString ::= {0, 0, 1, 234}

-- latinSmallLetterOWithOgonek BMPString ::= {0, 0, 1, 235}

-- latinCapitalLetterOWithOgonekAndMacron BMPString ::= {0, 0, 1, 236}

-- latinSmallLetterOWithOgonekAndMacron BMPString ::= {0, 0, 1, 237}

-- latinCapitalLetterEzhWithCaron BMPString ::= {0, 0, 1, 238}

-- latinSmallLetterEzhWithCaron BMPString ::= {0, 0, 1, 239}

-- latinSmallLetterJWithCaron BMPString ::= {0, 0, 1, 240}

-- latinCapitalLetterDz BMPString ::= {0, 0, 1, 241}

-- latinCapitalLetterDWithSmallLetterZ BMPString ::= {0, 0, 1, 242}

-- latinSmallLetterDz BMPString ::= {0, 0, 1, 243}

-- latinCapitalLetterGWithAcute BMPString ::= {0, 0, 1, 244}

-- latinSmallLetterGWithAcute BMPString ::= {0, 0, 1, 245}

-- latinCapitalLetterHwair BMPString ::= {0, 0, 1, 246}

-- latinCapitalLetterWynn BMPString ::= {0, 0, 1, 247}

-- latinCapitalLetterNWithGrave BMPString ::= {0, 0, 1, 248}

-- latinSmallLetterNWithGrave BMPString ::= {0, 0, 1, 249}

-- latinCapitalLetterAWithRingAboveAndAcute BMPString ::= {0, 0, 1, 250}

-- latinSmallLetterAWithRingAboveAndAcute BMPString ::= {0, 0, 1, 251}

-- latinCapitalLetterAeWithAcute BMPString ::= {0, 0, 1, 252}

-- latinSmallLetterAeWithAcute BMPString ::= {0, 0, 1, 253}

-- latinCapitalLetterOWithStrokeAndAcute BMPString ::= {0, 0, 1, 254}

-- latinSmallLetterOWithStrokeAndAcute BMPString ::= {0, 0, 1, 255}

-- latinCapitalLetterAWithDoubleGrave BMPString ::= {0, 0, 2, 0}

-- latinSmallLetterAWithDoubleGrave BMPString ::= {0, 0, 2, 1}

-- latinCapitalLetterAWithInvertedBreve BMPString ::= {0, 0, 2, 2}

-- latinSmallLetterAWithInvertedBreve BMPString ::= {0, 0, 2, 3}

-- latinCapitalLetterEWithDoubleGrave BMPString ::= {0, 0, 2, 4}

-- latinSmallLetterEWithDoubleGrave BMPString ::= {0, 0, 2, 5}

-- latinCapitalLetterEWithInvertedBreve BMPString ::= {0, 0, 2, 6}

-- latinSmallLetterEWithInvertedBreve BMPString ::= {0, 0, 2, 7}

-- latinCapitalLetterIWithDoubleGrave BMPString ::= {0, 0, 2, 8}

-- latinSmallLetterIWithDoubleGrave BMPString ::= {0, 0, 2, 9}

-- latinCapitalLetterIWithInvertedBreve BMPString ::= {0, 0, 2, 10}

-- latinSmallLetterIWithInvertedBreve BMPString ::= {0, 0, 2, 11}

-- latinCapitalLetterOWithDoubleGrave BMPString ::= {0, 0, 2, 12}

-- latinSmallLetterOWithDoubleGrave BMPString ::= {0, 0, 2, 13}

-- latinCapitalLetterOWithInvertedBreve BMPString ::= {0, 0, 2, 14}

-- latinSmallLetterOWithInvertedBreve BMPString ::= {0, 0, 2, 15}

-- latinCapitalLetterRWithDoubleGrave BMPString ::= {0, 0, 2, 16}

-- latinSmallLetterRWithDoubleGrave BMPString ::= {0, 0, 2, 17}

-- latinCapitalLetterRWithInvertedBreve BMPString ::= {0, 0, 2, 18}

-- latinSmallLetterRWithInvertedBreve BMPString ::= {0, 0, 2, 19}

-- latinCapitalLetterUWithDoubleGrave BMPString ::= {0, 0, 2, 20}

-- latinSmallLetterUWithDoubleGrave BMPString ::= {0, 0, 2, 21}

-- latinCapitalLetterUWithInvertedBreve BMPString ::= {0, 0, 2, 22}

-- latinSmallLetterUWithInvertedBreve BMPString ::= {0, 0, 2, 23}

-- latinCapitalLetterSWithCommaBelow BMPString ::= {0, 0, 2, 24}

-- latinSmallLetterSWithCommaBelow BMPString ::= {0, 0, 2, 25}

-- latinCapitalLetterTWithCommaBelow BMPString ::= {0, 0, 2, 26}

-- latinSmallLetterTWithCommaBelow BMPString ::= {0, 0, 2, 27}

-- latinCapitalLetterYogh BMPString ::= {0, 0, 2, 28}

-- latinSmallLetterYogh BMPString ::= {0, 0, 2, 29}

-- latinCapitalLetterHWithCaron BMPString ::= {0, 0, 2, 30}

-- latinSmallLetterHWithCaron BMPString ::= {0, 0, 2, 31}

-- latinCapitalLetterNWithLongRightLeg BMPString ::= {0, 0, 2, 32}

-- latinCapitalLetterOu BMPString ::= {0, 0, 2, 34}

-- latinSmallLetterOu BMPString ::= {0, 0, 2, 35}

-- latinCapitalLetterZWithHook BMPString ::= {0, 0, 2, 36}

-- latinSmallLetterZWithHook BMPString ::= {0, 0, 2, 37}

-- latinCapitalLetterAWithDotAbove BMPString ::= {0, 0, 2, 38}

-- latinSmallLetterAWithDotAbove BMPString ::= {0, 0, 2, 39}

-- latinCapitalLetterEWithCedilla BMPString ::= {0, 0, 2, 40}

-- latinSmallLetterEWithCedilla BMPString ::= {0, 0, 2, 41}

-- latinCapitalLetterOWithDiaeresisAndMacron BMPString ::= {0, 0, 2, 42}

-- latinSmallLetterOWithDiaeresisAndMacron BMPString ::= {0, 0, 2, 43}

-- latinCapitalLetterOWithTildeAndMacron BMPString ::= {0, 0, 2, 44}

-- latinSmallLetterOWithTildeAndMacron BMPString ::= {0, 0, 2, 45}

-- latinCapitalLetterOWithDotAbove BMPString ::= {0, 0, 2, 46}

-- latinSmallLetterOWithDotAbove BMPString ::= {0, 0, 2, 47}

-- latinCapitalLetterOWithDotAboveAndMacron BMPString ::= {0, 0, 2, 48}

-- latinSmallLetterOWithDotAboveAndMacron BMPString ::= {0, 0, 2, 49}

-- latinCapitalLetterYWithMacron BMPString ::= {0, 0, 2, 50}

-- latinSmallLetterYWithMacron BMPString ::= {0, 0, 2, 51}

-- latinSmallLetterTurnedA BMPString ::= {0, 0, 2, 80}

-- latinSmallLetterAlpha BMPString ::= {0, 0, 2, 81}

-- latinSmallLetterTurnedAlpha BMPString ::= {0, 0, 2, 82}

-- latinSmallLetterBWithHook BMPString ::= {0, 0, 2, 83}

-- latinSmallLetterOpenO BMPString ::= {0, 0, 2, 84}

-- latinSmallLetterCWithCurl BMPString ::= {0, 0, 2, 85}

-- latinSmallLetterDWithTail BMPString ::= {0, 0, 2, 86}

-- latinSmallLetterDWithHook BMPString ::= {0, 0, 2, 87}

-- latinSmallLetterReversedE BMPString ::= {0, 0, 2, 88}

-- latinSmallLetterSchwa BMPString ::= {0, 0, 2, 89}

-- latinSmallLetterSchwaWithHook BMPString ::= {0, 0, 2, 90}

-- latinSmallLetterOpenE BMPString ::= {0, 0, 2, 91}

-- latinSmallLetterReversedOpenE BMPString ::= {0, 0, 2, 92}

-- latinSmallLetterReversedOpenEWithHook BMPString ::= {0, 0, 2, 93}

-- latinSmallLetterClosedReversedOpenE BMPString ::= {0, 0, 2, 94}

-- latinSmallLetterDotlessJWithStroke BMPString ::= {0, 0, 2, 95}

-- latinSmallLetterGWithHook BMPString ::= {0, 0, 2, 96}

-- latinSmallLetterScriptG BMPString ::= {0, 0, 2, 97}

-- latinLetterSmallCapitalG BMPString ::= {0, 0, 2, 98}

-- latinSmallLetterGamma BMPString ::= {0, 0, 2, 99}

-- latinSmallLetterRamsHorn BMPString ::= {0, 0, 2, 100}

-- latinSmallLetterTurnedH BMPString ::= {0, 0, 2, 101}

-- latinSmallLetterHWithHook BMPString ::= {0, 0, 2, 102}

-- latinSmallLetterHengWithHook BMPString ::= {0, 0, 2, 103}

-- latinSmallLetterIWithStroke BMPString ::= {0, 0, 2, 104}

-- latinSmallLetterIota BMPString ::= {0, 0, 2, 105}

-- latinLetterSmallCapitalI BMPString ::= {0, 0, 2, 106}

-- latinSmallLetterLWithMiddleTilde BMPString ::= {0, 0, 2, 107}

-- latinSmallLetterLWithBelt BMPString ::= {0, 0, 2, 108}

-- latinSmallLetterLWithRetroflexHook BMPString ::= {0, 0, 2, 109}

-- latinSmallLetterLezh BMPString ::= {0, 0, 2, 110}

-- latinSmallLetterTurnedM BMPString ::= {0, 0, 2, 111}

-- latinSmallLetterTurnedMWithLongLeg BMPString ::= {0, 0, 2, 112}

-- latinSmallLetterMWithHook BMPString ::= {0, 0, 2, 113}

-- latinSmallLetterNWithLeftHook BMPString ::= {0, 0, 2, 114}

-- latinSmallLetterNWithRetroflexHook BMPString ::= {0, 0, 2, 115}

-- latinLetterSmallCapitalN BMPString ::= {0, 0, 2, 116}

-- latinSmallLetterBarredO BMPString ::= {0, 0, 2, 117}

-- latinLetterSmallCapitalOe BMPString ::= {0, 0, 2, 118}

-- latinSmallLetterClosedOmega BMPString ::= {0, 0, 2, 119}

-- latinSmallLetterPhi BMPString ::= {0, 0, 2, 120}

-- latinSmallLetterTurnedR BMPString ::= {0, 0, 2, 121}

-- latinSmallLetterTurnedRWithLongLeg BMPString ::= {0, 0, 2, 122}

-- latinSmallLetterTurnedRWithHook BMPString ::= {0, 0, 2, 123}

-- latinSmallLetterRWithLongLeg BMPString ::= {0, 0, 2, 124}

-- latinSmallLetterRWithTail BMPString ::= {0, 0, 2, 125}

-- latinSmallLetterRWithFishhook BMPString ::= {0, 0, 2, 126}

-- latinSmallLetterReversedRWithFishhook BMPString ::= {0, 0, 2, 127}

-- latinLetterSmallCapitalR BMPString ::= {0, 0, 2, 128}

-- latinLetterSmallCapitalInvertedR BMPString ::= {0, 0, 2, 129}

-- latinSmallLetterSWithHook BMPString ::= {0, 0, 2, 130}

-- latinSmallLetterEsh BMPString ::= {0, 0, 2, 131}

-- latinSmallLetterDotlessJWithStrokeAndHook BMPString ::= {0, 0, 2, 132}

-- latinSmallLetterSquatReversedEsh BMPString ::= {0, 0, 2, 133}

-- latinSmallLetterEshWithCurl BMPString ::= {0, 0, 2, 134}

-- latinSmallLetterTurnedT BMPString ::= {0, 0, 2, 135}

-- latinSmallLetterTWithRetroflexHook BMPString ::= {0, 0, 2, 136}

-- latinSmallLetterUBar BMPString ::= {0, 0, 2, 137}

-- latinSmallLetterUpsilon BMPString ::= {0, 0, 2, 138}

-- latinSmallLetterVWithHook BMPString ::= {0, 0, 2, 139}

-- latinSmallLetterTurnedV BMPString ::= {0, 0, 2, 140}

-- latinSmallLetterTurnedW BMPString ::= {0, 0, 2, 141}

-- latinSmallLetterTurnedY BMPString ::= {0, 0, 2, 142}

-- latinLetterSmallCapitalY BMPString ::= {0, 0, 2, 143}

-- latinSmallLetterZWithRetroflexHook BMPString ::= {0, 0, 2, 144}

-- latinSmallLetterZWithCurl BMPString ::= {0, 0, 2, 145}

-- latinSmallLetterEzh BMPString ::= {0, 0, 2, 146}

-- latinSmallLetterEzhWithCurl BMPString ::= {0, 0, 2, 147}

-- latinLetterGlottalStop BMPString ::= {0, 0, 2, 148}

-- latinLetterPharyngealVoicedFricative BMPString ::= {0, 0, 2, 149}

-- latinLetterInvertedGlottalStop BMPString ::= {0, 0, 2, 150}

-- latinLetterStretchedC BMPString ::= {0, 0, 2, 151}

-- latinLetterBilabialClick BMPString ::= {0, 0, 2, 152}

-- latinLetterSmallCapitalB BMPString ::= {0, 0, 2, 153}

-- latinSmallLetterClosedOpenE BMPString ::= {0, 0, 2, 154}

-- latinLetterSmallCapitalGWithHook BMPString ::= {0, 0, 2, 155}

-- latinLetterSmallCapitalH BMPString ::= {0, 0, 2, 156}

-- latinSmallLetterJWithCrossed-tail BMPString ::= {0, 0, 2, 157}

-- latinSmallLetterTurnedK BMPString ::= {0, 0, 2, 158}

-- latinLetterSmallCapitalL BMPString ::= {0, 0, 2, 159}

-- latinSmallLetterQWithHook BMPString ::= {0, 0, 2, 160}

-- latinLetterGlottalStopWithStroke BMPString ::= {0, 0, 2, 161}

-- latinLetterReversedGlottalStopWithStroke BMPString ::= {0, 0, 2, 162}

-- latinSmallLetterDzDigraph BMPString ::= {0, 0, 2, 163}

-- latinSmallLetterDezhDigraph BMPString ::= {0, 0, 2, 164}

-- latinSmallLetterDzDigraphWithCurl BMPString ::= {0, 0, 2, 165}

-- latinSmallLetterTsDigraph BMPString ::= {0, 0, 2, 166}

-- latinSmallLetterTeshDigraph BMPString ::= {0, 0, 2, 167}

-- latinSmallLetterTcDigraphWithCurl BMPString ::= {0, 0, 2, 168}

-- latinSmallLetterFengDigraph BMPString ::= {0, 0, 2, 169}

-- latinSmallLetterLsDigraph BMPString ::= {0, 0, 2, 170}

-- latinSmallLetterLzDigraph BMPString ::= {0, 0, 2, 171}

-- latinLetterBilabialPercussive BMPString ::= {0, 0, 2, 172}

-- latinLetterBidentalPercussive BMPString ::= {0, 0, 2, 173}

-- modifierLetterSmallH BMPString ::= {0, 0, 2, 176}

-- modifierLetterSmallHWithHook BMPString ::= {0, 0, 2, 177}

-- modifierLetterSmallJ BMPString ::= {0, 0, 2, 178}

-- modifierLetterSmallR BMPString ::= {0, 0, 2, 179}

-- modifierLetterSmallTurnedR BMPString ::= {0, 0, 2, 180}

-- modifierLetterSmallTurnedRWithHook BMPString ::= {0, 0, 2, 181}

-- modifierLetterSmallCapitalInvertedR BMPString ::= {0, 0, 2, 182}

-- modifierLetterSmallW BMPString ::= {0, 0, 2, 183}

-- modifierLetterSmallY BMPString ::= {0, 0, 2, 184}

-- modifierLetterPrime BMPString ::= {0, 0, 2, 185}

-- modifierLetterDoublePrime BMPString ::= {0, 0, 2, 186}

-- modifierLetterTurnedComma BMPString ::= {0, 0, 2, 187}

-- modifierLetterApostrophe BMPString ::= {0, 0, 2, 188}

-- modifierLetterReversedComma BMPString ::= {0, 0, 2, 189}

-- modifierLetterRightHalfRing BMPString ::= {0, 0, 2, 190}

-- modifierLetterLeftHalfRing BMPString ::= {0, 0, 2, 191}

-- modifierLetterGlottalStop BMPString ::= {0, 0, 2, 192}

-- modifierLetterReversedGlottalStop BMPString ::= {0, 0, 2, 193}

-- modifierLetterLeftArrowhead BMPString ::= {0, 0, 2, 194}

-- modifierLetterRightArrowhead BMPString ::= {0, 0, 2, 195}

-- modifierLetterUpArrowhead BMPString ::= {0, 0, 2, 196}

-- modifierLetterDownArrowhead BMPString ::= {0, 0, 2, 197}

-- modifierLetterCircumflexAccent BMPString ::= {0, 0, 2, 198}

-- caron BMPString ::= {0, 0, 2, 199}

-- modifierLetterVerticalLine BMPString ::= {0, 0, 2, 200}

-- modifierLetterMacron BMPString ::= {0, 0, 2, 201}

-- modifierLetterAcuteAccent BMPString ::= {0, 0, 2, 202}

-- modifierLetterGraveAccent BMPString ::= {0, 0, 2, 203}

-- modifierLetterLowVerticalLine BMPString ::= {0, 0, 2, 204}

-- modifierLetterLowMacron BMPString ::= {0, 0, 2, 205}

-- modifierLetterLowGraveAccent BMPString ::= {0, 0, 2, 206}

-- modifierLetterLowAcuteAccent BMPString ::= {0, 0, 2, 207}

-- modifierLetterTriangularColon BMPString ::= {0, 0, 2, 208}

-- modifierLetterHalfTriangularColon BMPString ::= {0, 0, 2, 209}

-- modifierLetterCentredRightHalfRing BMPString ::= {0, 0, 2, 210}

-- modifierLetterCentredLeftHalfRing BMPString ::= {0, 0, 2, 211}

-- modifierLetterUpTack BMPString ::= {0, 0, 2, 212}

-- modifierLetterDownTack BMPString ::= {0, 0, 2, 213}

-- modifierLetterPlusSign BMPString ::= {0, 0, 2, 214}

-- modifierLetterMinusSign BMPString ::= {0, 0, 2, 215}

-- breve BMPString ::= {0, 0, 2, 216}

-- dotAbove BMPString ::= {0, 0, 2, 217}

-- ringAbove BMPString ::= {0, 0, 2, 218}

-- ogonek BMPString ::= {0, 0, 2, 219}

-- smallTilde BMPString ::= {0, 0, 2, 220}

-- doubleAcuteAccent BMPString ::= {0, 0, 2, 221}

-- modifierLetterRhoticHook BMPString ::= {0, 0, 2, 222}

-- modifierLetterCrossAccent BMPString ::= {0, 0, 2, 223}

-- modifierLetterSmallGamma BMPString ::= {0, 0, 2, 224}

-- modifierLetterSmallL BMPString ::= {0, 0, 2, 225}

-- modifierLetterSmallS BMPString ::= {0, 0, 2, 226}

-- modifierLetterSmallX BMPString ::= {0, 0, 2, 227}

-- modifierLetterSmallReversedGlottalStop BMPString ::= {0, 0, 2, 228}

-- modifierLetterExtra-highToneBar BMPString ::= {0, 0, 2, 229}

-- modifierLetterHighToneBar BMPString ::= {0, 0, 2, 230}

-- modifierLetterMidToneBar BMPString ::= {0, 0, 2, 231}

-- modifierLetterLowToneBar BMPString ::= {0, 0, 2, 232}

-- modifierLetterExtra-lowToneBar BMPString ::= {0, 0, 2, 233}

-- modifierLetterYinDepartingToneMark BMPString ::= {0, 0, 2, 234}

-- modifierLetterYangDepartingToneMark BMPString ::= {0, 0, 2, 235}

-- modifierLetterVoicing BMPString ::= {0, 0, 2, 236}

-- modifierLetterUnaspirated BMPString ::= {0, 0, 2, 237}

-- modifierLetterDoubleApostrophe BMPString ::= {0, 0, 2, 238}

-- combiningGraveAccent BMPString ::= {0, 0, 3, 0}

-- combiningAcuteAccent BMPString ::= {0, 0, 3, 1}

-- combiningCircumflexAccent BMPString ::= {0, 0, 3, 2}

-- combiningTilde BMPString ::= {0, 0, 3, 3}

-- combiningMacron BMPString ::= {0, 0, 3, 4}

-- combiningOverline BMPString ::= {0, 0, 3, 5}

-- combiningBreve BMPString ::= {0, 0, 3, 6}

-- combiningDotAbove BMPString ::= {0, 0, 3, 7}

-- combiningDiaeresis BMPString ::= {0, 0, 3, 8}

-- combiningHookAbove BMPString ::= {0, 0, 3, 9}

-- combiningRingAbove BMPString ::= {0, 0, 3, 10}

-- combiningDoubleAcuteAccent BMPString ::= {0, 0, 3, 11}

-- combiningCaron BMPString ::= {0, 0, 3, 12}

-- combiningVerticalLineAbove BMPString ::= {0, 0, 3, 13}

-- combiningDoubleVerticalLineAbove BMPString ::= {0, 0, 3, 14}

-- combiningDoubleGraveAccent BMPString ::= {0, 0, 3, 15}

-- combiningCandrabindu BMPString ::= {0, 0, 3, 16}

-- combiningInvertedBreve BMPString ::= {0, 0, 3, 17}

-- combiningTurnedCommaAbove BMPString ::= {0, 0, 3, 18}

-- combiningCommaAbove BMPString ::= {0, 0, 3, 19}

-- combiningReversedCommaAbove BMPString ::= {0, 0, 3, 20}

-- combiningCommaAboveRight BMPString ::= {0, 0, 3, 21}

-- combiningGraveAccentBelow BMPString ::= {0, 0, 3, 22}

-- combiningAcuteAccentBelow BMPString ::= {0, 0, 3, 23}

-- combiningLeftTackBelow BMPString ::= {0, 0, 3, 24}

-- combiningRightTackBelow BMPString ::= {0, 0, 3, 25}

-- combiningLeftAngleAbove BMPString ::= {0, 0, 3, 26}

-- combiningHorn BMPString ::= {0, 0, 3, 27}

-- combiningLeftHalfRingBelow BMPString ::= {0, 0, 3, 28}

-- combiningUpTackBelow BMPString ::= {0, 0, 3, 29}

-- combiningDownTackBelow BMPString ::= {0, 0, 3, 30}

-- combiningPlusSignBelow BMPString ::= {0, 0, 3, 31}

-- combiningMinusSignBelow BMPString ::= {0, 0, 3, 32}

-- combiningPalatalizedHookBelow BMPString ::= {0, 0, 3, 33}

-- combiningRetroflexHookBelow BMPString ::= {0, 0, 3, 34}

-- combiningDotBelow BMPString ::= {0, 0, 3, 35}

-- combiningDiaeresisBelow BMPString ::= {0, 0, 3, 36}

-- combiningRingBelow BMPString ::= {0, 0, 3, 37}

-- combiningCommaBelow BMPString ::= {0, 0, 3, 38}

-- combiningCedilla BMPString ::= {0, 0, 3, 39}

-- combiningOgonek BMPString ::= {0, 0, 3, 40}

-- combiningVerticalLineBelow BMPString ::= {0, 0, 3, 41}

-- combiningBridgeBelow BMPString ::= {0, 0, 3, 42}

-- combiningInvertedDoubleArchBelow BMPString ::= {0, 0, 3, 43}

-- combiningCaronBelow BMPString ::= {0, 0, 3, 44}

-- combiningCircumflexAccentBelow BMPString ::= {0, 0, 3, 45}

-- combiningBreveBelow BMPString ::= {0, 0, 3, 46}

-- combiningInvertedBreveBelow BMPString ::= {0, 0, 3, 47}

-- combiningTildeBelow BMPString ::= {0, 0, 3, 48}

-- combiningMacronBelow BMPString ::= {0, 0, 3, 49}

-- combiningLowLine BMPString ::= {0, 0, 3, 50}

-- combiningDoubleLowLine BMPString ::= {0, 0, 3, 51}

-- combiningTildeOverlay BMPString ::= {0, 0, 3, 52}

-- combiningShortStrokeOverlay BMPString ::= {0, 0, 3, 53}

-- combiningLongStrokeOverlay BMPString ::= {0, 0, 3, 54}

-- combiningShortSolidusOverlay BMPString ::= {0, 0, 3, 55}

-- combiningLongSolidusOverlay BMPString ::= {0, 0, 3, 56}

-- combiningRightHalfRingBelow BMPString ::= {0, 0, 3, 57}

-- combiningInvertedBridgeBelow BMPString ::= {0, 0, 3, 58}

-- combiningSquareBelow BMPString ::= {0, 0, 3, 59}

-- combiningSeagullBelow BMPString ::= {0, 0, 3, 60}

-- combiningXAbove BMPString ::= {0, 0, 3, 61}

-- combiningVerticalTilde BMPString ::= {0, 0, 3, 62}

-- combiningDoubleOverline BMPString ::= {0, 0, 3, 63}

-- combiningGraveToneMark BMPString ::= {0, 0, 3, 64}

-- combiningAcuteToneMark BMPString ::= {0, 0, 3, 65}

-- combiningGreekPerispomeni BMPString ::= {0, 0, 3, 66}

-- combiningGreekKoronis BMPString ::= {0, 0, 3, 67}

-- combiningGreekDialytikaTonos BMPString ::= {0, 0, 3, 68}

-- combiningGreekYpogegrammeni BMPString ::= {0, 0, 3, 69}

-- combiningBridgeAbove BMPString ::= {0, 0, 3, 70}

-- combiningEqualsSignBelow BMPString ::= {0, 0, 3, 71}

-- combiningDoubleVerticalLineBelow BMPString ::= {0, 0, 3, 72}

-- combiningLeftAngleBelow BMPString ::= {0, 0, 3, 73}

-- combiningNotTildeAbove BMPString ::= {0, 0, 3, 74}

-- combiningHomotheticAbove BMPString ::= {0, 0, 3, 75}

-- combiningAlmostEqualToAbove BMPString ::= {0, 0, 3, 76}

-- combiningLeftRightArrowBelow BMPString ::= {0, 0, 3, 77}

-- combiningUpwardsArrowBelow BMPString ::= {0, 0, 3, 78}

-- combiningGraphemeJoiner BMPString ::= {0, 0, 3, 79}

-- combiningDoubleTilde BMPString ::= {0, 0, 3, 96}

-- combiningDoubleInvertedBreve BMPString ::= {0, 0, 3, 97}

-- combiningDoubleRightwardsArrowBelow BMPString ::= {0, 0, 3, 98}

-- combiningLatinSmallLetterA BMPString ::= {0, 0, 3, 99}

-- combiningLatinSmallLetterE BMPString ::= {0, 0, 3, 100}

-- combiningLatinSmallLetterI BMPString ::= {0, 0, 3, 101}

-- combiningLatinSmallLetterO BMPString ::= {0, 0, 3, 102}

-- combiningLatinSmallLetterU BMPString ::= {0, 0, 3, 103}

-- combiningLatinSmallLetterC BMPString ::= {0, 0, 3, 104}

-- combiningLatinSmallLetterD BMPString ::= {0, 0, 3, 105}

-- combiningLatinSmallLetterH BMPString ::= {0, 0, 3, 106}

-- combiningLatinSmallLetterM BMPString ::= {0, 0, 3, 107}

-- combiningLatinSmallLetterR BMPString ::= {0, 0, 3, 108}

-- combiningLatinSmallLetterT BMPString ::= {0, 0, 3, 109}

-- combiningLatinSmallLetterV BMPString ::= {0, 0, 3, 110}

-- combiningLatinSmallLetterX BMPString ::= {0, 0, 3, 111}

-- greekNumeralSign BMPString ::= {0, 0, 3, 116}

-- greekLowerNumeralSign BMPString ::= {0, 0, 3, 117}

-- greekYpogegrammeni BMPString ::= {0, 0, 3, 122}

-- greekQuestionMark BMPString ::= {0, 0, 3, 126}

-- greekTonos BMPString ::= {0, 0, 3, 132}

-- greekDialytikaTonos BMPString ::= {0, 0, 3, 133}

-- greekCapitalLetterAlphaWithTonos BMPString ::= {0, 0, 3, 134}

-- greekAnoTeleia BMPString ::= {0, 0, 3, 135}

-- greekCapitalLetterEpsilonWithTonos BMPString ::= {0, 0, 3, 136}

-- greekCapitalLetterEtaWithTonos BMPString ::= {0, 0, 3, 137}

-- greekCapitalLetterIotaWithTonos BMPString ::= {0, 0, 3, 138}

-- greekCapitalLetterOmicronWithTonos BMPString ::= {0, 0, 3, 140}

-- greekCapitalLetterUpsilonWithTonos BMPString ::= {0, 0, 3, 142}

-- greekCapitalLetterOmegaWithTonos BMPString ::= {0, 0, 3, 143}

-- greekSmallLetterIotaWithDialytikaAndTonos BMPString ::= {0, 0, 3, 144}

-- greekCapitalLetterAlpha BMPString ::= {0, 0, 3, 145}

-- greekCapitalLetterBeta BMPString ::= {0, 0, 3, 146}

-- greekCapitalLetterGamma BMPString ::= {0, 0, 3, 147}

-- greekCapitalLetterDelta BMPString ::= {0, 0, 3, 148}

-- greekCapitalLetterEpsilon BMPString ::= {0, 0, 3, 149}

-- greekCapitalLetterZeta BMPString ::= {0, 0, 3, 150}

-- greekCapitalLetterEta BMPString ::= {0, 0, 3, 151}

-- greekCapitalLetterTheta BMPString ::= {0, 0, 3, 152}

-- greekCapitalLetterIota BMPString ::= {0, 0, 3, 153}

-- greekCapitalLetterKappa BMPString ::= {0, 0, 3, 154}

-- greekCapitalLetterLamda BMPString ::= {0, 0, 3, 155}

-- greekCapitalLetterMu BMPString ::= {0, 0, 3, 156}

-- greekCapitalLetterNu BMPString ::= {0, 0, 3, 157}

-- greekCapitalLetterXi BMPString ::= {0, 0, 3, 158}

-- greekCapitalLetterOmicron BMPString ::= {0, 0, 3, 159}

-- greekCapitalLetterPi BMPString ::= {0, 0, 3, 160}

-- greekCapitalLetterRho BMPString ::= {0, 0, 3, 161}

-- greekCapitalLetterSigma BMPString ::= {0, 0, 3, 163}

-- greekCapitalLetterTau BMPString ::= {0, 0, 3, 164}

-- greekCapitalLetterUpsilon BMPString ::= {0, 0, 3, 165}

-- greekCapitalLetterPhi BMPString ::= {0, 0, 3, 166}

-- greekCapitalLetterChi BMPString ::= {0, 0, 3, 167}

-- greekCapitalLetterPsi BMPString ::= {0, 0, 3, 168}

-- greekCapitalLetterOmega BMPString ::= {0, 0, 3, 169}

-- greekCapitalLetterIotaWithDialytika BMPString ::= {0, 0, 3, 170}

-- greekCapitalLetterUpsilonWithDialytika BMPString ::= {0, 0, 3, 171}

-- greekSmallLetterAlphaWithTonos BMPString ::= {0, 0, 3, 172}

-- greekSmallLetterEpsilonWithTonos BMPString ::= {0, 0, 3, 173}

-- greekSmallLetterEtaWithTonos BMPString ::= {0, 0, 3, 174}

-- greekSmallLetterIotaWithTonos BMPString ::= {0, 0, 3, 175}

-- greekSmallLetterUpsilonWithDialytikaAndTonos BMPString ::= {0, 0, 3, 176}

-- greekSmallLetterAlpha BMPString ::= {0, 0, 3, 177}

-- greekSmallLetterBeta BMPString ::= {0, 0, 3, 178}

-- greekSmallLetterGamma BMPString ::= {0, 0, 3, 179}

-- greekSmallLetterDelta BMPString ::= {0, 0, 3, 180}

-- greekSmallLetterEpsilon BMPString ::= {0, 0, 3, 181}

-- greekSmallLetterZeta BMPString ::= {0, 0, 3, 182}

-- greekSmallLetterEta BMPString ::= {0, 0, 3, 183}

-- greekSmallLetterTheta BMPString ::= {0, 0, 3, 184}

-- greekSmallLetterIota BMPString ::= {0, 0, 3, 185}

-- greekSmallLetterKappa BMPString ::= {0, 0, 3, 186}

-- greekSmallLetterLamda BMPString ::= {0, 0, 3, 187}

-- greekSmallLetterMu BMPString ::= {0, 0, 3, 188}

-- greekSmallLetterNu BMPString ::= {0, 0, 3, 189}

-- greekSmallLetterXi BMPString ::= {0, 0, 3, 190}

-- greekSmallLetterOmicron BMPString ::= {0, 0, 3, 191}

-- greekSmallLetterPi BMPString ::= {0, 0, 3, 192}

-- greekSmallLetterRho BMPString ::= {0, 0, 3, 193}

-- greekSmallLetterFinalSigma BMPString ::= {0, 0, 3, 194}

-- greekSmallLetterSigma BMPString ::= {0, 0, 3, 195}

-- greekSmallLetterTau BMPString ::= {0, 0, 3, 196}

-- greekSmallLetterUpsilon BMPString ::= {0, 0, 3, 197}

-- greekSmallLetterPhi BMPString ::= {0, 0, 3, 198}

-- greekSmallLetterChi BMPString ::= {0, 0, 3, 199}

-- greekSmallLetterPsi BMPString ::= {0, 0, 3, 200}

-- greekSmallLetterOmega BMPString ::= {0, 0, 3, 201}

-- greekSmallLetterIotaWithDialytika BMPString ::= {0, 0, 3, 202}

-- greekSmallLetterUpsilonWithDialytika BMPString ::= {0, 0, 3, 203}

-- greekSmallLetterOmicronWithTonos BMPString ::= {0, 0, 3, 204}

-- greekSmallLetterUpsilonWithTonos BMPString ::= {0, 0, 3, 205}

-- greekSmallLetterOmegaWithTonos BMPString ::= {0, 0, 3, 206}

-- greekBetaSymbol BMPString ::= {0, 0, 3, 208}

-- greekThetaSymbol BMPString ::= {0, 0, 3, 209}

-- greekUpsilonWithHookSymbol BMPString ::= {0, 0, 3, 210}

-- greekUpsilonWithAcuteAndHookSymbol BMPString ::= {0, 0, 3, 211}

-- greekUpsilonWithDiaeresisAndHookSymbol BMPString ::= {0, 0, 3, 212}

-- greekPhiSymbol BMPString ::= {0, 0, 3, 213}

-- greekPiSymbol BMPString ::= {0, 0, 3, 214}

-- greekKaiSymbol BMPString ::= {0, 0, 3, 215}

-- greekLetterArchaicKoppa BMPString ::= {0, 0, 3, 216}

-- greekSmallLetterArchaicKoppa BMPString ::= {0, 0, 3, 217}

-- greekLetterStigma BMPString ::= {0, 0, 3, 218}

-- greekSmallLetterStigma BMPString ::= {0, 0, 3, 219}

-- greekLetterDigamma BMPString ::= {0, 0, 3, 220}

-- greekSmallLetterDigamma BMPString ::= {0, 0, 3, 221}

-- greekLetterKoppa BMPString ::= {0, 0, 3, 222}

-- greekSmallLetterKoppa BMPString ::= {0, 0, 3, 223}

-- greekLetterSampi BMPString ::= {0, 0, 3, 224}

-- greekSmallLetterSampi BMPString ::= {0, 0, 3, 225}

-- copticCapitalLetterShei BMPString ::= {0, 0, 3, 226}

-- copticSmallLetterShei BMPString ::= {0, 0, 3, 227}

-- copticCapitalLetterFei BMPString ::= {0, 0, 3, 228}

-- copticSmallLetterFei BMPString ::= {0, 0, 3, 229}

-- copticCapitalLetterKhei BMPString ::= {0, 0, 3, 230}

-- copticSmallLetterKhei BMPString ::= {0, 0, 3, 231}

-- copticCapitalLetterHori BMPString ::= {0, 0, 3, 232}

-- copticSmallLetterHori BMPString ::= {0, 0, 3, 233}

-- copticCapitalLetterGangia BMPString ::= {0, 0, 3, 234}

-- copticSmallLetterGangia BMPString ::= {0, 0, 3, 235}

-- copticCapitalLetterShima BMPString ::= {0, 0, 3, 236}

-- copticSmallLetterShima BMPString ::= {0, 0, 3, 237}

-- copticCapitalLetterDei BMPString ::= {0, 0, 3, 238}

-- copticSmallLetterDei BMPString ::= {0, 0, 3, 239}

-- greekKappaSymbol BMPString ::= {0, 0, 3, 240}

-- greekRhoSymbol BMPString ::= {0, 0, 3, 241}

-- greekLunateSigmaSymbol BMPString ::= {0, 0, 3, 242}

-- greekLetterYot BMPString ::= {0, 0, 3, 243}

-- greekCapitalThetaSymbol BMPString ::= {0, 0, 3, 244}

-- greekLunateEpsilonSymbol BMPString ::= {0, 0, 3, 245}

-- greekReversedLunateEpsilonSymbol BMPString ::= {0, 0, 3, 246}

-- cyrillicCapitalLetterIeWithGrave BMPString ::= {0, 0, 4, 0}

-- cyrillicCapitalLetterIo BMPString ::= {0, 0, 4, 1}

-- cyrillicCapitalLetterDje BMPString ::= {0, 0, 4, 2}

-- cyrillicCapitalLetterGje BMPString ::= {0, 0, 4, 3}

-- cyrillicCapitalLetterUkrainianIe BMPString ::= {0, 0, 4, 4}

-- cyrillicCapitalLetterDze BMPString ::= {0, 0, 4, 5}

-- cyrillicCapitalLetterByelorussian-ukrainianI BMPString ::= {0, 0, 4, 6}

-- cyrillicCapitalLetterYi BMPString ::= {0, 0, 4, 7}

-- cyrillicCapitalLetterJe BMPString ::= {0, 0, 4, 8}

-- cyrillicCapitalLetterLje BMPString ::= {0, 0, 4, 9}

-- cyrillicCapitalLetterNje BMPString ::= {0, 0, 4, 10}

-- cyrillicCapitalLetterTshe BMPString ::= {0, 0, 4, 11}

-- cyrillicCapitalLetterKje BMPString ::= {0, 0, 4, 12}

-- cyrillicCapitalLetterIWithGrave BMPString ::= {0, 0, 4, 13}

-- cyrillicCapitalLetterShortU BMPString ::= {0, 0, 4, 14}

-- cyrillicCapitalLetterDzhe BMPString ::= {0, 0, 4, 15}

-- cyrillicCapitalLetterA BMPString ::= {0, 0, 4, 16}

-- cyrillicCapitalLetterBe BMPString ::= {0, 0, 4, 17}

-- cyrillicCapitalLetterVe BMPString ::= {0, 0, 4, 18}

-- cyrillicCapitalLetterGhe BMPString ::= {0, 0, 4, 19}

-- cyrillicCapitalLetterDe BMPString ::= {0, 0, 4, 20}

-- cyrillicCapitalLetterIe BMPString ::= {0, 0, 4, 21}

-- cyrillicCapitalLetterZhe BMPString ::= {0, 0, 4, 22}

-- cyrillicCapitalLetterZe BMPString ::= {0, 0, 4, 23}

-- cyrillicCapitalLetterI BMPString ::= {0, 0, 4, 24}

-- cyrillicCapitalLetterShortI BMPString ::= {0, 0, 4, 25}

-- cyrillicCapitalLetterKa BMPString ::= {0, 0, 4, 26}

-- cyrillicCapitalLetterEl BMPString ::= {0, 0, 4, 27}

-- cyrillicCapitalLetterEm BMPString ::= {0, 0, 4, 28}

-- cyrillicCapitalLetterEn BMPString ::= {0, 0, 4, 29}

-- cyrillicCapitalLetterO BMPString ::= {0, 0, 4, 30}

-- cyrillicCapitalLetterPe BMPString ::= {0, 0, 4, 31}

-- cyrillicCapitalLetterEr BMPString ::= {0, 0, 4, 32}

-- cyrillicCapitalLetterEs BMPString ::= {0, 0, 4, 33}

-- cyrillicCapitalLetterTe BMPString ::= {0, 0, 4, 34}

-- cyrillicCapitalLetterU BMPString ::= {0, 0, 4, 35}

-- cyrillicCapitalLetterEf BMPString ::= {0, 0, 4, 36}

-- cyrillicCapitalLetterHa BMPString ::= {0, 0, 4, 37}

-- cyrillicCapitalLetterTse BMPString ::= {0, 0, 4, 38}

-- cyrillicCapitalLetterChe BMPString ::= {0, 0, 4, 39}

-- cyrillicCapitalLetterSha BMPString ::= {0, 0, 4, 40}

-- cyrillicCapitalLetterShcha BMPString ::= {0, 0, 4, 41}

-- cyrillicCapitalLetterHardSign BMPString ::= {0, 0, 4, 42}

-- cyrillicCapitalLetterYeru BMPString ::= {0, 0, 4, 43}

-- cyrillicCapitalLetterSoftSign BMPString ::= {0, 0, 4, 44}

-- cyrillicCapitalLetterE BMPString ::= {0, 0, 4, 45}

-- cyrillicCapitalLetterYu BMPString ::= {0, 0, 4, 46}

-- cyrillicCapitalLetterYa BMPString ::= {0, 0, 4, 47}

-- cyrillicSmallLetterA BMPString ::= {0, 0, 4, 48}

-- cyrillicSmallLetterBe BMPString ::= {0, 0, 4, 49}

-- cyrillicSmallLetterVe BMPString ::= {0, 0, 4, 50}

-- cyrillicSmallLetterGhe BMPString ::= {0, 0, 4, 51}

-- cyrillicSmallLetterDe BMPString ::= {0, 0, 4, 52}

-- cyrillicSmallLetterIe BMPString ::= {0, 0, 4, 53}

-- cyrillicSmallLetterZhe BMPString ::= {0, 0, 4, 54}

-- cyrillicSmallLetterZe BMPString ::= {0, 0, 4, 55}

-- cyrillicSmallLetterI BMPString ::= {0, 0, 4, 56}

-- cyrillicSmallLetterShortI BMPString ::= {0, 0, 4, 57}

-- cyrillicSmallLetterKa BMPString ::= {0, 0, 4, 58}

-- cyrillicSmallLetterEl BMPString ::= {0, 0, 4, 59}

-- cyrillicSmallLetterEm BMPString ::= {0, 0, 4, 60}

-- cyrillicSmallLetterEn BMPString ::= {0, 0, 4, 61}

-- cyrillicSmallLetterO BMPString ::= {0, 0, 4, 62}

-- cyrillicSmallLetterPe BMPString ::= {0, 0, 4, 63}

-- cyrillicSmallLetterEr BMPString ::= {0, 0, 4, 64}

-- cyrillicSmallLetterEs BMPString ::= {0, 0, 4, 65}

-- cyrillicSmallLetterTe BMPString ::= {0, 0, 4, 66}

-- cyrillicSmallLetterU BMPString ::= {0, 0, 4, 67}

-- cyrillicSmallLetterEf BMPString ::= {0, 0, 4, 68}

-- cyrillicSmallLetterHa BMPString ::= {0, 0, 4, 69}

-- cyrillicSmallLetterTse BMPString ::= {0, 0, 4, 70}

-- cyrillicSmallLetterChe BMPString ::= {0, 0, 4, 71}

-- cyrillicSmallLetterSha BMPString ::= {0, 0, 4, 72}

-- cyrillicSmallLetterShcha BMPString ::= {0, 0, 4, 73}

-- cyrillicSmallLetterHardSign BMPString ::= {0, 0, 4, 74}

-- cyrillicSmallLetterYeru BMPString ::= {0, 0, 4, 75}

-- cyrillicSmallLetterSoftSign BMPString ::= {0, 0, 4, 76}

-- cyrillicSmallLetterE BMPString ::= {0, 0, 4, 77}

-- cyrillicSmallLetterYu BMPString ::= {0, 0, 4, 78}

-- cyrillicSmallLetterYa BMPString ::= {0, 0, 4, 79}

-- cyrillicSmallLetterIeWithGrave BMPString ::= {0, 0, 4, 80}

-- cyrillicSmallLetterIo BMPString ::= {0, 0, 4, 81}

-- cyrillicSmallLetterDje BMPString ::= {0, 0, 4, 82}

-- cyrillicSmallLetterGje BMPString ::= {0, 0, 4, 83}

-- cyrillicSmallLetterUkrainianIe BMPString ::= {0, 0, 4, 84}

-- cyrillicSmallLetterDze BMPString ::= {0, 0, 4, 85}

-- cyrillicSmallLetterByelorussian-ukrainianI BMPString ::= {0, 0, 4, 86}

-- cyrillicSmallLetterYi BMPString ::= {0, 0, 4, 87}

-- cyrillicSmallLetterJe BMPString ::= {0, 0, 4, 88}

-- cyrillicSmallLetterLje BMPString ::= {0, 0, 4, 89}

-- cyrillicSmallLetterNje BMPString ::= {0, 0, 4, 90}

-- cyrillicSmallLetterTshe BMPString ::= {0, 0, 4, 91}

-- cyrillicSmallLetterKje BMPString ::= {0, 0, 4, 92}

-- cyrillicSmallLetterIWithGrave BMPString ::= {0, 0, 4, 93}

-- cyrillicSmallLetterShortU BMPString ::= {0, 0, 4, 94}

-- cyrillicSmallLetterDzhe BMPString ::= {0, 0, 4, 95}

-- cyrillicCapitalLetterOmega BMPString ::= {0, 0, 4, 96}

-- cyrillicSmallLetterOmega BMPString ::= {0, 0, 4, 97}

-- cyrillicCapitalLetterYat BMPString ::= {0, 0, 4, 98}

-- cyrillicSmallLetterYat BMPString ::= {0, 0, 4, 99}

-- cyrillicCapitalLetterIotifiedE BMPString ::= {0, 0, 4, 100}

-- cyrillicSmallLetterIotifiedE BMPString ::= {0, 0, 4, 101}

-- cyrillicCapitalLetterLittleYus BMPString ::= {0, 0, 4, 102}

-- cyrillicSmallLetterLittleYus BMPString ::= {0, 0, 4, 103}

-- cyrillicCapitalLetterIotifiedLittleYus BMPString ::= {0, 0, 4, 104}

-- cyrillicSmallLetterIotifiedLittleYus BMPString ::= {0, 0, 4, 105}

-- cyrillicCapitalLetterBigYus BMPString ::= {0, 0, 4, 106}

-- cyrillicSmallLetterBigYus BMPString ::= {0, 0, 4, 107}

-- cyrillicCapitalLetterIotifiedBigYus BMPString ::= {0, 0, 4, 108}

-- cyrillicSmallLetterIotifiedBigYus BMPString ::= {0, 0, 4, 109}

-- cyrillicCapitalLetterKsi BMPString ::= {0, 0, 4, 110}

-- cyrillicSmallLetterKsi BMPString ::= {0, 0, 4, 111}

-- cyrillicCapitalLetterPsi BMPString ::= {0, 0, 4, 112}

-- cyrillicSmallLetterPsi BMPString ::= {0, 0, 4, 113}

-- cyrillicCapitalLetterFita BMPString ::= {0, 0, 4, 114}

-- cyrillicSmallLetterFita BMPString ::= {0, 0, 4, 115}

-- cyrillicCapitalLetterIzhitsa BMPString ::= {0, 0, 4, 116}

-- cyrillicSmallLetterIzhitsa BMPString ::= {0, 0, 4, 117}

-- cyrillicCapitalLetterIzhitsaWithDoubleGraveAccent BMPString ::= {0, 0, 4, 118}

-- cyrillicSmallLetterIzhitsaWithDoubleGraveAccent BMPString ::= {0, 0, 4, 119}

-- cyrillicCapitalLetterUk BMPString ::= {0, 0, 4, 120}

-- cyrillicSmallLetterUk BMPString ::= {0, 0, 4, 121}

-- cyrillicCapitalLetterRoundOmega BMPString ::= {0, 0, 4, 122}

-- cyrillicSmallLetterRoundOmega BMPString ::= {0, 0, 4, 123}

-- cyrillicCapitalLetterOmegaWithTitlo BMPString ::= {0, 0, 4, 124}

-- cyrillicSmallLetterOmegaWithTitlo BMPString ::= {0, 0, 4, 125}

-- cyrillicCapitalLetterOt BMPString ::= {0, 0, 4, 126}

-- cyrillicSmallLetterOt BMPString ::= {0, 0, 4, 127}

-- cyrillicCapitalLetterKoppa BMPString ::= {0, 0, 4, 128}

-- cyrillicSmallLetterKoppa BMPString ::= {0, 0, 4, 129}

-- cyrillicThousandsSign BMPString ::= {0, 0, 4, 130}

-- combiningCyrillicTitlo BMPString ::= {0, 0, 4, 131}

-- combiningCyrillicPalatalization BMPString ::= {0, 0, 4, 132}

-- combiningCyrillicDasiaPneumata BMPString ::= {0, 0, 4, 133}

-- combiningCyrillicPsiliPneumata BMPString ::= {0, 0, 4, 134}

-- combiningCyrillicHundredThousandsSign BMPString ::= {0, 0, 4, 136}

-- combiningCyrillicMillionsSign BMPString ::= {0, 0, 4, 137}

-- cyrillicCapitalLetterShortIWithTail BMPString ::= {0, 0, 4, 138}

-- cyrillicSmallLetterShortIWithTail BMPString ::= {0, 0, 4, 139}

-- cyrillicCapitalLetterSemisoftSign BMPString ::= {0, 0, 4, 140}

-- cyrillicSmallLetterSemisoftSign BMPString ::= {0, 0, 4, 141}

-- cyrillicCapitalLetterErWithTick BMPString ::= {0, 0, 4, 142}

-- cyrillicSmallLetterErWithTick BMPString ::= {0, 0, 4, 143}

-- cyrillicCapitalLetterGheWithUpturn BMPString ::= {0, 0, 4, 144}

-- cyrillicSmallLetterGheWithUpturn BMPString ::= {0, 0, 4, 145}

-- cyrillicCapitalLetterGheWithStroke BMPString ::= {0, 0, 4, 146}

-- cyrillicSmallLetterGheWithStroke BMPString ::= {0, 0, 4, 147}

-- cyrillicCapitalLetterGheWithMiddleHook BMPString ::= {0, 0, 4, 148}

-- cyrillicSmallLetterGheWithMiddleHook BMPString ::= {0, 0, 4, 149}

-- cyrillicCapitalLetterZheWithDescender BMPString ::= {0, 0, 4, 150}

-- cyrillicSmallLetterZheWithDescender BMPString ::= {0, 0, 4, 151}

-- cyrillicCapitalLetterZeWithDescender BMPString ::= {0, 0, 4, 152}

-- cyrillicSmallLetterZeWithDescender BMPString ::= {0, 0, 4, 153}

-- cyrillicCapitalLetterKaWithDescender BMPString ::= {0, 0, 4, 154}

-- cyrillicSmallLetterKaWithDescender BMPString ::= {0, 0, 4, 155}

-- cyrillicCapitalLetterKaWithVerticalStroke BMPString ::= {0, 0, 4, 156}

-- cyrillicSmallLetterKaWithVerticalStroke BMPString ::= {0, 0, 4, 157}

-- cyrillicCapitalLetterKaWithStroke BMPString ::= {0, 0, 4, 158}

-- cyrillicSmallLetterKaWithStroke BMPString ::= {0, 0, 4, 159}

-- cyrillicCapitalLetterBashkirKa BMPString ::= {0, 0, 4, 160}

-- cyrillicSmallLetterBashkirKa BMPString ::= {0, 0, 4, 161}

-- cyrillicCapitalLetterEnWithDescender BMPString ::= {0, 0, 4, 162}

-- cyrillicSmallLetterEnWithDescender BMPString ::= {0, 0, 4, 163}

-- cyrillicCapitalLigatureEnGhe BMPString ::= {0, 0, 4, 164}

-- cyrillicSmallLigatureEnGhe BMPString ::= {0, 0, 4, 165}

-- cyrillicCapitalLetterPeWithMiddleHook BMPString ::= {0, 0, 4, 166}

-- cyrillicSmallLetterPeWithMiddleHook BMPString ::= {0, 0, 4, 167}

-- cyrillicCapitalLetterAbkhasianHa BMPString ::= {0, 0, 4, 168}

-- cyrillicSmallLetterAbkhasianHa BMPString ::= {0, 0, 4, 169}

-- cyrillicCapitalLetterEsWithDescender BMPString ::= {0, 0, 4, 170}

-- cyrillicSmallLetterEsWithDescender BMPString ::= {0, 0, 4, 171}

-- cyrillicCapitalLetterTeWithDescender BMPString ::= {0, 0, 4, 172}

-- cyrillicSmallLetterTeWithDescender BMPString ::= {0, 0, 4, 173}

-- cyrillicCapitalLetterStraightU BMPString ::= {0, 0, 4, 174}

-- cyrillicSmallLetterStraightU BMPString ::= {0, 0, 4, 175}

-- cyrillicCapitalLetterStraightUWithStroke BMPString ::= {0, 0, 4, 176}

-- cyrillicSmallLetterStraightUWithStroke BMPString ::= {0, 0, 4, 177}

-- cyrillicCapitalLetterHaWithDescender BMPString ::= {0, 0, 4, 178}

-- cyrillicSmallLetterHaWithDescender BMPString ::= {0, 0, 4, 179}

-- cyrillicCapitalLigatureTeTse BMPString ::= {0, 0, 4, 180}

-- cyrillicSmallLigatureTeTse BMPString ::= {0, 0, 4, 181}

-- cyrillicCapitalLetterCheWithDescender BMPString ::= {0, 0, 4, 182}

-- cyrillicSmallLetterCheWithDescender BMPString ::= {0, 0, 4, 183}

-- cyrillicCapitalLetterCheWithVerticalStroke BMPString ::= {0, 0, 4, 184}

-- cyrillicSmallLetterCheWithVerticalStroke BMPString ::= {0, 0, 4, 185}

-- cyrillicCapitalLetterShha BMPString ::= {0, 0, 4, 186}

-- cyrillicSmallLetterShha BMPString ::= {0, 0, 4, 187}

-- cyrillicCapitalLetterAbkhasianChe BMPString ::= {0, 0, 4, 188}

-- cyrillicSmallLetterAbkhasianChe BMPString ::= {0, 0, 4, 189}

-- cyrillicCapitalLetterAbkhasianCheWithDescender BMPString ::= {0, 0, 4, 190}

-- cyrillicSmallLetterAbkhasianCheWithDescender BMPString ::= {0, 0, 4, 191}

-- cyrillicLetterPalochka BMPString ::= {0, 0, 4, 192}

-- cyrillicCapitalLetterZheWithBreve BMPString ::= {0, 0, 4, 193}

-- cyrillicSmallLetterZheWithBreve BMPString ::= {0, 0, 4, 194}

-- cyrillicCapitalLetterKaWithHook BMPString ::= {0, 0, 4, 195}

-- cyrillicSmallLetterKaWithHook BMPString ::= {0, 0, 4, 196}

-- cyrillicCapitalLetterElWithTail BMPString ::= {0, 0, 4, 197}

-- cyrillicSmallLetterElWithTail BMPString ::= {0, 0, 4, 198}

-- cyrillicCapitalLetterEnWithHook BMPString ::= {0, 0, 4, 199}

-- cyrillicSmallLetterEnWithHook BMPString ::= {0, 0, 4, 200}

-- cyrillicCapitalLetterEnWithTail BMPString ::= {0, 0, 4, 201}

-- cyrillicSmallLetterEnWithTail BMPString ::= {0, 0, 4, 202}

-- cyrillicCapitalLetterKhakassianChe BMPString ::= {0, 0, 4, 203}

-- cyrillicSmallLetterKhakassianChe BMPString ::= {0, 0, 4, 204}

-- cyrillicCapitalLetterEmWithTail BMPString ::= {0, 0, 4, 205}

-- cyrillicSmallLetterEmWithTail BMPString ::= {0, 0, 4, 206}

-- cyrillicCapitalLetterAWithBreve BMPString ::= {0, 0, 4, 208}

-- cyrillicSmallLetterAWithBreve BMPString ::= {0, 0, 4, 209}

-- cyrillicCapitalLetterAWithDiaeresis BMPString ::= {0, 0, 4, 210}

-- cyrillicSmallLetterAWithDiaeresis BMPString ::= {0, 0, 4, 211}

-- cyrillicCapitalLigatureAIe BMPString ::= {0, 0, 4, 212}

-- cyrillicSmallLigatureAIe BMPString ::= {0, 0, 4, 213}

-- cyrillicCapitalLetterIeWithBreve BMPString ::= {0, 0, 4, 214}

-- cyrillicSmallLetterIeWithBreve BMPString ::= {0, 0, 4, 215}

-- cyrillicCapitalLetterSchwa BMPString ::= {0, 0, 4, 216}

-- cyrillicSmallLetterSchwa BMPString ::= {0, 0, 4, 217}

-- cyrillicCapitalLetterSchwaWithDiaeresis BMPString ::= {0, 0, 4, 218}

-- cyrillicSmallLetterSchwaWithDiaeresis BMPString ::= {0, 0, 4, 219}

-- cyrillicCapitalLetterZheWithDiaeresis BMPString ::= {0, 0, 4, 220}

-- cyrillicSmallLetterZheWithDiaeresis BMPString ::= {0, 0, 4, 221}

-- cyrillicCapitalLetterZeWithDiaeresis BMPString ::= {0, 0, 4, 222}

-- cyrillicSmallLetterZeWithDiaeresis BMPString ::= {0, 0, 4, 223}

-- cyrillicCapitalLetterAbkhasianDze BMPString ::= {0, 0, 4, 224}

-- cyrillicSmallLetterAbkhasianDze BMPString ::= {0, 0, 4, 225}

-- cyrillicCapitalLetterIWithMacron BMPString ::= {0, 0, 4, 226}

-- cyrillicSmallLetterIWithMacron BMPString ::= {0, 0, 4, 227}

-- cyrillicCapitalLetterIWithDiaeresis BMPString ::= {0, 0, 4, 228}

-- cyrillicSmallLetterIWithDiaeresis BMPString ::= {0, 0, 4, 229}

-- cyrillicCapitalLetterOWithDiaeresis BMPString ::= {0, 0, 4, 230}

-- cyrillicSmallLetterOWithDiaeresis BMPString ::= {0, 0, 4, 231}

-- cyrillicCapitalLetterBarredO BMPString ::= {0, 0, 4, 232}

-- cyrillicSmallLetterBarredO BMPString ::= {0, 0, 4, 233}

-- cyrillicCapitalLetterBarredOWithDiaeresis BMPString ::= {0, 0, 4, 234}

-- cyrillicSmallLetterBarredOWithDiaeresis BMPString ::= {0, 0, 4, 235}

-- cyrillicCapitalLetterEWithDiaeresis BMPString ::= {0, 0, 4, 236}

-- cyrillicSmallLetterEWithDiaeresis BMPString ::= {0, 0, 4, 237}

-- cyrillicCapitalLetterUWithMacron BMPString ::= {0, 0, 4, 238}

-- cyrillicSmallLetterUWithMacron BMPString ::= {0, 0, 4, 239}

-- cyrillicCapitalLetterUWithDiaeresis BMPString ::= {0, 0, 4, 240}

-- cyrillicSmallLetterUWithDiaeresis BMPString ::= {0, 0, 4, 241}

-- cyrillicCapitalLetterUWithDoubleAcute BMPString ::= {0, 0, 4, 242}

-- cyrillicSmallLetterUWithDoubleAcute BMPString ::= {0, 0, 4, 243}

-- cyrillicCapitalLetterCheWithDiaeresis BMPString ::= {0, 0, 4, 244}

-- cyrillicSmallLetterCheWithDiaeresis BMPString ::= {0, 0, 4, 245}

-- cyrillicCapitalLetterYeruWithDiaeresis BMPString ::= {0, 0, 4, 248}

-- cyrillicSmallLetterYeruWithDiaeresis BMPString ::= {0, 0, 4, 249}

-- cyrillicCapitalLetterKomiDe BMPString ::= {0, 0, 5, 0}

-- cyrillicSmallLetterKomiDe BMPString ::= {0, 0, 5, 1}

-- cyrillicCapitalLetterKomiDje BMPString ::= {0, 0, 5, 2}

-- cyrillicSmallLetterKomiDje BMPString ::= {0, 0, 5, 3}

-- cyrillicCapitalLetterKomiZje BMPString ::= {0, 0, 5, 4}

-- cyrillicSmallLetterKomiZje BMPString ::= {0, 0, 5, 5}

-- cyrillicCapitalLetterKomiDzje BMPString ::= {0, 0, 5, 6}

-- cyrillicSmallLetterKomiDzje BMPString ::= {0, 0, 5, 7}

-- cyrillicCapitalLetterKomiLje BMPString ::= {0, 0, 5, 8}

-- cyrillicSmallLetterKomiLje BMPString ::= {0, 0, 5, 9}

-- cyrillicCapitalLetterKomiNje BMPString ::= {0, 0, 5, 10}

-- cyrillicSmallLetterKomiNje BMPString ::= {0, 0, 5, 11}

-- cyrillicCapitalLetterKomiSje BMPString ::= {0, 0, 5, 12}

-- cyrillicSmallLetterKomiSje BMPString ::= {0, 0, 5, 13}

-- cyrillicCapitalLetterKomiTje BMPString ::= {0, 0, 5, 14}

-- cyrillicSmallLetterKomiTje BMPString ::= {0, 0, 5, 15}

-- armenianCapitalLetterAyb BMPString ::= {0, 0, 5, 49}

-- armenianCapitalLetterBen BMPString ::= {0, 0, 5, 50}

-- armenianCapitalLetterGim BMPString ::= {0, 0, 5, 51}

-- armenianCapitalLetterDa BMPString ::= {0, 0, 5, 52}

-- armenianCapitalLetterEch BMPString ::= {0, 0, 5, 53}

-- armenianCapitalLetterZa BMPString ::= {0, 0, 5, 54}

-- armenianCapitalLetterEh BMPString ::= {0, 0, 5, 55}

-- armenianCapitalLetterEt BMPString ::= {0, 0, 5, 56}

-- armenianCapitalLetterTo BMPString ::= {0, 0, 5, 57}

-- armenianCapitalLetterZhe BMPString ::= {0, 0, 5, 58}

-- armenianCapitalLetterIni BMPString ::= {0, 0, 5, 59}

-- armenianCapitalLetterLiwn BMPString ::= {0, 0, 5, 60}

-- armenianCapitalLetterXeh BMPString ::= {0, 0, 5, 61}

-- armenianCapitalLetterCa BMPString ::= {0, 0, 5, 62}

-- armenianCapitalLetterKen BMPString ::= {0, 0, 5, 63}

-- armenianCapitalLetterHo BMPString ::= {0, 0, 5, 64}

-- armenianCapitalLetterJa BMPString ::= {0, 0, 5, 65}

-- armenianCapitalLetterGhad BMPString ::= {0, 0, 5, 66}

-- armenianCapitalLetterCheh BMPString ::= {0, 0, 5, 67}

-- armenianCapitalLetterMen BMPString ::= {0, 0, 5, 68}

-- armenianCapitalLetterYi BMPString ::= {0, 0, 5, 69}

-- armenianCapitalLetterNow BMPString ::= {0, 0, 5, 70}

-- armenianCapitalLetterSha BMPString ::= {0, 0, 5, 71}

-- armenianCapitalLetterVo BMPString ::= {0, 0, 5, 72}

-- armenianCapitalLetterCha BMPString ::= {0, 0, 5, 73}

-- armenianCapitalLetterPeh BMPString ::= {0, 0, 5, 74}

-- armenianCapitalLetterJheh BMPString ::= {0, 0, 5, 75}

-- armenianCapitalLetterRa BMPString ::= {0, 0, 5, 76}

-- armenianCapitalLetterSeh BMPString ::= {0, 0, 5, 77}

-- armenianCapitalLetterVew BMPString ::= {0, 0, 5, 78}

-- armenianCapitalLetterTiwn BMPString ::= {0, 0, 5, 79}

-- armenianCapitalLetterReh BMPString ::= {0, 0, 5, 80}

-- armenianCapitalLetterCo BMPString ::= {0, 0, 5, 81}

-- armenianCapitalLetterYiwn BMPString ::= {0, 0, 5, 82}

-- armenianCapitalLetterPiwr BMPString ::= {0, 0, 5, 83}

-- armenianCapitalLetterKeh BMPString ::= {0, 0, 5, 84}

-- armenianCapitalLetterOh BMPString ::= {0, 0, 5, 85}

-- armenianCapitalLetterFeh BMPString ::= {0, 0, 5, 86}

-- armenianModifierLetterLeftHalfRing BMPString ::= {0, 0, 5, 89}

-- armenianApostrophe BMPString ::= {0, 0, 5, 90}

-- armenianEmphasisMark BMPString ::= {0, 0, 5, 91}

-- armenianExclamationMark BMPString ::= {0, 0, 5, 92}

-- armenianComma BMPString ::= {0, 0, 5, 93}

-- armenianQuestionMark BMPString ::= {0, 0, 5, 94}

-- armenianAbbreviationMark BMPString ::= {0, 0, 5, 95}

-- armenianSmallLetterAyb BMPString ::= {0, 0, 5, 97}

-- armenianSmallLetterBen BMPString ::= {0, 0, 5, 98}

-- armenianSmallLetterGim BMPString ::= {0, 0, 5, 99}

-- armenianSmallLetterDa BMPString ::= {0, 0, 5, 100}

-- armenianSmallLetterEch BMPString ::= {0, 0, 5, 101}

-- armenianSmallLetterZa BMPString ::= {0, 0, 5, 102}

-- armenianSmallLetterEh BMPString ::= {0, 0, 5, 103}

-- armenianSmallLetterEt BMPString ::= {0, 0, 5, 104}

-- armenianSmallLetterTo BMPString ::= {0, 0, 5, 105}

-- armenianSmallLetterZhe BMPString ::= {0, 0, 5, 106}

-- armenianSmallLetterIni BMPString ::= {0, 0, 5, 107}

-- armenianSmallLetterLiwn BMPString ::= {0, 0, 5, 108}

-- armenianSmallLetterXeh BMPString ::= {0, 0, 5, 109}

-- armenianSmallLetterCa BMPString ::= {0, 0, 5, 110}

-- armenianSmallLetterKen BMPString ::= {0, 0, 5, 111}

-- armenianSmallLetterHo BMPString ::= {0, 0, 5, 112}

-- armenianSmallLetterJa BMPString ::= {0, 0, 5, 113}

-- armenianSmallLetterGhad BMPString ::= {0, 0, 5, 114}

-- armenianSmallLetterCheh BMPString ::= {0, 0, 5, 115}

-- armenianSmallLetterMen BMPString ::= {0, 0, 5, 116}

-- armenianSmallLetterYi BMPString ::= {0, 0, 5, 117}

-- armenianSmallLetterNow BMPString ::= {0, 0, 5, 118}

-- armenianSmallLetterSha BMPString ::= {0, 0, 5, 119}

-- armenianSmallLetterVo BMPString ::= {0, 0, 5, 120}

-- armenianSmallLetterCha BMPString ::= {0, 0, 5, 121}

-- armenianSmallLetterPeh BMPString ::= {0, 0, 5, 122}

-- armenianSmallLetterJheh BMPString ::= {0, 0, 5, 123}

-- armenianSmallLetterRa BMPString ::= {0, 0, 5, 124}

-- armenianSmallLetterSeh BMPString ::= {0, 0, 5, 125}

-- armenianSmallLetterVew BMPString ::= {0, 0, 5, 126}

-- armenianSmallLetterTiwn BMPString ::= {0, 0, 5, 127}

-- armenianSmallLetterReh BMPString ::= {0, 0, 5, 128}

-- armenianSmallLetterCo BMPString ::= {0, 0, 5, 129}

-- armenianSmallLetterYiwn BMPString ::= {0, 0, 5, 130}

-- armenianSmallLetterPiwr BMPString ::= {0, 0, 5, 131}

-- armenianSmallLetterKeh BMPString ::= {0, 0, 5, 132}

-- armenianSmallLetterOh BMPString ::= {0, 0, 5, 133}

-- armenianSmallLetterFeh BMPString ::= {0, 0, 5, 134}

-- armenianSmallLigatureEchYiwn BMPString ::= {0, 0, 5, 135}

-- armenianFullStop BMPString ::= {0, 0, 5, 137}

-- armenianHyphen BMPString ::= {0, 0, 5, 138}

-- hebrewAccentEtnahta BMPString ::= {0, 0, 5, 145}

-- hebrewAccentSegol BMPString ::= {0, 0, 5, 146}

-- hebrewAccentShalshelet BMPString ::= {0, 0, 5, 147}

-- hebrewAccentZaqefQatan BMPString ::= {0, 0, 5, 148}

-- hebrewAccentZaqefGadol BMPString ::= {0, 0, 5, 149}

-- hebrewAccentTipeha BMPString ::= {0, 0, 5, 150}

-- hebrewAccentRevia BMPString ::= {0, 0, 5, 151}

-- hebrewAccentZarqa BMPString ::= {0, 0, 5, 152}

-- hebrewAccentPashta BMPString ::= {0, 0, 5, 153}

-- hebrewAccentYetiv BMPString ::= {0, 0, 5, 154}

-- hebrewAccentTevir BMPString ::= {0, 0, 5, 155}

-- hebrewAccentGeresh BMPString ::= {0, 0, 5, 156}

-- hebrewAccentGereshMuqdam BMPString ::= {0, 0, 5, 157}

-- hebrewAccentGershayim BMPString ::= {0, 0, 5, 158}

-- hebrewAccentQarneyPara BMPString ::= {0, 0, 5, 159}

-- hebrewAccentTelishaGedola BMPString ::= {0, 0, 5, 160}

-- hebrewAccentPazer BMPString ::= {0, 0, 5, 161}

-- hebrewAccentMunah BMPString ::= {0, 0, 5, 163}

-- hebrewAccentMahapakh BMPString ::= {0, 0, 5, 164}

-- hebrewAccentMerkha BMPString ::= {0, 0, 5, 165}

-- hebrewAccentMerkhaKefula BMPString ::= {0, 0, 5, 166}

-- hebrewAccentDarga BMPString ::= {0, 0, 5, 167}

-- hebrewAccentQadma BMPString ::= {0, 0, 5, 168}

-- hebrewAccentTelishaQetana BMPString ::= {0, 0, 5, 169}

-- hebrewAccentYerahBenYomo BMPString ::= {0, 0, 5, 170}

-- hebrewAccentOle BMPString ::= {0, 0, 5, 171}

-- hebrewAccentIluy BMPString ::= {0, 0, 5, 172}

-- hebrewAccentDehi BMPString ::= {0, 0, 5, 173}

-- hebrewAccentZinor BMPString ::= {0, 0, 5, 174}

-- hebrewMarkMasoraCircle BMPString ::= {0, 0, 5, 175}

-- hebrewPointSheva BMPString ::= {0, 0, 5, 176}

-- hebrewPointHatafSegol BMPString ::= {0, 0, 5, 177}

-- hebrewPointHatafPatah BMPString ::= {0, 0, 5, 178}

-- hebrewPointHatafQamats BMPString ::= {0, 0, 5, 179}

-- hebrewPointHiriq BMPString ::= {0, 0, 5, 180}

-- hebrewPointTsere BMPString ::= {0, 0, 5, 181}

-- hebrewPointSegol BMPString ::= {0, 0, 5, 182}

-- hebrewPointPatah BMPString ::= {0, 0, 5, 183}

-- hebrewPointQamats BMPString ::= {0, 0, 5, 184}

-- hebrewPointHolam BMPString ::= {0, 0, 5, 185}

-- hebrewPointQubuts BMPString ::= {0, 0, 5, 187}

-- hebrewPointDageshOrMapiq BMPString ::= {0, 0, 5, 188}

-- hebrewPointMeteg BMPString ::= {0, 0, 5, 189}

-- hebrewPunctuationMaqaf BMPString ::= {0, 0, 5, 190}

-- hebrewPointRafe BMPString ::= {0, 0, 5, 191}

-- hebrewPunctuationPaseq BMPString ::= {0, 0, 5, 192}

-- hebrewPointShinDot BMPString ::= {0, 0, 5, 193}

-- hebrewPointSinDot BMPString ::= {0, 0, 5, 194}

-- hebrewPunctuationSofPasuq BMPString ::= {0, 0, 5, 195}

-- hebrewMarkUpperDot BMPString ::= {0, 0, 5, 196}

-- hebrewLetterAlef BMPString ::= {0, 0, 5, 208}

-- hebrewLetterBet BMPString ::= {0, 0, 5, 209}

-- hebrewLetterGimel BMPString ::= {0, 0, 5, 210}

-- hebrewLetterDalet BMPString ::= {0, 0, 5, 211}

-- hebrewLetterHe BMPString ::= {0, 0, 5, 212}

-- hebrewLetterVav BMPString ::= {0, 0, 5, 213}

-- hebrewLetterZayin BMPString ::= {0, 0, 5, 214}

-- hebrewLetterHet BMPString ::= {0, 0, 5, 215}

-- hebrewLetterTet BMPString ::= {0, 0, 5, 216}

-- hebrewLetterYod BMPString ::= {0, 0, 5, 217}

-- hebrewLetterFinalKaf BMPString ::= {0, 0, 5, 218}

-- hebrewLetterKaf BMPString ::= {0, 0, 5, 219}

-- hebrewLetterLamed BMPString ::= {0, 0, 5, 220}

-- hebrewLetterFinalMem BMPString ::= {0, 0, 5, 221}

-- hebrewLetterMem BMPString ::= {0, 0, 5, 222}

-- hebrewLetterFinalNun BMPString ::= {0, 0, 5, 223}

-- hebrewLetterNun BMPString ::= {0, 0, 5, 224}

-- hebrewLetterSamekh BMPString ::= {0, 0, 5, 225}

-- hebrewLetterAyin BMPString ::= {0, 0, 5, 226}

-- hebrewLetterFinalPe BMPString ::= {0, 0, 5, 227}

-- hebrewLetterPe BMPString ::= {0, 0, 5, 228}

-- hebrewLetterFinalTsadi BMPString ::= {0, 0, 5, 229}

-- hebrewLetterTsadi BMPString ::= {0, 0, 5, 230}

-- hebrewLetterQof BMPString ::= {0, 0, 5, 231}

-- hebrewLetterResh BMPString ::= {0, 0, 5, 232}

-- hebrewLetterShin BMPString ::= {0, 0, 5, 233}

-- hebrewLetterTav BMPString ::= {0, 0, 5, 234}

-- hebrewLigatureYiddishDoubleVav BMPString ::= {0, 0, 5, 240}

-- hebrewLigatureYiddishVavYod BMPString ::= {0, 0, 5, 241}

-- hebrewLigatureYiddishDoubleYod BMPString ::= {0, 0, 5, 242}

-- hebrewPunctuationGeresh BMPString ::= {0, 0, 5, 243}

-- hebrewPunctuationGershayim BMPString ::= {0, 0, 5, 244}

-- arabicComma BMPString ::= {0, 0, 6, 12}

-- arabicSemicolon BMPString ::= {0, 0, 6, 27}

-- arabicQuestionMark BMPString ::= {0, 0, 6, 31}

-- arabicLetterHamza BMPString ::= {0, 0, 6, 33}

-- arabicLetterAlefWithMaddaAbove BMPString ::= {0, 0, 6, 34}

-- arabicLetterAlefWithHamzaAbove BMPString ::= {0, 0, 6, 35}

-- arabicLetterWawWithHamzaAbove BMPString ::= {0, 0, 6, 36}

-- arabicLetterAlefWithHamzaBelow BMPString ::= {0, 0, 6, 37}

-- arabicLetterYehWithHamzaAbove BMPString ::= {0, 0, 6, 38}

-- arabicLetterAlef BMPString ::= {0, 0, 6, 39}

-- arabicLetterBeh BMPString ::= {0, 0, 6, 40}

-- arabicLetterTehMarbuta BMPString ::= {0, 0, 6, 41}

-- arabicLetterTeh BMPString ::= {0, 0, 6, 42}

-- arabicLetterTheh BMPString ::= {0, 0, 6, 43}

-- arabicLetterJeem BMPString ::= {0, 0, 6, 44}

-- arabicLetterHah BMPString ::= {0, 0, 6, 45}

-- arabicLetterKhah BMPString ::= {0, 0, 6, 46}

-- arabicLetterDal BMPString ::= {0, 0, 6, 47}

-- arabicLetterThal BMPString ::= {0, 0, 6, 48}

-- arabicLetterReh BMPString ::= {0, 0, 6, 49}

-- arabicLetterZain BMPString ::= {0, 0, 6, 50}

-- arabicLetterSeen BMPString ::= {0, 0, 6, 51}

-- arabicLetterSheen BMPString ::= {0, 0, 6, 52}

-- arabicLetterSad BMPString ::= {0, 0, 6, 53}

-- arabicLetterDad BMPString ::= {0, 0, 6, 54}

-- arabicLetterTah BMPString ::= {0, 0, 6, 55}

-- arabicLetterZah BMPString ::= {0, 0, 6, 56}

-- arabicLetterAin BMPString ::= {0, 0, 6, 57}

-- arabicLetterGhain BMPString ::= {0, 0, 6, 58}

-- arabicTatweel BMPString ::= {0, 0, 6, 64}

-- arabicLetterFeh BMPString ::= {0, 0, 6, 65}

-- arabicLetterQaf BMPString ::= {0, 0, 6, 66}

-- arabicLetterKaf BMPString ::= {0, 0, 6, 67}

-- arabicLetterLam BMPString ::= {0, 0, 6, 68}

-- arabicLetterMeem BMPString ::= {0, 0, 6, 69}

-- arabicLetterNoon BMPString ::= {0, 0, 6, 70}

-- arabicLetterHeh BMPString ::= {0, 0, 6, 71}

-- arabicLetterWaw BMPString ::= {0, 0, 6, 72}

-- arabicLetterAlefMaksura BMPString ::= {0, 0, 6, 73}

-- arabicLetterYeh BMPString ::= {0, 0, 6, 74}

-- arabicFathatan BMPString ::= {0, 0, 6, 75}

-- arabicDammatan BMPString ::= {0, 0, 6, 76}

-- arabicKasratan BMPString ::= {0, 0, 6, 77}

-- arabicFatha BMPString ::= {0, 0, 6, 78}

-- arabicDamma BMPString ::= {0, 0, 6, 79}

-- arabicKasra BMPString ::= {0, 0, 6, 80}

-- arabicShadda BMPString ::= {0, 0, 6, 81}

-- arabicSukun BMPString ::= {0, 0, 6, 82}

-- arabicMaddahAbove BMPString ::= {0, 0, 6, 83}

-- arabicHamzaAbove BMPString ::= {0, 0, 6, 84}

-- arabicHamzaBelow BMPString ::= {0, 0, 6, 85}

-- arabic-indicDigitZero BMPString ::= {0, 0, 6, 96}

-- arabic-indicDigitOne BMPString ::= {0, 0, 6, 97}

-- arabic-indicDigitTwo BMPString ::= {0, 0, 6, 98}

-- arabic-indicDigitThree BMPString ::= {0, 0, 6, 99}

-- arabic-indicDigitFour BMPString ::= {0, 0, 6, 100}

-- arabic-indicDigitFive BMPString ::= {0, 0, 6, 101}

-- arabic-indicDigitSix BMPString ::= {0, 0, 6, 102}

-- arabic-indicDigitSeven BMPString ::= {0, 0, 6, 103}

-- arabic-indicDigitEight BMPString ::= {0, 0, 6, 104}

-- arabic-indicDigitNine BMPString ::= {0, 0, 6, 105}

-- arabicPercentSign BMPString ::= {0, 0, 6, 106}

-- arabicDecimalSeparator BMPString ::= {0, 0, 6, 107}

-- arabicThousandsSeparator BMPString ::= {0, 0, 6, 108}

-- arabicFivePointedStar BMPString ::= {0, 0, 6, 109}

-- arabicLetterDotlessBeh BMPString ::= {0, 0, 6, 110}

-- arabicLetterDotlessQaf BMPString ::= {0, 0, 6, 111}

-- arabicLetterSuperscriptAlef BMPString ::= {0, 0, 6, 112}

-- arabicLetterAlefWasla BMPString ::= {0, 0, 6, 113}

-- arabicLetterAlefWithWavyHamzaAbove BMPString ::= {0, 0, 6, 114}

-- arabicLetterAlefWithWavyHamzaBelow BMPString ::= {0, 0, 6, 115}

-- arabicLetterHighHamza BMPString ::= {0, 0, 6, 116}

-- arabicLetterHighHamzaAlef BMPString ::= {0, 0, 6, 117}

-- arabicLetterHighHamzaWaw BMPString ::= {0, 0, 6, 118}

-- arabicLetterUWithHamzaAbove BMPString ::= {0, 0, 6, 119}

-- arabicLetterHighHamzaYeh BMPString ::= {0, 0, 6, 120}

-- arabicLetterTteh BMPString ::= {0, 0, 6, 121}

-- arabicLetterTteheh BMPString ::= {0, 0, 6, 122}

-- arabicLetterBeeh BMPString ::= {0, 0, 6, 123}

-- arabicLetterTehWithRing BMPString ::= {0, 0, 6, 124}

-- arabicLetterTehWithThreeDotsAboveDownwards BMPString ::= {0, 0, 6, 125}

-- arabicLetterPeh BMPString ::= {0, 0, 6, 126}

-- arabicLetterTeheh BMPString ::= {0, 0, 6, 127}

-- arabicLetterBeheh BMPString ::= {0, 0, 6, 128}

-- arabicLetterHahWithHamzaAbove BMPString ::= {0, 0, 6, 129}

-- arabicLetterHahWithTwoDotsVerticalAbove BMPString ::= {0, 0, 6, 130}

-- arabicLetterNyeh BMPString ::= {0, 0, 6, 131}

-- arabicLetterDyeh BMPString ::= {0, 0, 6, 132}

-- arabicLetterHahWithThreeDotsAbove BMPString ::= {0, 0, 6, 133}

-- arabicLetterTcheh BMPString ::= {0, 0, 6, 134}

-- arabicLetterTcheheh BMPString ::= {0, 0, 6, 135}

-- arabicLetterDdal BMPString ::= {0, 0, 6, 136}

-- arabicLetterDalWithRing BMPString ::= {0, 0, 6, 137}

-- arabicLetterDalWithDotBelow BMPString ::= {0, 0, 6, 138}

-- arabicLetterDalWithDotBelowAndSmallTah BMPString ::= {0, 0, 6, 139}

-- arabicLetterDahal BMPString ::= {0, 0, 6, 140}

-- arabicLetterDdahal BMPString ::= {0, 0, 6, 141}

-- arabicLetterDul BMPString ::= {0, 0, 6, 142}

-- arabicLetterDalWithThreeDotsAboveDownwards BMPString ::= {0, 0, 6, 143}

-- arabicLetterDalWithFourDotsAbove BMPString ::= {0, 0, 6, 144}

-- arabicLetterRreh BMPString ::= {0, 0, 6, 145}

-- arabicLetterRehWithSmallV BMPString ::= {0, 0, 6, 146}

-- arabicLetterRehWithRing BMPString ::= {0, 0, 6, 147}

-- arabicLetterRehWithDotBelow BMPString ::= {0, 0, 6, 148}

-- arabicLetterRehWithSmallVBelow BMPString ::= {0, 0, 6, 149}

-- arabicLetterRehWithDotBelowAndDotAbove BMPString ::= {0, 0, 6, 150}

-- arabicLetterRehWithTwoDotsAbove BMPString ::= {0, 0, 6, 151}

-- arabicLetterJeh BMPString ::= {0, 0, 6, 152}

-- arabicLetterRehWithFourDotsAbove BMPString ::= {0, 0, 6, 153}

-- arabicLetterSeenWithDotBelowAndDotAbove BMPString ::= {0, 0, 6, 154}

-- arabicLetterSeenWithThreeDotsBelow BMPString ::= {0, 0, 6, 155}

-- arabicLetterSeenWithThreeDotsBelowAndThreeDotsAbove BMPString ::=
--   {0, 0, 6, 156}

-- arabicLetterSadWithTwoDotsBelow BMPString ::= {0, 0, 6, 157}

-- arabicLetterSadWithThreeDotsAbove BMPString ::= {0, 0, 6, 158}

-- arabicLetterTahWithThreeDotsAbove BMPString ::= {0, 0, 6, 159}

-- arabicLetterAinWithThreeDotsAbove BMPString ::= {0, 0, 6, 160}

-- arabicLetterDotlessFeh BMPString ::= {0, 0, 6, 161}

-- arabicLetterFehWithDotMovedBelow BMPString ::= {0, 0, 6, 162}

-- arabicLetterFehWithDotBelow BMPString ::= {0, 0, 6, 163}

-- arabicLetterVeh BMPString ::= {0, 0, 6, 164}

-- arabicLetterFehWithThreeDotsBelow BMPString ::= {0, 0, 6, 165}

-- arabicLetterPeheh BMPString ::= {0, 0, 6, 166}

-- arabicLetterQafWithDotAbove BMPString ::= {0, 0, 6, 167}

-- arabicLetterQafWithThreeDotsAbove BMPString ::= {0, 0, 6, 168}

-- arabicLetterKeheh BMPString ::= {0, 0, 6, 169}

-- arabicLetterSwashKaf BMPString ::= {0, 0, 6, 170}

-- arabicLetterKafWithRing BMPString ::= {0, 0, 6, 171}

-- arabicLetterKafWithDotAbove BMPString ::= {0, 0, 6, 172}

-- arabicLetterNg BMPString ::= {0, 0, 6, 173}

-- arabicLetterKafWithThreeDotsBelow BMPString ::= {0, 0, 6, 174}

-- arabicLetterGaf BMPString ::= {0, 0, 6, 175}

-- arabicLetterGafWithRing BMPString ::= {0, 0, 6, 176}

-- arabicLetterNgoeh BMPString ::= {0, 0, 6, 177}

-- arabicLetterGafWithTwoDotsBelow BMPString ::= {0, 0, 6, 178}

-- arabicLetterGueh BMPString ::= {0, 0, 6, 179}

-- arabicLetterGafWithThreeDotsAbove BMPString ::= {0, 0, 6, 180}

-- arabicLetterLamWithSmallV BMPString ::= {0, 0, 6, 181}

-- arabicLetterLamWithDotAbove BMPString ::= {0, 0, 6, 182}

-- arabicLetterLamWithThreeDotsAbove BMPString ::= {0, 0, 6, 183}

-- arabicLetterLamWithThreeDotsBelow BMPString ::= {0, 0, 6, 184}

-- arabicLetterNoonWithDotBelow BMPString ::= {0, 0, 6, 185}

-- arabicLetterNoonGhunna BMPString ::= {0, 0, 6, 186}

-- arabicLetterRnoon BMPString ::= {0, 0, 6, 187}

-- arabicLetterNoonWithRing BMPString ::= {0, 0, 6, 188}

-- arabicLetterNoonWithThreeDotsAbove BMPString ::= {0, 0, 6, 189}

-- arabicLetterHehDoachashmee BMPString ::= {0, 0, 6, 190}

-- arabicLetterTchehWithDotAbove BMPString ::= {0, 0, 6, 191}

-- arabicLetterHehWithYehAbove BMPString ::= {0, 0, 6, 192}

-- arabicLetterHehGoal BMPString ::= {0, 0, 6, 193}

-- arabicLetterHehGoalWithHamzaAbove BMPString ::= {0, 0, 6, 194}

-- arabicLetterTehMarbutaGoal BMPString ::= {0, 0, 6, 195}

-- arabicLetterWawWithRing BMPString ::= {0, 0, 6, 196}

-- arabicLetterKirghizOe BMPString ::= {0, 0, 6, 197}

-- arabicLetterOe BMPString ::= {0, 0, 6, 198}

-- arabicLetterU BMPString ::= {0, 0, 6, 199}

-- arabicLetterYu BMPString ::= {0, 0, 6, 200}

-- arabicLetterKirghizYu BMPString ::= {0, 0, 6, 201}

-- arabicLetterWawWithTwoDotsAbove BMPString ::= {0, 0, 6, 202}

-- arabicLetterVe BMPString ::= {0, 0, 6, 203}

-- arabicLetterFarsiYeh BMPString ::= {0, 0, 6, 204}

-- arabicLetterYehWithTail BMPString ::= {0, 0, 6, 205}

-- arabicLetterYehWithSmallV BMPString ::= {0, 0, 6, 206}

-- arabicLetterWawWithDotAbove BMPString ::= {0, 0, 6, 207}

-- arabicLetterE BMPString ::= {0, 0, 6, 208}

-- arabicLetterYehWithThreeDotsBelow BMPString ::= {0, 0, 6, 209}

-- arabicLetterYehBarree BMPString ::= {0, 0, 6, 210}

-- arabicLetterYehBarreeWithHamzaAbove BMPString ::= {0, 0, 6, 211}

-- arabicFullStop BMPString ::= {0, 0, 6, 212}

-- arabicLetterAe BMPString ::= {0, 0, 6, 213}

-- arabicSmallHighLigatureSadWithLamWithAlefMaksura BMPString ::= {0, 0, 6, 214}

-- arabicSmallHighLigatureQafWithLamWithAlefMaksura BMPString ::= {0, 0, 6, 215}

-- arabicSmallHighMeemInitialForm BMPString ::= {0, 0, 6, 216}

-- arabicSmallHighLamAlef BMPString ::= {0, 0, 6, 217}

-- arabicSmallHighJeem BMPString ::= {0, 0, 6, 218}

-- arabicSmallHighThreeDots BMPString ::= {0, 0, 6, 219}

-- arabicSmallHighSeen BMPString ::= {0, 0, 6, 220}

-- arabicEndOfAyah BMPString ::= {0, 0, 6, 221}

-- arabicStartOfRubElHizb BMPString ::= {0, 0, 6, 222}

-- arabicSmallHighRoundedZero BMPString ::= {0, 0, 6, 223}

-- arabicSmallHighUprightRectangularZero BMPString ::= {0, 0, 6, 224}

-- arabicSmallHighDotlessHeadOfKhah BMPString ::= {0, 0, 6, 225}

-- arabicSmallHighMeemIsolatedForm BMPString ::= {0, 0, 6, 226}

-- arabicSmallLowSeen BMPString ::= {0, 0, 6, 227}

-- arabicSmallHighMadda BMPString ::= {0, 0, 6, 228}

-- arabicSmallWaw BMPString ::= {0, 0, 6, 229}

-- arabicSmallYeh BMPString ::= {0, 0, 6, 230}

-- arabicSmallHighYeh BMPString ::= {0, 0, 6, 231}

-- arabicSmallHighNoon BMPString ::= {0, 0, 6, 232}

-- arabicPlaceOfSajdah BMPString ::= {0, 0, 6, 233}

-- arabicEmptyCentreLowStop BMPString ::= {0, 0, 6, 234}

-- arabicEmptyCentreHighStop BMPString ::= {0, 0, 6, 235}

-- arabicRoundedHighStopWithFilledCentre BMPString ::= {0, 0, 6, 236}

-- arabicSmallLowMeem BMPString ::= {0, 0, 6, 237}

-- extendedArabic-indicDigitZero BMPString ::= {0, 0, 6, 240}

-- extendedArabic-indicDigitOne BMPString ::= {0, 0, 6, 241}

-- extendedArabic-indicDigitTwo BMPString ::= {0, 0, 6, 242}

-- extendedArabic-indicDigitThree BMPString ::= {0, 0, 6, 243}

-- extendedArabic-indicDigitFour BMPString ::= {0, 0, 6, 244}

-- extendedArabic-indicDigitFive BMPString ::= {0, 0, 6, 245}

-- extendedArabic-indicDigitSix BMPString ::= {0, 0, 6, 246}

-- extendedArabic-indicDigitSeven BMPString ::= {0, 0, 6, 247}

-- extendedArabic-indicDigitEight BMPString ::= {0, 0, 6, 248}

-- extendedArabic-indicDigitNine BMPString ::= {0, 0, 6, 249}

-- arabicLetterSheenWithDotBelow BMPString ::= {0, 0, 6, 250}

-- arabicLetterDadWithDotBelow BMPString ::= {0, 0, 6, 251}

-- arabicLetterGhainWithDotBelow BMPString ::= {0, 0, 6, 252}

-- arabicSignSindhiAmpersand BMPString ::= {0, 0, 6, 253}

-- arabicSignSindhiPostpositionMen BMPString ::= {0, 0, 6, 254}

-- syriacEndOfParagraph BMPString ::= {0, 0, 7, 0}

-- syriacSupralinearFullStop BMPString ::= {0, 0, 7, 1}

-- syriacSublinearFullStop BMPString ::= {0, 0, 7, 2}

-- syriacSupralinearColon BMPString ::= {0, 0, 7, 3}

-- syriacSublinearColon BMPString ::= {0, 0, 7, 4}

-- syriacHorizontalColon BMPString ::= {0, 0, 7, 5}

-- syriacColonSkewedLeft BMPString ::= {0, 0, 7, 6}

-- syriacColonSkewedRight BMPString ::= {0, 0, 7, 7}

-- syriacSupralinearColonSkewedLeft BMPString ::= {0, 0, 7, 8}

-- syriacSublinearColonSkewedRight BMPString ::= {0, 0, 7, 9}

-- syriacContraction BMPString ::= {0, 0, 7, 10}

-- syriacHarkleanObelus BMPString ::= {0, 0, 7, 11}

-- syriacHarkleanMetobelus BMPString ::= {0, 0, 7, 12}

-- syriacHarkleanAsteriscus BMPString ::= {0, 0, 7, 13}

-- syriacAbbreviationMark BMPString ::= {0, 0, 7, 15}

-- syriacLetterAlaph BMPString ::= {0, 0, 7, 16}

-- syriacLetterSuperscriptAlaph BMPString ::= {0, 0, 7, 17}

-- syriacLetterBeth BMPString ::= {0, 0, 7, 18}

-- syriacLetterGamal BMPString ::= {0, 0, 7, 19}

-- syriacLetterGamalGarshuni BMPString ::= {0, 0, 7, 20}

-- syriacLetterDalath BMPString ::= {0, 0, 7, 21}

-- syriacLetterDotlessDalathRish BMPString ::= {0, 0, 7, 22}

-- syriacLetterHe BMPString ::= {0, 0, 7, 23}

-- syriacLetterWaw BMPString ::= {0, 0, 7, 24}

-- syriacLetterZain BMPString ::= {0, 0, 7, 25}

-- syriacLetterHeth BMPString ::= {0, 0, 7, 26}

-- syriacLetterTeth BMPString ::= {0, 0, 7, 27}

-- syriacLetterTethGarshuni BMPString ::= {0, 0, 7, 28}

-- syriacLetterYudh BMPString ::= {0, 0, 7, 29}

-- syriacLetterYudhHe BMPString ::= {0, 0, 7, 30}

-- syriacLetterKaph BMPString ::= {0, 0, 7, 31}

-- syriacLetterLamadh BMPString ::= {0, 0, 7, 32}

-- syriacLetterMim BMPString ::= {0, 0, 7, 33}

-- syriacLetterNun BMPString ::= {0, 0, 7, 34}

-- syriacLetterSemkath BMPString ::= {0, 0, 7, 35}

-- syriacLetterFinalSemkath BMPString ::= {0, 0, 7, 36}

-- syriacLetterE BMPString ::= {0, 0, 7, 37}

-- syriacLetterPe BMPString ::= {0, 0, 7, 38}

-- syriacLetterReversedPe BMPString ::= {0, 0, 7, 39}

-- syriacLetterSadhe BMPString ::= {0, 0, 7, 40}

-- syriacLetterQaph BMPString ::= {0, 0, 7, 41}

-- syriacLetterRish BMPString ::= {0, 0, 7, 42}

-- syriacLetterShin BMPString ::= {0, 0, 7, 43}

-- syriacLetterTaw BMPString ::= {0, 0, 7, 44}

-- syriacPthahaAbove BMPString ::= {0, 0, 7, 48}

-- syriacPthahaBelow BMPString ::= {0, 0, 7, 49}

-- syriacPthahaDotted BMPString ::= {0, 0, 7, 50}

-- syriacZqaphaAbove BMPString ::= {0, 0, 7, 51}

-- syriacZqaphaBelow BMPString ::= {0, 0, 7, 52}

-- syriacZqaphaDotted BMPString ::= {0, 0, 7, 53}

-- syriacRbasaAbove BMPString ::= {0, 0, 7, 54}

-- syriacRbasaBelow BMPString ::= {0, 0, 7, 55}

-- syriacDottedZlamaHorizontal BMPString ::= {0, 0, 7, 56}

-- syriacDottedZlamaAngular BMPString ::= {0, 0, 7, 57}

-- syriacHbasaAbove BMPString ::= {0, 0, 7, 58}

-- syriacHbasaBelow BMPString ::= {0, 0, 7, 59}

-- syriacHbasa-esasaDotted BMPString ::= {0, 0, 7, 60}

-- syriacEsasaAbove BMPString ::= {0, 0, 7, 61}

-- syriacEsasaBelow BMPString ::= {0, 0, 7, 62}

-- syriacRwaha BMPString ::= {0, 0, 7, 63}

-- syriacFeminineDot BMPString ::= {0, 0, 7, 64}

-- syriacQushshaya BMPString ::= {0, 0, 7, 65}

-- syriacRukkakha BMPString ::= {0, 0, 7, 66}

-- syriacTwoVerticalDotsAbove BMPString ::= {0, 0, 7, 67}

-- syriacTwoVerticalDotsBelow BMPString ::= {0, 0, 7, 68}

-- syriacThreeDotsAbove BMPString ::= {0, 0, 7, 69}

-- syriacThreeDotsBelow BMPString ::= {0, 0, 7, 70}

-- syriacObliqueLineAbove BMPString ::= {0, 0, 7, 71}

-- syriacObliqueLineBelow BMPString ::= {0, 0, 7, 72}

-- syriacMusic BMPString ::= {0, 0, 7, 73}

-- syriacBarrekh BMPString ::= {0, 0, 7, 74}

-- thaanaLetterHaa BMPString ::= {0, 0, 7, 128}

-- thaanaLetterShaviyani BMPString ::= {0, 0, 7, 129}

-- thaanaLetterNoonu BMPString ::= {0, 0, 7, 130}

-- thaanaLetterRaa BMPString ::= {0, 0, 7, 131}

-- thaanaLetterBaa BMPString ::= {0, 0, 7, 132}

-- thaanaLetterLhaviyani BMPString ::= {0, 0, 7, 133}

-- thaanaLetterKaafu BMPString ::= {0, 0, 7, 134}

-- thaanaLetterAlifu BMPString ::= {0, 0, 7, 135}

-- thaanaLetterVaavu BMPString ::= {0, 0, 7, 136}

-- thaanaLetterMeemu BMPString ::= {0, 0, 7, 137}

-- thaanaLetterFaafu BMPString ::= {0, 0, 7, 138}

-- thaanaLetterDhaalu BMPString ::= {0, 0, 7, 139}

-- thaanaLetterThaa BMPString ::= {0, 0, 7, 140}

-- thaanaLetterLaamu BMPString ::= {0, 0, 7, 141}

-- thaanaLetterGaafu BMPString ::= {0, 0, 7, 142}

-- thaanaLetterGnaviyani BMPString ::= {0, 0, 7, 143}

-- thaanaLetterSeenu BMPString ::= {0, 0, 7, 144}

-- thaanaLetterDaviyani BMPString ::= {0, 0, 7, 145}

-- thaanaLetterZaviyani BMPString ::= {0, 0, 7, 146}

-- thaanaLetterTaviyani BMPString ::= {0, 0, 7, 147}

-- thaanaLetterYaa BMPString ::= {0, 0, 7, 148}

-- thaanaLetterPaviyani BMPString ::= {0, 0, 7, 149}

-- thaanaLetterJaviyani BMPString ::= {0, 0, 7, 150}

-- thaanaLetterChaviyani BMPString ::= {0, 0, 7, 151}

-- thaanaLetterTtaa BMPString ::= {0, 0, 7, 152}

-- thaanaLetterHhaa BMPString ::= {0, 0, 7, 153}

-- thaanaLetterKhaa BMPString ::= {0, 0, 7, 154}

-- thaanaLetterThaalu BMPString ::= {0, 0, 7, 155}

-- thaanaLetterZaa BMPString ::= {0, 0, 7, 156}

-- thaanaLetterSheenu BMPString ::= {0, 0, 7, 157}

-- thaanaLetterSaadhu BMPString ::= {0, 0, 7, 158}

-- thaanaLetterDaadhu BMPString ::= {0, 0, 7, 159}

-- thaanaLetterTo BMPString ::= {0, 0, 7, 160}

-- thaanaLetterZo BMPString ::= {0, 0, 7, 161}

-- thaanaLetterAinu BMPString ::= {0, 0, 7, 162}

-- thaanaLetterGhainu BMPString ::= {0, 0, 7, 163}

-- thaanaLetterQaafu BMPString ::= {0, 0, 7, 164}

-- thaanaLetterWaavu BMPString ::= {0, 0, 7, 165}

-- thaanaAbafili BMPString ::= {0, 0, 7, 166}

-- thaanaAabaafili BMPString ::= {0, 0, 7, 167}

-- thaanaIbifili BMPString ::= {0, 0, 7, 168}

-- thaanaEebeefili BMPString ::= {0, 0, 7, 169}

-- thaanaUbufili BMPString ::= {0, 0, 7, 170}

-- thaanaOoboofili BMPString ::= {0, 0, 7, 171}

-- thaanaEbefili BMPString ::= {0, 0, 7, 172}

-- thaanaEybeyfili BMPString ::= {0, 0, 7, 173}

-- thaanaObofili BMPString ::= {0, 0, 7, 174}

-- thaanaOaboafili BMPString ::= {0, 0, 7, 175}

-- thaanaSukun BMPString ::= {0, 0, 7, 176}

-- thaanaLetterNaa BMPString ::= {0, 0, 7, 177}

-- devanagariSignCandrabindu BMPString ::= {0, 0, 9, 1}

-- devanagariSignAnusvara BMPString ::= {0, 0, 9, 2}

-- devanagariSignVisarga BMPString ::= {0, 0, 9, 3}

-- devanagariLetterA BMPString ::= {0, 0, 9, 5}

-- devanagariLetterAa BMPString ::= {0, 0, 9, 6}

-- devanagariLetterI BMPString ::= {0, 0, 9, 7}

-- devanagariLetterIi BMPString ::= {0, 0, 9, 8}

-- devanagariLetterU BMPString ::= {0, 0, 9, 9}

-- devanagariLetterUu BMPString ::= {0, 0, 9, 10}

-- devanagariLetterVocalicR BMPString ::= {0, 0, 9, 11}

-- devanagariLetterVocalicL BMPString ::= {0, 0, 9, 12}

-- devanagariLetterCandraE BMPString ::= {0, 0, 9, 13}

-- devanagariLetterShortE BMPString ::= {0, 0, 9, 14}

-- devanagariLetterE BMPString ::= {0, 0, 9, 15}

-- devanagariLetterAi BMPString ::= {0, 0, 9, 16}

-- devanagariLetterCandraO BMPString ::= {0, 0, 9, 17}

-- devanagariLetterShortO BMPString ::= {0, 0, 9, 18}

-- devanagariLetterO BMPString ::= {0, 0, 9, 19}

-- devanagariLetterAu BMPString ::= {0, 0, 9, 20}

-- devanagariLetterKa BMPString ::= {0, 0, 9, 21}

-- devanagariLetterKha BMPString ::= {0, 0, 9, 22}

-- devanagariLetterGa BMPString ::= {0, 0, 9, 23}

-- devanagariLetterGha BMPString ::= {0, 0, 9, 24}

-- devanagariLetterNga BMPString ::= {0, 0, 9, 25}

-- devanagariLetterCa BMPString ::= {0, 0, 9, 26}

-- devanagariLetterCha BMPString ::= {0, 0, 9, 27}

-- devanagariLetterJa BMPString ::= {0, 0, 9, 28}

-- devanagariLetterJha BMPString ::= {0, 0, 9, 29}

-- devanagariLetterNya BMPString ::= {0, 0, 9, 30}

-- devanagariLetterTta BMPString ::= {0, 0, 9, 31}

-- devanagariLetterTtha BMPString ::= {0, 0, 9, 32}

-- devanagariLetterDda BMPString ::= {0, 0, 9, 33}

-- devanagariLetterDdha BMPString ::= {0, 0, 9, 34}

-- devanagariLetterNna BMPString ::= {0, 0, 9, 35}

-- devanagariLetterTa BMPString ::= {0, 0, 9, 36}

-- devanagariLetterTha BMPString ::= {0, 0, 9, 37}

-- devanagariLetterDa BMPString ::= {0, 0, 9, 38}

-- devanagariLetterDha BMPString ::= {0, 0, 9, 39}

-- devanagariLetterNa BMPString ::= {0, 0, 9, 40}

-- devanagariLetterNnna BMPString ::= {0, 0, 9, 41}

-- devanagariLetterPa BMPString ::= {0, 0, 9, 42}

-- devanagariLetterPha BMPString ::= {0, 0, 9, 43}

-- devanagariLetterBa BMPString ::= {0, 0, 9, 44}

-- devanagariLetterBha BMPString ::= {0, 0, 9, 45}

-- devanagariLetterMa BMPString ::= {0, 0, 9, 46}

-- devanagariLetterYa BMPString ::= {0, 0, 9, 47}

-- devanagariLetterRa BMPString ::= {0, 0, 9, 48}

-- devanagariLetterRra BMPString ::= {0, 0, 9, 49}

-- devanagariLetterLa BMPString ::= {0, 0, 9, 50}

-- devanagariLetterLla BMPString ::= {0, 0, 9, 51}

-- devanagariLetterLlla BMPString ::= {0, 0, 9, 52}

-- devanagariLetterVa BMPString ::= {0, 0, 9, 53}

-- devanagariLetterSha BMPString ::= {0, 0, 9, 54}

-- devanagariLetterSsa BMPString ::= {0, 0, 9, 55}

-- devanagariLetterSa BMPString ::= {0, 0, 9, 56}

-- devanagariLetterHa BMPString ::= {0, 0, 9, 57}

-- devanagariSignNukta BMPString ::= {0, 0, 9, 60}

-- devanagariSignAvagraha BMPString ::= {0, 0, 9, 61}

-- devanagariVowelSignAa BMPString ::= {0, 0, 9, 62}

-- devanagariVowelSignI BMPString ::= {0, 0, 9, 63}

-- devanagariVowelSignIi BMPString ::= {0, 0, 9, 64}

-- devanagariVowelSignU BMPString ::= {0, 0, 9, 65}

-- devanagariVowelSignUu BMPString ::= {0, 0, 9, 66}

-- devanagariVowelSignVocalicR BMPString ::= {0, 0, 9, 67}

-- devanagariVowelSignVocalicRr BMPString ::= {0, 0, 9, 68}

-- devanagariVowelSignCandraE BMPString ::= {0, 0, 9, 69}

-- devanagariVowelSignShortE BMPString ::= {0, 0, 9, 70}

-- devanagariVowelSignE BMPString ::= {0, 0, 9, 71}

-- devanagariVowelSignAi BMPString ::= {0, 0, 9, 72}

-- devanagariVowelSignCandraO BMPString ::= {0, 0, 9, 73}

-- devanagariVowelSignShortO BMPString ::= {0, 0, 9, 74}

-- devanagariVowelSignO BMPString ::= {0, 0, 9, 75}

-- devanagariVowelSignAu BMPString ::= {0, 0, 9, 76}

-- devanagariSignVirama BMPString ::= {0, 0, 9, 77}

-- devanagariOm BMPString ::= {0, 0, 9, 80}

-- devanagariStressSignUdatta BMPString ::= {0, 0, 9, 81}

-- devanagariStressSignAnudatta BMPString ::= {0, 0, 9, 82}

-- devanagariGraveAccent BMPString ::= {0, 0, 9, 83}

-- devanagariAcuteAccent BMPString ::= {0, 0, 9, 84}

-- devanagariLetterQa BMPString ::= {0, 0, 9, 88}

-- devanagariLetterKhha BMPString ::= {0, 0, 9, 89}

-- devanagariLetterGhha BMPString ::= {0, 0, 9, 90}

-- devanagariLetterZa BMPString ::= {0, 0, 9, 91}

-- devanagariLetterDddha BMPString ::= {0, 0, 9, 92}

-- devanagariLetterRha BMPString ::= {0, 0, 9, 93}

-- devanagariLetterFa BMPString ::= {0, 0, 9, 94}

-- devanagariLetterYya BMPString ::= {0, 0, 9, 95}

-- devanagariLetterVocalicRr BMPString ::= {0, 0, 9, 96}

-- devanagariLetterVocalicLl BMPString ::= {0, 0, 9, 97}

-- devanagariVowelSignVocalicL BMPString ::= {0, 0, 9, 98}

-- devanagariVowelSignVocalicLl BMPString ::= {0, 0, 9, 99}

-- devanagariDanda BMPString ::= {0, 0, 9, 100}

-- devanagariDoubleDanda BMPString ::= {0, 0, 9, 101}

-- devanagariDigitZero BMPString ::= {0, 0, 9, 102}

-- devanagariDigitOne BMPString ::= {0, 0, 9, 103}

-- devanagariDigitTwo BMPString ::= {0, 0, 9, 104}

-- devanagariDigitThree BMPString ::= {0, 0, 9, 105}

-- devanagariDigitFour BMPString ::= {0, 0, 9, 106}

-- devanagariDigitFive BMPString ::= {0, 0, 9, 107}

-- devanagariDigitSix BMPString ::= {0, 0, 9, 108}

-- devanagariDigitSeven BMPString ::= {0, 0, 9, 109}

-- devanagariDigitEight BMPString ::= {0, 0, 9, 110}

-- devanagariDigitNine BMPString ::= {0, 0, 9, 111}

-- devanagariAbbreviationSign BMPString ::= {0, 0, 9, 112}

-- bengaliSignCandrabindu BMPString ::= {0, 0, 9, 129}

-- bengaliSignAnusvara BMPString ::= {0, 0, 9, 130}

-- bengaliSignVisarga BMPString ::= {0, 0, 9, 131}

-- bengaliLetterA BMPString ::= {0, 0, 9, 133}

-- bengaliLetterAa BMPString ::= {0, 0, 9, 134}

-- bengaliLetterI BMPString ::= {0, 0, 9, 135}

-- bengaliLetterIi BMPString ::= {0, 0, 9, 136}

-- bengaliLetterU BMPString ::= {0, 0, 9, 137}

-- bengaliLetterUu BMPString ::= {0, 0, 9, 138}

-- bengaliLetterVocalicR BMPString ::= {0, 0, 9, 139}

-- bengaliLetterVocalicL BMPString ::= {0, 0, 9, 140}

-- bengaliLetterE BMPString ::= {0, 0, 9, 143}

-- bengaliLetterAi BMPString ::= {0, 0, 9, 144}

-- bengaliLetterO BMPString ::= {0, 0, 9, 147}

-- bengaliLetterAu BMPString ::= {0, 0, 9, 148}

-- bengaliLetterKa BMPString ::= {0, 0, 9, 149}

-- bengaliLetterKha BMPString ::= {0, 0, 9, 150}

-- bengaliLetterGa BMPString ::= {0, 0, 9, 151}

-- bengaliLetterGha BMPString ::= {0, 0, 9, 152}

-- bengaliLetterNga BMPString ::= {0, 0, 9, 153}

-- bengaliLetterCa BMPString ::= {0, 0, 9, 154}

-- bengaliLetterCha BMPString ::= {0, 0, 9, 155}

-- bengaliLetterJa BMPString ::= {0, 0, 9, 156}

-- bengaliLetterJha BMPString ::= {0, 0, 9, 157}

-- bengaliLetterNya BMPString ::= {0, 0, 9, 158}

-- bengaliLetterTta BMPString ::= {0, 0, 9, 159}

-- bengaliLetterTtha BMPString ::= {0, 0, 9, 160}

-- bengaliLetterDda BMPString ::= {0, 0, 9, 161}

-- bengaliLetterDdha BMPString ::= {0, 0, 9, 162}

-- bengaliLetterNna BMPString ::= {0, 0, 9, 163}

-- bengaliLetterTa BMPString ::= {0, 0, 9, 164}

-- bengaliLetterTha BMPString ::= {0, 0, 9, 165}

-- bengaliLetterDa BMPString ::= {0, 0, 9, 166}

-- bengaliLetterDha BMPString ::= {0, 0, 9, 167}

-- bengaliLetterNa BMPString ::= {0, 0, 9, 168}

-- bengaliLetterPa BMPString ::= {0, 0, 9, 170}

-- bengaliLetterPha BMPString ::= {0, 0, 9, 171}

-- bengaliLetterBa BMPString ::= {0, 0, 9, 172}

-- bengaliLetterBha BMPString ::= {0, 0, 9, 173}

-- bengaliLetterMa BMPString ::= {0, 0, 9, 174}

-- bengaliLetterYa BMPString ::= {0, 0, 9, 175}

-- bengaliLetterRa BMPString ::= {0, 0, 9, 176}

-- bengaliLetterLa BMPString ::= {0, 0, 9, 178}

-- bengaliLetterSha BMPString ::= {0, 0, 9, 182}

-- bengaliLetterSsa BMPString ::= {0, 0, 9, 183}

-- bengaliLetterSa BMPString ::= {0, 0, 9, 184}

-- bengaliLetterHa BMPString ::= {0, 0, 9, 185}

-- bengaliSignNukta BMPString ::= {0, 0, 9, 188}

-- bengaliVowelSignAa BMPString ::= {0, 0, 9, 190}

-- bengaliVowelSignI BMPString ::= {0, 0, 9, 191}

-- bengaliVowelSignIi BMPString ::= {0, 0, 9, 192}

-- bengaliVowelSignU BMPString ::= {0, 0, 9, 193}

-- bengaliVowelSignUu BMPString ::= {0, 0, 9, 194}

-- bengaliVowelSignVocalicR BMPString ::= {0, 0, 9, 195}

-- bengaliVowelSignVocalicRr BMPString ::= {0, 0, 9, 196}

-- bengaliVowelSignE BMPString ::= {0, 0, 9, 199}

-- bengaliVowelSignAi BMPString ::= {0, 0, 9, 200}

-- bengaliVowelSignO BMPString ::= {0, 0, 9, 203}

-- bengaliVowelSignAu BMPString ::= {0, 0, 9, 204}

-- bengaliSignVirama BMPString ::= {0, 0, 9, 205}

-- bengaliAuLengthMark BMPString ::= {0, 0, 9, 215}

-- bengaliLetterRra BMPString ::= {0, 0, 9, 220}

-- bengaliLetterRha BMPString ::= {0, 0, 9, 221}

-- bengaliLetterYya BMPString ::= {0, 0, 9, 223}

-- bengaliLetterVocalicRr BMPString ::= {0, 0, 9, 224}

-- bengaliLetterVocalicLl BMPString ::= {0, 0, 9, 225}

-- bengaliVowelSignVocalicL BMPString ::= {0, 0, 9, 226}

-- bengaliVowelSignVocalicLl BMPString ::= {0, 0, 9, 227}

-- bengaliDigitZero BMPString ::= {0, 0, 9, 230}

-- bengaliDigitOne BMPString ::= {0, 0, 9, 231}

-- bengaliDigitTwo BMPString ::= {0, 0, 9, 232}

-- bengaliDigitThree BMPString ::= {0, 0, 9, 233}

-- bengaliDigitFour BMPString ::= {0, 0, 9, 234}

-- bengaliDigitFive BMPString ::= {0, 0, 9, 235}

-- bengaliDigitSix BMPString ::= {0, 0, 9, 236}

-- bengaliDigitSeven BMPString ::= {0, 0, 9, 237}

-- bengaliDigitEight BMPString ::= {0, 0, 9, 238}

-- bengaliDigitNine BMPString ::= {0, 0, 9, 239}

-- bengaliLetterRaWithMiddleDiagonal BMPString ::= {0, 0, 9, 240}

-- bengaliLetterRaWithLowerDiagonal BMPString ::= {0, 0, 9, 241}

-- bengaliRupeeMark BMPString ::= {0, 0, 9, 242}

-- bengaliRupeeSign BMPString ::= {0, 0, 9, 243}

-- bengaliCurrencyNumeratorOne BMPString ::= {0, 0, 9, 244}

-- bengaliCurrencyNumeratorTwo BMPString ::= {0, 0, 9, 245}

-- bengaliCurrencyNumeratorThree BMPString ::= {0, 0, 9, 246}

-- bengaliCurrencyNumeratorFour BMPString ::= {0, 0, 9, 247}

-- bengaliCurrencyNumeratorOneLessThanTheDenominator BMPString ::= {0, 0, 9, 248}

-- bengaliCurrencyDenominatorSixteen BMPString ::= {0, 0, 9, 249}

-- bengaliIsshar BMPString ::= {0, 0, 9, 250}

-- gurmukhiSignBindi BMPString ::= {0, 0, 10, 2}

-- gurmukhiLetterA BMPString ::= {0, 0, 10, 5}

-- gurmukhiLetterAa BMPString ::= {0, 0, 10, 6}

-- gurmukhiLetterI BMPString ::= {0, 0, 10, 7}

-- gurmukhiLetterIi BMPString ::= {0, 0, 10, 8}

-- gurmukhiLetterU BMPString ::= {0, 0, 10, 9}

-- gurmukhiLetterUu BMPString ::= {0, 0, 10, 10}

-- gurmukhiLetterEe BMPString ::= {0, 0, 10, 15}

-- gurmukhiLetterAi BMPString ::= {0, 0, 10, 16}

-- gurmukhiLetterOo BMPString ::= {0, 0, 10, 19}

-- gurmukhiLetterAu BMPString ::= {0, 0, 10, 20}

-- gurmukhiLetterKa BMPString ::= {0, 0, 10, 21}

-- gurmukhiLetterKha BMPString ::= {0, 0, 10, 22}

-- gurmukhiLetterGa BMPString ::= {0, 0, 10, 23}

-- gurmukhiLetterGha BMPString ::= {0, 0, 10, 24}

-- gurmukhiLetterNga BMPString ::= {0, 0, 10, 25}

-- gurmukhiLetterCa BMPString ::= {0, 0, 10, 26}

-- gurmukhiLetterCha BMPString ::= {0, 0, 10, 27}

-- gurmukhiLetterJa BMPString ::= {0, 0, 10, 28}

-- gurmukhiLetterJha BMPString ::= {0, 0, 10, 29}

-- gurmukhiLetterNya BMPString ::= {0, 0, 10, 30}

-- gurmukhiLetterTta BMPString ::= {0, 0, 10, 31}

-- gurmukhiLetterTtha BMPString ::= {0, 0, 10, 32}

-- gurmukhiLetterDda BMPString ::= {0, 0, 10, 33}

-- gurmukhiLetterDdha BMPString ::= {0, 0, 10, 34}

-- gurmukhiLetterNna BMPString ::= {0, 0, 10, 35}

-- gurmukhiLetterTa BMPString ::= {0, 0, 10, 36}

-- gurmukhiLetterTha BMPString ::= {0, 0, 10, 37}

-- gurmukhiLetterDa BMPString ::= {0, 0, 10, 38}

-- gurmukhiLetterDha BMPString ::= {0, 0, 10, 39}

-- gurmukhiLetterNa BMPString ::= {0, 0, 10, 40}

-- gurmukhiLetterPa BMPString ::= {0, 0, 10, 42}

-- gurmukhiLetterPha BMPString ::= {0, 0, 10, 43}

-- gurmukhiLetterBa BMPString ::= {0, 0, 10, 44}

-- gurmukhiLetterBha BMPString ::= {0, 0, 10, 45}

-- gurmukhiLetterMa BMPString ::= {0, 0, 10, 46}

-- gurmukhiLetterYa BMPString ::= {0, 0, 10, 47}

-- gurmukhiLetterRa BMPString ::= {0, 0, 10, 48}

-- gurmukhiLetterLa BMPString ::= {0, 0, 10, 50}

-- gurmukhiLetterLla BMPString ::= {0, 0, 10, 51}

-- gurmukhiLetterVa BMPString ::= {0, 0, 10, 53}

-- gurmukhiLetterSha BMPString ::= {0, 0, 10, 54}

-- gurmukhiLetterSa BMPString ::= {0, 0, 10, 56}

-- gurmukhiLetterHa BMPString ::= {0, 0, 10, 57}

-- gurmukhiSignNukta BMPString ::= {0, 0, 10, 60}

-- gurmukhiVowelSignAa BMPString ::= {0, 0, 10, 62}

-- gurmukhiVowelSignI BMPString ::= {0, 0, 10, 63}

-- gurmukhiVowelSignIi BMPString ::= {0, 0, 10, 64}

-- gurmukhiVowelSignU BMPString ::= {0, 0, 10, 65}

-- gurmukhiVowelSignUu BMPString ::= {0, 0, 10, 66}

-- gurmukhiVowelSignEe BMPString ::= {0, 0, 10, 71}

-- gurmukhiVowelSignAi BMPString ::= {0, 0, 10, 72}

-- gurmukhiVowelSignOo BMPString ::= {0, 0, 10, 75}

-- gurmukhiVowelSignAu BMPString ::= {0, 0, 10, 76}

-- gurmukhiSignVirama BMPString ::= {0, 0, 10, 77}

-- gurmukhiLetterKhha BMPString ::= {0, 0, 10, 89}

-- gurmukhiLetterGhha BMPString ::= {0, 0, 10, 90}

-- gurmukhiLetterZa BMPString ::= {0, 0, 10, 91}

-- gurmukhiLetterRra BMPString ::= {0, 0, 10, 92}

-- gurmukhiLetterFa BMPString ::= {0, 0, 10, 94}

-- gurmukhiDigitZero BMPString ::= {0, 0, 10, 102}

-- gurmukhiDigitOne BMPString ::= {0, 0, 10, 103}

-- gurmukhiDigitTwo BMPString ::= {0, 0, 10, 104}

-- gurmukhiDigitThree BMPString ::= {0, 0, 10, 105}

-- gurmukhiDigitFour BMPString ::= {0, 0, 10, 106}

-- gurmukhiDigitFive BMPString ::= {0, 0, 10, 107}

-- gurmukhiDigitSix BMPString ::= {0, 0, 10, 108}

-- gurmukhiDigitSeven BMPString ::= {0, 0, 10, 109}

-- gurmukhiDigitEight BMPString ::= {0, 0, 10, 110}

-- gurmukhiDigitNine BMPString ::= {0, 0, 10, 111}

-- gurmukhiTippi BMPString ::= {0, 0, 10, 112}

-- gurmukhiAddak BMPString ::= {0, 0, 10, 113}

-- gurmukhiIri BMPString ::= {0, 0, 10, 114}

-- gurmukhiUra BMPString ::= {0, 0, 10, 115}

-- gurmukhiEkOnkar BMPString ::= {0, 0, 10, 116}

-- gujaratiSignCandrabindu BMPString ::= {0, 0, 10, 129}

-- gujaratiSignAnusvara BMPString ::= {0, 0, 10, 130}

-- gujaratiSignVisarga BMPString ::= {0, 0, 10, 131}

-- gujaratiLetterA BMPString ::= {0, 0, 10, 133}

-- gujaratiLetterAa BMPString ::= {0, 0, 10, 134}

-- gujaratiLetterI BMPString ::= {0, 0, 10, 135}

-- gujaratiLetterIi BMPString ::= {0, 0, 10, 136}

-- gujaratiLetterU BMPString ::= {0, 0, 10, 137}

-- gujaratiLetterUu BMPString ::= {0, 0, 10, 138}

-- gujaratiLetterVocalicR BMPString ::= {0, 0, 10, 139}

-- gujaratiVowelCandraE BMPString ::= {0, 0, 10, 141}

-- gujaratiLetterE BMPString ::= {0, 0, 10, 143}

-- gujaratiLetterAi BMPString ::= {0, 0, 10, 144}

-- gujaratiVowelCandraO BMPString ::= {0, 0, 10, 145}

-- gujaratiLetterO BMPString ::= {0, 0, 10, 147}

-- gujaratiLetterAu BMPString ::= {0, 0, 10, 148}

-- gujaratiLetterKa BMPString ::= {0, 0, 10, 149}

-- gujaratiLetterKha BMPString ::= {0, 0, 10, 150}

-- gujaratiLetterGa BMPString ::= {0, 0, 10, 151}

-- gujaratiLetterGha BMPString ::= {0, 0, 10, 152}

-- gujaratiLetterNga BMPString ::= {0, 0, 10, 153}

-- gujaratiLetterCa BMPString ::= {0, 0, 10, 154}

-- gujaratiLetterCha BMPString ::= {0, 0, 10, 155}

-- gujaratiLetterJa BMPString ::= {0, 0, 10, 156}

-- gujaratiLetterJha BMPString ::= {0, 0, 10, 157}

-- gujaratiLetterNya BMPString ::= {0, 0, 10, 158}

-- gujaratiLetterTta BMPString ::= {0, 0, 10, 159}

-- gujaratiLetterTtha BMPString ::= {0, 0, 10, 160}

-- gujaratiLetterDda BMPString ::= {0, 0, 10, 161}

-- gujaratiLetterDdha BMPString ::= {0, 0, 10, 162}

-- gujaratiLetterNna BMPString ::= {0, 0, 10, 163}

-- gujaratiLetterTa BMPString ::= {0, 0, 10, 164}

-- gujaratiLetterTha BMPString ::= {0, 0, 10, 165}

-- gujaratiLetterDa BMPString ::= {0, 0, 10, 166}

-- gujaratiLetterDha BMPString ::= {0, 0, 10, 167}

-- gujaratiLetterNa BMPString ::= {0, 0, 10, 168}

-- gujaratiLetterPa BMPString ::= {0, 0, 10, 170}

-- gujaratiLetterPha BMPString ::= {0, 0, 10, 171}

-- gujaratiLetterBa BMPString ::= {0, 0, 10, 172}

-- gujaratiLetterBha BMPString ::= {0, 0, 10, 173}

-- gujaratiLetterMa BMPString ::= {0, 0, 10, 174}

-- gujaratiLetterYa BMPString ::= {0, 0, 10, 175}

-- gujaratiLetterRa BMPString ::= {0, 0, 10, 176}

-- gujaratiLetterLa BMPString ::= {0, 0, 10, 178}

-- gujaratiLetterLla BMPString ::= {0, 0, 10, 179}

-- gujaratiLetterVa BMPString ::= {0, 0, 10, 181}

-- gujaratiLetterSha BMPString ::= {0, 0, 10, 182}

-- gujaratiLetterSsa BMPString ::= {0, 0, 10, 183}

-- gujaratiLetterSa BMPString ::= {0, 0, 10, 184}

-- gujaratiLetterHa BMPString ::= {0, 0, 10, 185}

-- gujaratiSignNukta BMPString ::= {0, 0, 10, 188}

-- gujaratiSignAvagraha BMPString ::= {0, 0, 10, 189}

-- gujaratiVowelSignAa BMPString ::= {0, 0, 10, 190}

-- gujaratiVowelSignI BMPString ::= {0, 0, 10, 191}

-- gujaratiVowelSignIi BMPString ::= {0, 0, 10, 192}

-- gujaratiVowelSignU BMPString ::= {0, 0, 10, 193}

-- gujaratiVowelSignUu BMPString ::= {0, 0, 10, 194}

-- gujaratiVowelSignVocalicR BMPString ::= {0, 0, 10, 195}

-- gujaratiVowelSignVocalicRr BMPString ::= {0, 0, 10, 196}

-- gujaratiVowelSignCandraE BMPString ::= {0, 0, 10, 197}

-- gujaratiVowelSignE BMPString ::= {0, 0, 10, 199}

-- gujaratiVowelSignAi BMPString ::= {0, 0, 10, 200}

-- gujaratiVowelSignCandraO BMPString ::= {0, 0, 10, 201}

-- gujaratiVowelSignO BMPString ::= {0, 0, 10, 203}

-- gujaratiVowelSignAu BMPString ::= {0, 0, 10, 204}

-- gujaratiSignVirama BMPString ::= {0, 0, 10, 205}

-- gujaratiOm BMPString ::= {0, 0, 10, 208}

-- gujaratiLetterVocalicRr BMPString ::= {0, 0, 10, 224}

-- gujaratiDigitZero BMPString ::= {0, 0, 10, 230}

-- gujaratiDigitOne BMPString ::= {0, 0, 10, 231}

-- gujaratiDigitTwo BMPString ::= {0, 0, 10, 232}

-- gujaratiDigitThree BMPString ::= {0, 0, 10, 233}

-- gujaratiDigitFour BMPString ::= {0, 0, 10, 234}

-- gujaratiDigitFive BMPString ::= {0, 0, 10, 235}

-- gujaratiDigitSix BMPString ::= {0, 0, 10, 236}

-- gujaratiDigitSeven BMPString ::= {0, 0, 10, 237}

-- gujaratiDigitEight BMPString ::= {0, 0, 10, 238}

-- gujaratiDigitNine BMPString ::= {0, 0, 10, 239}

-- oriyaSignCandrabindu BMPString ::= {0, 0, 11, 1}

-- oriyaSignAnusvara BMPString ::= {0, 0, 11, 2}

-- oriyaSignVisarga BMPString ::= {0, 0, 11, 3}

-- oriyaLetterA BMPString ::= {0, 0, 11, 5}

-- oriyaLetterAa BMPString ::= {0, 0, 11, 6}

-- oriyaLetterI BMPString ::= {0, 0, 11, 7}

-- oriyaLetterIi BMPString ::= {0, 0, 11, 8}

-- oriyaLetterU BMPString ::= {0, 0, 11, 9}

-- oriyaLetterUu BMPString ::= {0, 0, 11, 10}

-- oriyaLetterVocalicR BMPString ::= {0, 0, 11, 11}

-- oriyaLetterVocalicL BMPString ::= {0, 0, 11, 12}

-- oriyaLetterE BMPString ::= {0, 0, 11, 15}

-- oriyaLetterAi BMPString ::= {0, 0, 11, 16}

-- oriyaLetterO BMPString ::= {0, 0, 11, 19}

-- oriyaLetterAu BMPString ::= {0, 0, 11, 20}

-- oriyaLetterKa BMPString ::= {0, 0, 11, 21}

-- oriyaLetterKha BMPString ::= {0, 0, 11, 22}

-- oriyaLetterGa BMPString ::= {0, 0, 11, 23}

-- oriyaLetterGha BMPString ::= {0, 0, 11, 24}

-- oriyaLetterNga BMPString ::= {0, 0, 11, 25}

-- oriyaLetterCa BMPString ::= {0, 0, 11, 26}

-- oriyaLetterCha BMPString ::= {0, 0, 11, 27}

-- oriyaLetterJa BMPString ::= {0, 0, 11, 28}

-- oriyaLetterJha BMPString ::= {0, 0, 11, 29}

-- oriyaLetterNya BMPString ::= {0, 0, 11, 30}

-- oriyaLetterTta BMPString ::= {0, 0, 11, 31}

-- oriyaLetterTtha BMPString ::= {0, 0, 11, 32}

-- oriyaLetterDda BMPString ::= {0, 0, 11, 33}

-- oriyaLetterDdha BMPString ::= {0, 0, 11, 34}

-- oriyaLetterNna BMPString ::= {0, 0, 11, 35}

-- oriyaLetterTa BMPString ::= {0, 0, 11, 36}

-- oriyaLetterTha BMPString ::= {0, 0, 11, 37}

-- oriyaLetterDa BMPString ::= {0, 0, 11, 38}

-- oriyaLetterDha BMPString ::= {0, 0, 11, 39}

-- oriyaLetterNa BMPString ::= {0, 0, 11, 40}

-- oriyaLetterPa BMPString ::= {0, 0, 11, 42}

-- oriyaLetterPha BMPString ::= {0, 0, 11, 43}

-- oriyaLetterBa BMPString ::= {0, 0, 11, 44}

-- oriyaLetterBha BMPString ::= {0, 0, 11, 45}

-- oriyaLetterMa BMPString ::= {0, 0, 11, 46}

-- oriyaLetterYa BMPString ::= {0, 0, 11, 47}

-- oriyaLetterRa BMPString ::= {0, 0, 11, 48}

-- oriyaLetterLa BMPString ::= {0, 0, 11, 50}

-- oriyaLetterLla BMPString ::= {0, 0, 11, 51}

-- oriyaLetterSha BMPString ::= {0, 0, 11, 54}

-- oriyaLetterSsa BMPString ::= {0, 0, 11, 55}

-- oriyaLetterSa BMPString ::= {0, 0, 11, 56}

-- oriyaLetterHa BMPString ::= {0, 0, 11, 57}

-- oriyaSignNukta BMPString ::= {0, 0, 11, 60}

-- oriyaSignAvagraha BMPString ::= {0, 0, 11, 61}

-- oriyaVowelSignAa BMPString ::= {0, 0, 11, 62}

-- oriyaVowelSignI BMPString ::= {0, 0, 11, 63}

-- oriyaVowelSignIi BMPString ::= {0, 0, 11, 64}

-- oriyaVowelSignU BMPString ::= {0, 0, 11, 65}

-- oriyaVowelSignUu BMPString ::= {0, 0, 11, 66}

-- oriyaVowelSignVocalicR BMPString ::= {0, 0, 11, 67}

-- oriyaVowelSignE BMPString ::= {0, 0, 11, 71}

-- oriyaVowelSignAi BMPString ::= {0, 0, 11, 72}

-- oriyaVowelSignO BMPString ::= {0, 0, 11, 75}

-- oriyaVowelSignAu BMPString ::= {0, 0, 11, 76}

-- oriyaSignVirama BMPString ::= {0, 0, 11, 77}

-- oriyaAiLengthMark BMPString ::= {0, 0, 11, 86}

-- oriyaAuLengthMark BMPString ::= {0, 0, 11, 87}

-- oriyaLetterRra BMPString ::= {0, 0, 11, 92}

-- oriyaLetterRha BMPString ::= {0, 0, 11, 93}

-- oriyaLetterYya BMPString ::= {0, 0, 11, 95}

-- oriyaLetterVocalicRr BMPString ::= {0, 0, 11, 96}

-- oriyaLetterVocalicLl BMPString ::= {0, 0, 11, 97}

-- oriyaDigitZero BMPString ::= {0, 0, 11, 102}

-- oriyaDigitOne BMPString ::= {0, 0, 11, 103}

-- oriyaDigitTwo BMPString ::= {0, 0, 11, 104}

-- oriyaDigitThree BMPString ::= {0, 0, 11, 105}

-- oriyaDigitFour BMPString ::= {0, 0, 11, 106}

-- oriyaDigitFive BMPString ::= {0, 0, 11, 107}

-- oriyaDigitSix BMPString ::= {0, 0, 11, 108}

-- oriyaDigitSeven BMPString ::= {0, 0, 11, 109}

-- oriyaDigitEight BMPString ::= {0, 0, 11, 110}

-- oriyaDigitNine BMPString ::= {0, 0, 11, 111}

-- oriyaIsshar BMPString ::= {0, 0, 11, 112}

-- tamilSignAnusvara BMPString ::= {0, 0, 11, 130}

-- tamilSignVisarga BMPString ::= {0, 0, 11, 131}

-- tamilLetterA BMPString ::= {0, 0, 11, 133}

-- tamilLetterAa BMPString ::= {0, 0, 11, 134}

-- tamilLetterI BMPString ::= {0, 0, 11, 135}

-- tamilLetterIi BMPString ::= {0, 0, 11, 136}

-- tamilLetterU BMPString ::= {0, 0, 11, 137}

-- tamilLetterUu BMPString ::= {0, 0, 11, 138}

-- tamilLetterE BMPString ::= {0, 0, 11, 142}

-- tamilLetterEe BMPString ::= {0, 0, 11, 143}

-- tamilLetterAi BMPString ::= {0, 0, 11, 144}

-- tamilLetterO BMPString ::= {0, 0, 11, 146}

-- tamilLetterOo BMPString ::= {0, 0, 11, 147}

-- tamilLetterAu BMPString ::= {0, 0, 11, 148}

-- tamilLetterKa BMPString ::= {0, 0, 11, 149}

-- tamilLetterNga BMPString ::= {0, 0, 11, 153}

-- tamilLetterCa BMPString ::= {0, 0, 11, 154}

-- tamilLetterJa BMPString ::= {0, 0, 11, 156}

-- tamilLetterNya BMPString ::= {0, 0, 11, 158}

-- tamilLetterTta BMPString ::= {0, 0, 11, 159}

-- tamilLetterNna BMPString ::= {0, 0, 11, 163}

-- tamilLetterTa BMPString ::= {0, 0, 11, 164}

-- tamilLetterNa BMPString ::= {0, 0, 11, 168}

-- tamilLetterNnna BMPString ::= {0, 0, 11, 169}

-- tamilLetterPa BMPString ::= {0, 0, 11, 170}

-- tamilLetterMa BMPString ::= {0, 0, 11, 174}

-- tamilLetterYa BMPString ::= {0, 0, 11, 175}

-- tamilLetterRa BMPString ::= {0, 0, 11, 176}

-- tamilLetterRra BMPString ::= {0, 0, 11, 177}

-- tamilLetterLa BMPString ::= {0, 0, 11, 178}

-- tamilLetterLla BMPString ::= {0, 0, 11, 179}

-- tamilLetterLlla BMPString ::= {0, 0, 11, 180}

-- tamilLetterVa BMPString ::= {0, 0, 11, 181}

-- tamilLetterSsa BMPString ::= {0, 0, 11, 183}

-- tamilLetterSa BMPString ::= {0, 0, 11, 184}

-- tamilLetterHa BMPString ::= {0, 0, 11, 185}

-- tamilVowelSignAa BMPString ::= {0, 0, 11, 190}

-- tamilVowelSignI BMPString ::= {0, 0, 11, 191}

-- tamilVowelSignIi BMPString ::= {0, 0, 11, 192}

-- tamilVowelSignU BMPString ::= {0, 0, 11, 193}

-- tamilVowelSignUu BMPString ::= {0, 0, 11, 194}

-- tamilVowelSignE BMPString ::= {0, 0, 11, 198}

-- tamilVowelSignEe BMPString ::= {0, 0, 11, 199}

-- tamilVowelSignAi BMPString ::= {0, 0, 11, 200}

-- tamilVowelSignO BMPString ::= {0, 0, 11, 202}

-- tamilVowelSignOo BMPString ::= {0, 0, 11, 203}

-- tamilVowelSignAu BMPString ::= {0, 0, 11, 204}

-- tamilSignVirama BMPString ::= {0, 0, 11, 205}

-- tamilAuLengthMark BMPString ::= {0, 0, 11, 215}

-- tamilDigitOne BMPString ::= {0, 0, 11, 231}

-- tamilDigitTwo BMPString ::= {0, 0, 11, 232}

-- tamilDigitThree BMPString ::= {0, 0, 11, 233}

-- tamilDigitFour BMPString ::= {0, 0, 11, 234}

-- tamilDigitFive BMPString ::= {0, 0, 11, 235}

-- tamilDigitSix BMPString ::= {0, 0, 11, 236}

-- tamilDigitSeven BMPString ::= {0, 0, 11, 237}

-- tamilDigitEight BMPString ::= {0, 0, 11, 238}

-- tamilDigitNine BMPString ::= {0, 0, 11, 239}

-- tamilNumberTen BMPString ::= {0, 0, 11, 240}

-- tamilNumberOneHundred BMPString ::= {0, 0, 11, 241}

-- tamilNumberOneThousand BMPString ::= {0, 0, 11, 242}

-- teluguSignCandrabindu BMPString ::= {0, 0, 12, 1}

-- teluguSignAnusvara BMPString ::= {0, 0, 12, 2}

-- teluguSignVisarga BMPString ::= {0, 0, 12, 3}

-- teluguLetterA BMPString ::= {0, 0, 12, 5}

-- teluguLetterAa BMPString ::= {0, 0, 12, 6}

-- teluguLetterI BMPString ::= {0, 0, 12, 7}

-- teluguLetterIi BMPString ::= {0, 0, 12, 8}

-- teluguLetterU BMPString ::= {0, 0, 12, 9}

-- teluguLetterUu BMPString ::= {0, 0, 12, 10}

-- teluguLetterVocalicR BMPString ::= {0, 0, 12, 11}

-- teluguLetterVocalicL BMPString ::= {0, 0, 12, 12}

-- teluguLetterE BMPString ::= {0, 0, 12, 14}

-- teluguLetterEe BMPString ::= {0, 0, 12, 15}

-- teluguLetterAi BMPString ::= {0, 0, 12, 16}

-- teluguLetterO BMPString ::= {0, 0, 12, 18}

-- teluguLetterOo BMPString ::= {0, 0, 12, 19}

-- teluguLetterAu BMPString ::= {0, 0, 12, 20}

-- teluguLetterKa BMPString ::= {0, 0, 12, 21}

-- teluguLetterKha BMPString ::= {0, 0, 12, 22}

-- teluguLetterGa BMPString ::= {0, 0, 12, 23}

-- teluguLetterGha BMPString ::= {0, 0, 12, 24}

-- teluguLetterNga BMPString ::= {0, 0, 12, 25}

-- teluguLetterCa BMPString ::= {0, 0, 12, 26}

-- teluguLetterCha BMPString ::= {0, 0, 12, 27}

-- teluguLetterJa BMPString ::= {0, 0, 12, 28}

-- teluguLetterJha BMPString ::= {0, 0, 12, 29}

-- teluguLetterNya BMPString ::= {0, 0, 12, 30}

-- teluguLetterTta BMPString ::= {0, 0, 12, 31}

-- teluguLetterTtha BMPString ::= {0, 0, 12, 32}

-- teluguLetterDda BMPString ::= {0, 0, 12, 33}

-- teluguLetterDdha BMPString ::= {0, 0, 12, 34}

-- teluguLetterNna BMPString ::= {0, 0, 12, 35}

-- teluguLetterTa BMPString ::= {0, 0, 12, 36}

-- teluguLetterTha BMPString ::= {0, 0, 12, 37}

-- teluguLetterDa BMPString ::= {0, 0, 12, 38}

-- teluguLetterDha BMPString ::= {0, 0, 12, 39}

-- teluguLetterNa BMPString ::= {0, 0, 12, 40}

-- teluguLetterPa BMPString ::= {0, 0, 12, 42}

-- teluguLetterPha BMPString ::= {0, 0, 12, 43}

-- teluguLetterBa BMPString ::= {0, 0, 12, 44}

-- teluguLetterBha BMPString ::= {0, 0, 12, 45}

-- teluguLetterMa BMPString ::= {0, 0, 12, 46}

-- teluguLetterYa BMPString ::= {0, 0, 12, 47}

-- teluguLetterRa BMPString ::= {0, 0, 12, 48}

-- teluguLetterRra BMPString ::= {0, 0, 12, 49}

-- teluguLetterLa BMPString ::= {0, 0, 12, 50}

-- teluguLetterLla BMPString ::= {0, 0, 12, 51}

-- teluguLetterVa BMPString ::= {0, 0, 12, 53}

-- teluguLetterSha BMPString ::= {0, 0, 12, 54}

-- teluguLetterSsa BMPString ::= {0, 0, 12, 55}

-- teluguLetterSa BMPString ::= {0, 0, 12, 56}

-- teluguLetterHa BMPString ::= {0, 0, 12, 57}

-- teluguVowelSignAa BMPString ::= {0, 0, 12, 62}

-- teluguVowelSignI BMPString ::= {0, 0, 12, 63}

-- teluguVowelSignIi BMPString ::= {0, 0, 12, 64}

-- teluguVowelSignU BMPString ::= {0, 0, 12, 65}

-- teluguVowelSignUu BMPString ::= {0, 0, 12, 66}

-- teluguVowelSignVocalicR BMPString ::= {0, 0, 12, 67}

-- teluguVowelSignVocalicRr BMPString ::= {0, 0, 12, 68}

-- teluguVowelSignE BMPString ::= {0, 0, 12, 70}

-- teluguVowelSignEe BMPString ::= {0, 0, 12, 71}

-- teluguVowelSignAi BMPString ::= {0, 0, 12, 72}

-- teluguVowelSignO BMPString ::= {0, 0, 12, 74}

-- teluguVowelSignOo BMPString ::= {0, 0, 12, 75}

-- teluguVowelSignAu BMPString ::= {0, 0, 12, 76}

-- teluguSignVirama BMPString ::= {0, 0, 12, 77}

-- teluguLengthMark BMPString ::= {0, 0, 12, 85}

-- teluguAiLengthMark BMPString ::= {0, 0, 12, 86}

-- teluguLetterVocalicRr BMPString ::= {0, 0, 12, 96}

-- teluguLetterVocalicLl BMPString ::= {0, 0, 12, 97}

-- teluguDigitZero BMPString ::= {0, 0, 12, 102}

-- teluguDigitOne BMPString ::= {0, 0, 12, 103}

-- teluguDigitTwo BMPString ::= {0, 0, 12, 104}

-- teluguDigitThree BMPString ::= {0, 0, 12, 105}

-- teluguDigitFour BMPString ::= {0, 0, 12, 106}

-- teluguDigitFive BMPString ::= {0, 0, 12, 107}

-- teluguDigitSix BMPString ::= {0, 0, 12, 108}

-- teluguDigitSeven BMPString ::= {0, 0, 12, 109}

-- teluguDigitEight BMPString ::= {0, 0, 12, 110}

-- teluguDigitNine BMPString ::= {0, 0, 12, 111}

-- kannadaSignAnusvara BMPString ::= {0, 0, 12, 130}

-- kannadaSignVisarga BMPString ::= {0, 0, 12, 131}

-- kannadaLetterA BMPString ::= {0, 0, 12, 133}

-- kannadaLetterAa BMPString ::= {0, 0, 12, 134}

-- kannadaLetterI BMPString ::= {0, 0, 12, 135}

-- kannadaLetterIi BMPString ::= {0, 0, 12, 136}

-- kannadaLetterU BMPString ::= {0, 0, 12, 137}

-- kannadaLetterUu BMPString ::= {0, 0, 12, 138}

-- kannadaLetterVocalicR BMPString ::= {0, 0, 12, 139}

-- kannadaLetterVocalicL BMPString ::= {0, 0, 12, 140}

-- kannadaLetterE BMPString ::= {0, 0, 12, 142}

-- kannadaLetterEe BMPString ::= {0, 0, 12, 143}

-- kannadaLetterAi BMPString ::= {0, 0, 12, 144}

-- kannadaLetterO BMPString ::= {0, 0, 12, 146}

-- kannadaLetterOo BMPString ::= {0, 0, 12, 147}

-- kannadaLetterAu BMPString ::= {0, 0, 12, 148}

-- kannadaLetterKa BMPString ::= {0, 0, 12, 149}

-- kannadaLetterKha BMPString ::= {0, 0, 12, 150}

-- kannadaLetterGa BMPString ::= {0, 0, 12, 151}

-- kannadaLetterGha BMPString ::= {0, 0, 12, 152}

-- kannadaLetterNga BMPString ::= {0, 0, 12, 153}

-- kannadaLetterCa BMPString ::= {0, 0, 12, 154}

-- kannadaLetterCha BMPString ::= {0, 0, 12, 155}

-- kannadaLetterJa BMPString ::= {0, 0, 12, 156}

-- kannadaLetterJha BMPString ::= {0, 0, 12, 157}

-- kannadaLetterNya BMPString ::= {0, 0, 12, 158}

-- kannadaLetterTta BMPString ::= {0, 0, 12, 159}

-- kannadaLetterTtha BMPString ::= {0, 0, 12, 160}

-- kannadaLetterDda BMPString ::= {0, 0, 12, 161}

-- kannadaLetterDdha BMPString ::= {0, 0, 12, 162}

-- kannadaLetterNna BMPString ::= {0, 0, 12, 163}

-- kannadaLetterTa BMPString ::= {0, 0, 12, 164}

-- kannadaLetterTha BMPString ::= {0, 0, 12, 165}

-- kannadaLetterDa BMPString ::= {0, 0, 12, 166}

-- kannadaLetterDha BMPString ::= {0, 0, 12, 167}

-- kannadaLetterNa BMPString ::= {0, 0, 12, 168}

-- kannadaLetterPa BMPString ::= {0, 0, 12, 170}

-- kannadaLetterPha BMPString ::= {0, 0, 12, 171}

-- kannadaLetterBa BMPString ::= {0, 0, 12, 172}

-- kannadaLetterBha BMPString ::= {0, 0, 12, 173}

-- kannadaLetterMa BMPString ::= {0, 0, 12, 174}

-- kannadaLetterYa BMPString ::= {0, 0, 12, 175}

-- kannadaLetterRa BMPString ::= {0, 0, 12, 176}

-- kannadaLetterRra BMPString ::= {0, 0, 12, 177}

-- kannadaLetterLa BMPString ::= {0, 0, 12, 178}

-- kannadaLetterLla BMPString ::= {0, 0, 12, 179}

-- kannadaLetterVa BMPString ::= {0, 0, 12, 181}

-- kannadaLetterSha BMPString ::= {0, 0, 12, 182}

-- kannadaLetterSsa BMPString ::= {0, 0, 12, 183}

-- kannadaLetterSa BMPString ::= {0, 0, 12, 184}

-- kannadaLetterHa BMPString ::= {0, 0, 12, 185}

-- kannadaVowelSignAa BMPString ::= {0, 0, 12, 190}

-- kannadaVowelSignI BMPString ::= {0, 0, 12, 191}

-- kannadaVowelSignIi BMPString ::= {0, 0, 12, 192}

-- kannadaVowelSignU BMPString ::= {0, 0, 12, 193}

-- kannadaVowelSignUu BMPString ::= {0, 0, 12, 194}

-- kannadaVowelSignVocalicR BMPString ::= {0, 0, 12, 195}

-- kannadaVowelSignVocalicRr BMPString ::= {0, 0, 12, 196}

-- kannadaVowelSignE BMPString ::= {0, 0, 12, 198}

-- kannadaVowelSignEe BMPString ::= {0, 0, 12, 199}

-- kannadaVowelSignAi BMPString ::= {0, 0, 12, 200}

-- kannadaVowelSignO BMPString ::= {0, 0, 12, 202}

-- kannadaVowelSignOo BMPString ::= {0, 0, 12, 203}

-- kannadaVowelSignAu BMPString ::= {0, 0, 12, 204}

-- kannadaSignVirama BMPString ::= {0, 0, 12, 205}

-- kannadaLengthMark BMPString ::= {0, 0, 12, 213}

-- kannadaAiLengthMark BMPString ::= {0, 0, 12, 214}

-- kannadaLetterFa BMPString ::= {0, 0, 12, 222}

-- kannadaLetterVocalicRr BMPString ::= {0, 0, 12, 224}

-- kannadaLetterVocalicLl BMPString ::= {0, 0, 12, 225}

-- kannadaDigitZero BMPString ::= {0, 0, 12, 230}

-- kannadaDigitOne BMPString ::= {0, 0, 12, 231}

-- kannadaDigitTwo BMPString ::= {0, 0, 12, 232}

-- kannadaDigitThree BMPString ::= {0, 0, 12, 233}

-- kannadaDigitFour BMPString ::= {0, 0, 12, 234}

-- kannadaDigitFive BMPString ::= {0, 0, 12, 235}

-- kannadaDigitSix BMPString ::= {0, 0, 12, 236}

-- kannadaDigitSeven BMPString ::= {0, 0, 12, 237}

-- kannadaDigitEight BMPString ::= {0, 0, 12, 238}

-- kannadaDigitNine BMPString ::= {0, 0, 12, 239}

-- malayalamSignAnusvara BMPString ::= {0, 0, 13, 2}

-- malayalamSignVisarga BMPString ::= {0, 0, 13, 3}

-- malayalamLetterA BMPString ::= {0, 0, 13, 5}

-- malayalamLetterAa BMPString ::= {0, 0, 13, 6}

-- malayalamLetterI BMPString ::= {0, 0, 13, 7}

-- malayalamLetterIi BMPString ::= {0, 0, 13, 8}

-- malayalamLetterU BMPString ::= {0, 0, 13, 9}

-- malayalamLetterUu BMPString ::= {0, 0, 13, 10}

-- malayalamLetterVocalicR BMPString ::= {0, 0, 13, 11}

-- malayalamLetterVocalicL BMPString ::= {0, 0, 13, 12}

-- malayalamLetterE BMPString ::= {0, 0, 13, 14}

-- malayalamLetterEe BMPString ::= {0, 0, 13, 15}

-- malayalamLetterAi BMPString ::= {0, 0, 13, 16}

-- malayalamLetterO BMPString ::= {0, 0, 13, 18}

-- malayalamLetterOo BMPString ::= {0, 0, 13, 19}

-- malayalamLetterAu BMPString ::= {0, 0, 13, 20}

-- malayalamLetterKa BMPString ::= {0, 0, 13, 21}

-- malayalamLetterKha BMPString ::= {0, 0, 13, 22}

-- malayalamLetterGa BMPString ::= {0, 0, 13, 23}

-- malayalamLetterGha BMPString ::= {0, 0, 13, 24}

-- malayalamLetterNga BMPString ::= {0, 0, 13, 25}

-- malayalamLetterCa BMPString ::= {0, 0, 13, 26}

-- malayalamLetterCha BMPString ::= {0, 0, 13, 27}

-- malayalamLetterJa BMPString ::= {0, 0, 13, 28}

-- malayalamLetterJha BMPString ::= {0, 0, 13, 29}

-- malayalamLetterNya BMPString ::= {0, 0, 13, 30}

-- malayalamLetterTta BMPString ::= {0, 0, 13, 31}

-- malayalamLetterTtha BMPString ::= {0, 0, 13, 32}

-- malayalamLetterDda BMPString ::= {0, 0, 13, 33}

-- malayalamLetterDdha BMPString ::= {0, 0, 13, 34}

-- malayalamLetterNna BMPString ::= {0, 0, 13, 35}

-- malayalamLetterTa BMPString ::= {0, 0, 13, 36}

-- malayalamLetterTha BMPString ::= {0, 0, 13, 37}

-- malayalamLetterDa BMPString ::= {0, 0, 13, 38}

-- malayalamLetterDha BMPString ::= {0, 0, 13, 39}

-- malayalamLetterNa BMPString ::= {0, 0, 13, 40}

-- malayalamLetterPa BMPString ::= {0, 0, 13, 42}

-- malayalamLetterPha BMPString ::= {0, 0, 13, 43}

-- malayalamLetterBa BMPString ::= {0, 0, 13, 44}

-- malayalamLetterBha BMPString ::= {0, 0, 13, 45}

-- malayalamLetterMa BMPString ::= {0, 0, 13, 46}

-- malayalamLetterYa BMPString ::= {0, 0, 13, 47}

-- malayalamLetterRa BMPString ::= {0, 0, 13, 48}

-- malayalamLetterRra BMPString ::= {0, 0, 13, 49}

-- malayalamLetterLa BMPString ::= {0, 0, 13, 50}

-- malayalamLetterLla BMPString ::= {0, 0, 13, 51}

-- malayalamLetterLlla BMPString ::= {0, 0, 13, 52}

-- malayalamLetterVa BMPString ::= {0, 0, 13, 53}

-- malayalamLetterSha BMPString ::= {0, 0, 13, 54}

-- malayalamLetterSsa BMPString ::= {0, 0, 13, 55}

-- malayalamLetterSa BMPString ::= {0, 0, 13, 56}

-- malayalamLetterHa BMPString ::= {0, 0, 13, 57}

-- malayalamVowelSignAa BMPString ::= {0, 0, 13, 62}

-- malayalamVowelSignI BMPString ::= {0, 0, 13, 63}

-- malayalamVowelSignIi BMPString ::= {0, 0, 13, 64}

-- malayalamVowelSignU BMPString ::= {0, 0, 13, 65}

-- malayalamVowelSignUu BMPString ::= {0, 0, 13, 66}

-- malayalamVowelSignVocalicR BMPString ::= {0, 0, 13, 67}

-- malayalamVowelSignE BMPString ::= {0, 0, 13, 70}

-- malayalamVowelSignEe BMPString ::= {0, 0, 13, 71}

-- malayalamVowelSignAi BMPString ::= {0, 0, 13, 72}

-- malayalamVowelSignO BMPString ::= {0, 0, 13, 74}

-- malayalamVowelSignOo BMPString ::= {0, 0, 13, 75}

-- malayalamVowelSignAu BMPString ::= {0, 0, 13, 76}

-- malayalamSignVirama BMPString ::= {0, 0, 13, 77}

-- malayalamAuLengthMark BMPString ::= {0, 0, 13, 87}

-- malayalamLetterVocalicRr BMPString ::= {0, 0, 13, 96}

-- malayalamLetterVocalicLl BMPString ::= {0, 0, 13, 97}

-- malayalamDigitZero BMPString ::= {0, 0, 13, 102}

-- malayalamDigitOne BMPString ::= {0, 0, 13, 103}

-- malayalamDigitTwo BMPString ::= {0, 0, 13, 104}

-- malayalamDigitThree BMPString ::= {0, 0, 13, 105}

-- malayalamDigitFour BMPString ::= {0, 0, 13, 106}

-- malayalamDigitFive BMPString ::= {0, 0, 13, 107}

-- malayalamDigitSix BMPString ::= {0, 0, 13, 108}

-- malayalamDigitSeven BMPString ::= {0, 0, 13, 109}

-- malayalamDigitEight BMPString ::= {0, 0, 13, 110}

-- malayalamDigitNine BMPString ::= {0, 0, 13, 111}

-- sinhalaSignAnusvaraya BMPString ::= {0, 0, 13, 130}

-- sinhalaSignVisargaya BMPString ::= {0, 0, 13, 131}

-- sinhalaLetterAyanna BMPString ::= {0, 0, 13, 133}

-- sinhalaLetterAayanna BMPString ::= {0, 0, 13, 134}

-- sinhalaLetterAeyanna BMPString ::= {0, 0, 13, 135}

-- sinhalaLetterAeeyanna BMPString ::= {0, 0, 13, 136}

-- sinhalaLetterIyanna BMPString ::= {0, 0, 13, 137}

-- sinhalaLetterIiyanna BMPString ::= {0, 0, 13, 138}

-- sinhalaLetterUyanna BMPString ::= {0, 0, 13, 139}

-- sinhalaLetterUuyanna BMPString ::= {0, 0, 13, 140}

-- sinhalaLetterIruyanna BMPString ::= {0, 0, 13, 141}

-- sinhalaLetterIruuyanna BMPString ::= {0, 0, 13, 142}

-- sinhalaLetterIluyanna BMPString ::= {0, 0, 13, 143}

-- sinhalaLetterIluuyanna BMPString ::= {0, 0, 13, 144}

-- sinhalaLetterEyanna BMPString ::= {0, 0, 13, 145}

-- sinhalaLetterEeyanna BMPString ::= {0, 0, 13, 146}

-- sinhalaLetterAiyanna BMPString ::= {0, 0, 13, 147}

-- sinhalaLetterOyanna BMPString ::= {0, 0, 13, 148}

-- sinhalaLetterOoyanna BMPString ::= {0, 0, 13, 149}

-- sinhalaLetterAuyanna BMPString ::= {0, 0, 13, 150}

-- sinhalaLetterAlpapraanaKayanna BMPString ::= {0, 0, 13, 154}

-- sinhalaLetterMahaapraanaKayanna BMPString ::= {0, 0, 13, 155}

-- sinhalaLetterAlpapraanaGayanna BMPString ::= {0, 0, 13, 156}

-- sinhalaLetterMahaapraanaGayanna BMPString ::= {0, 0, 13, 157}

-- sinhalaLetterKantajaNaasikyaya BMPString ::= {0, 0, 13, 158}

-- sinhalaLetterSanyakaGayanna BMPString ::= {0, 0, 13, 159}

-- sinhalaLetterAlpapraanaCayanna BMPString ::= {0, 0, 13, 160}

-- sinhalaLetterMahaapraanaCayanna BMPString ::= {0, 0, 13, 161}

-- sinhalaLetterAlpapraanaJayanna BMPString ::= {0, 0, 13, 162}

-- sinhalaLetterMahaapraanaJayanna BMPString ::= {0, 0, 13, 163}

-- sinhalaLetterTaalujaNaasikyaya BMPString ::= {0, 0, 13, 164}

-- sinhalaLetterTaalujaSanyoogaNaaksikyaya BMPString ::= {0, 0, 13, 165}

-- sinhalaLetterSanyakaJayanna BMPString ::= {0, 0, 13, 166}

-- sinhalaLetterAlpapraanaTtayanna BMPString ::= {0, 0, 13, 167}

-- sinhalaLetterMahaapraanaTtayanna BMPString ::= {0, 0, 13, 168}

-- sinhalaLetterAlpapraanaDdayanna BMPString ::= {0, 0, 13, 169}

-- sinhalaLetterMahaapraanaDdayanna BMPString ::= {0, 0, 13, 170}

-- sinhalaLetterMuurdhajaNayanna BMPString ::= {0, 0, 13, 171}

-- sinhalaLetterSanyakaDdayanna BMPString ::= {0, 0, 13, 172}

-- sinhalaLetterAlpapraanaTayanna BMPString ::= {0, 0, 13, 173}

-- sinhalaLetterMahaapraanaTayanna BMPString ::= {0, 0, 13, 174}

-- sinhalaLetterAlpapraanaDayanna BMPString ::= {0, 0, 13, 175}

-- sinhalaLetterMahaapraanaDayanna BMPString ::= {0, 0, 13, 176}

-- sinhalaLetterDantajaNayanna BMPString ::= {0, 0, 13, 177}

-- sinhalaLetterSanyakaDayanna BMPString ::= {0, 0, 13, 179}

-- sinhalaLetterAlpapraanaPayanna BMPString ::= {0, 0, 13, 180}

-- sinhalaLetterMahaapraanaPayanna BMPString ::= {0, 0, 13, 181}

-- sinhalaLetterAlpapraanaBayanna BMPString ::= {0, 0, 13, 182}

-- sinhalaLetterMahaapraanaBayanna BMPString ::= {0, 0, 13, 183}

-- sinhalaLetterMayanna BMPString ::= {0, 0, 13, 184}

-- sinhalaLetterAmbaBayanna BMPString ::= {0, 0, 13, 185}

-- sinhalaLetterYayanna BMPString ::= {0, 0, 13, 186}

-- sinhalaLetterRayanna BMPString ::= {0, 0, 13, 187}

-- sinhalaLetterDantajaLayanna BMPString ::= {0, 0, 13, 189}

-- sinhalaLetterVayanna BMPString ::= {0, 0, 13, 192}

-- sinhalaLetterTaalujaSayanna BMPString ::= {0, 0, 13, 193}

-- sinhalaLetterMuurdhajaSayanna BMPString ::= {0, 0, 13, 194}

-- sinhalaLetterDantajaSayanna BMPString ::= {0, 0, 13, 195}

-- sinhalaLetterHayanna BMPString ::= {0, 0, 13, 196}

-- sinhalaLetterMuurdhajaLayanna BMPString ::= {0, 0, 13, 197}

-- sinhalaLetterFayanna BMPString ::= {0, 0, 13, 198}

-- sinhalaSignAl-lakuna BMPString ::= {0, 0, 13, 202}

-- sinhalaVowelSignAela-pilla BMPString ::= {0, 0, 13, 207}

-- sinhalaVowelSignKettiAeda-pilla BMPString ::= {0, 0, 13, 208}

-- sinhalaVowelSignDigaAeda-pilla BMPString ::= {0, 0, 13, 209}

-- sinhalaVowelSignKettiIs-pilla BMPString ::= {0, 0, 13, 210}

-- sinhalaVowelSignDigaIs-pilla BMPString ::= {0, 0, 13, 211}

-- sinhalaVowelSignKettiPaa-pilla BMPString ::= {0, 0, 13, 212}

-- sinhalaVowelSignDigaPaa-pilla BMPString ::= {0, 0, 13, 214}

-- sinhalaVowelSignGaetta-pilla BMPString ::= {0, 0, 13, 216}

-- sinhalaVowelSignKombuva BMPString ::= {0, 0, 13, 217}

-- sinhalaVowelSignDigaKombuva BMPString ::= {0, 0, 13, 218}

-- sinhalaVowelSignKombuDeka BMPString ::= {0, 0, 13, 219}

-- sinhalaVowelSignKombuvaHaaAela-pilla BMPString ::= {0, 0, 13, 220}

-- sinhalaVowelSignKombuvaHaaDigaAela-pilla BMPString ::= {0, 0, 13, 221}

-- sinhalaVowelSignKombuvaHaaGayanukitta BMPString ::= {0, 0, 13, 222}

-- sinhalaVowelSignGayanukitta BMPString ::= {0, 0, 13, 223}

-- sinhalaVowelSignDigaGaetta-pilla BMPString ::= {0, 0, 13, 242}

-- sinhalaVowelSignDigaGayanukitta BMPString ::= {0, 0, 13, 243}

-- sinhalaPunctuationKunddaliya BMPString ::= {0, 0, 13, 244}

-- thaiCharacterKoKai BMPString ::= {0, 0, 14, 1}

-- thaiCharacterKhoKhai BMPString ::= {0, 0, 14, 2}

-- thaiCharacterKhoKhuat BMPString ::= {0, 0, 14, 3}

-- thaiCharacterKhoKhwai BMPString ::= {0, 0, 14, 4}

-- thaiCharacterKhoKhon BMPString ::= {0, 0, 14, 5}

-- thaiCharacterKhoRakhang BMPString ::= {0, 0, 14, 6}

-- thaiCharacterNgoNgu BMPString ::= {0, 0, 14, 7}

-- thaiCharacterChoChan BMPString ::= {0, 0, 14, 8}

-- thaiCharacterChoChing BMPString ::= {0, 0, 14, 9}

-- thaiCharacterChoChang BMPString ::= {0, 0, 14, 10}

-- thaiCharacterSoSo BMPString ::= {0, 0, 14, 11}

-- thaiCharacterChoChoe BMPString ::= {0, 0, 14, 12}

-- thaiCharacterYoYing BMPString ::= {0, 0, 14, 13}

-- thaiCharacterDoChada BMPString ::= {0, 0, 14, 14}

-- thaiCharacterToPatak BMPString ::= {0, 0, 14, 15}

-- thaiCharacterThoThan BMPString ::= {0, 0, 14, 16}

-- thaiCharacterThoNangmontho BMPString ::= {0, 0, 14, 17}

-- thaiCharacterThoPhuthao BMPString ::= {0, 0, 14, 18}

-- thaiCharacterNoNen BMPString ::= {0, 0, 14, 19}

-- thaiCharacterDoDek BMPString ::= {0, 0, 14, 20}

-- thaiCharacterToTao BMPString ::= {0, 0, 14, 21}

-- thaiCharacterThoThung BMPString ::= {0, 0, 14, 22}

-- thaiCharacterThoThahan BMPString ::= {0, 0, 14, 23}

-- thaiCharacterThoThong BMPString ::= {0, 0, 14, 24}

-- thaiCharacterNoNu BMPString ::= {0, 0, 14, 25}

-- thaiCharacterBoBaimai BMPString ::= {0, 0, 14, 26}

-- thaiCharacterPoPla BMPString ::= {0, 0, 14, 27}

-- thaiCharacterPhoPhung BMPString ::= {0, 0, 14, 28}

-- thaiCharacterFoFa BMPString ::= {0, 0, 14, 29}

-- thaiCharacterPhoPhan BMPString ::= {0, 0, 14, 30}

-- thaiCharacterFoFan BMPString ::= {0, 0, 14, 31}

-- thaiCharacterPhoSamphao BMPString ::= {0, 0, 14, 32}

-- thaiCharacterMoMa BMPString ::= {0, 0, 14, 33}

-- thaiCharacterYoYak BMPString ::= {0, 0, 14, 34}

-- thaiCharacterRoRua BMPString ::= {0, 0, 14, 35}

-- thaiCharacterRu BMPString ::= {0, 0, 14, 36}

-- thaiCharacterLoLing BMPString ::= {0, 0, 14, 37}

-- thaiCharacterLu BMPString ::= {0, 0, 14, 38}

-- thaiCharacterWoWaen BMPString ::= {0, 0, 14, 39}

-- thaiCharacterSoSala BMPString ::= {0, 0, 14, 40}

-- thaiCharacterSoRusi BMPString ::= {0, 0, 14, 41}

-- thaiCharacterSoSua BMPString ::= {0, 0, 14, 42}

-- thaiCharacterHoHip BMPString ::= {0, 0, 14, 43}

-- thaiCharacterLoChula BMPString ::= {0, 0, 14, 44}

-- thaiCharacterOAng BMPString ::= {0, 0, 14, 45}

-- thaiCharacterHoNokhuk BMPString ::= {0, 0, 14, 46}

-- thaiCharacterPaiyannoi BMPString ::= {0, 0, 14, 47}

-- thaiCharacterSaraA BMPString ::= {0, 0, 14, 48}

-- thaiCharacterMaiHan-akat BMPString ::= {0, 0, 14, 49}

-- thaiCharacterSaraAa BMPString ::= {0, 0, 14, 50}

-- thaiCharacterSaraAm BMPString ::= {0, 0, 14, 51}

-- thaiCharacterSaraI BMPString ::= {0, 0, 14, 52}

-- thaiCharacterSaraIi BMPString ::= {0, 0, 14, 53}

-- thaiCharacterSaraUe BMPString ::= {0, 0, 14, 54}

-- thaiCharacterSaraUee BMPString ::= {0, 0, 14, 55}

-- thaiCharacterSaraU BMPString ::= {0, 0, 14, 56}

-- thaiCharacterSaraUu BMPString ::= {0, 0, 14, 57}

-- thaiCharacterPhinthu BMPString ::= {0, 0, 14, 58}

-- thaiCurrencySymbolBaht BMPString ::= {0, 0, 14, 63}

-- thaiCharacterSaraE BMPString ::= {0, 0, 14, 64}

-- thaiCharacterSaraAe BMPString ::= {0, 0, 14, 65}

-- thaiCharacterSaraO BMPString ::= {0, 0, 14, 66}

-- thaiCharacterSaraAiMaimuan BMPString ::= {0, 0, 14, 67}

-- thaiCharacterSaraAiMaimalai BMPString ::= {0, 0, 14, 68}

-- thaiCharacterLakkhangyao BMPString ::= {0, 0, 14, 69}

-- thaiCharacterMaiyamok BMPString ::= {0, 0, 14, 70}

-- thaiCharacterMaitaikhu BMPString ::= {0, 0, 14, 71}

-- thaiCharacterMaiEk BMPString ::= {0, 0, 14, 72}

-- thaiCharacterMaiTho BMPString ::= {0, 0, 14, 73}

-- thaiCharacterMaiTri BMPString ::= {0, 0, 14, 74}

-- thaiCharacterMaiChattawa BMPString ::= {0, 0, 14, 75}

-- thaiCharacterThanthakhat BMPString ::= {0, 0, 14, 76}

-- thaiCharacterNikhahit BMPString ::= {0, 0, 14, 77}

-- thaiCharacterYamakkan BMPString ::= {0, 0, 14, 78}

-- thaiCharacterFongman BMPString ::= {0, 0, 14, 79}

-- thaiDigitZero BMPString ::= {0, 0, 14, 80}

-- thaiDigitOne BMPString ::= {0, 0, 14, 81}

-- thaiDigitTwo BMPString ::= {0, 0, 14, 82}

-- thaiDigitThree BMPString ::= {0, 0, 14, 83}

-- thaiDigitFour BMPString ::= {0, 0, 14, 84}

-- thaiDigitFive BMPString ::= {0, 0, 14, 85}

-- thaiDigitSix BMPString ::= {0, 0, 14, 86}

-- thaiDigitSeven BMPString ::= {0, 0, 14, 87}

-- thaiDigitEight BMPString ::= {0, 0, 14, 88}

-- thaiDigitNine BMPString ::= {0, 0, 14, 89}

-- thaiCharacterAngkhankhu BMPString ::= {0, 0, 14, 90}

-- thaiCharacterKhomut BMPString ::= {0, 0, 14, 91}

-- laoLetterKo BMPString ::= {0, 0, 14, 129}

-- laoLetterKhoSung BMPString ::= {0, 0, 14, 130}

-- laoLetterKhoTam BMPString ::= {0, 0, 14, 132}

-- laoLetterNgo BMPString ::= {0, 0, 14, 135}

-- laoLetterCo BMPString ::= {0, 0, 14, 136}

-- laoLetterSoTam BMPString ::= {0, 0, 14, 138}

-- laoLetterNyo BMPString ::= {0, 0, 14, 141}

-- laoLetterDo BMPString ::= {0, 0, 14, 148}

-- laoLetterTo BMPString ::= {0, 0, 14, 149}

-- laoLetterThoSung BMPString ::= {0, 0, 14, 150}

-- laoLetterThoTam BMPString ::= {0, 0, 14, 151}

-- laoLetterNo BMPString ::= {0, 0, 14, 153}

-- laoLetterBo BMPString ::= {0, 0, 14, 154}

-- laoLetterPo BMPString ::= {0, 0, 14, 155}

-- laoLetterPhoSung BMPString ::= {0, 0, 14, 156}

-- laoLetterFoTam BMPString ::= {0, 0, 14, 157}

-- laoLetterPhoTam BMPString ::= {0, 0, 14, 158}

-- laoLetterFoSung BMPString ::= {0, 0, 14, 159}

-- laoLetterMo BMPString ::= {0, 0, 14, 161}

-- laoLetterYo BMPString ::= {0, 0, 14, 162}

-- laoLetterLoLing BMPString ::= {0, 0, 14, 163}

-- laoLetterLoLoot BMPString ::= {0, 0, 14, 165}

-- laoLetterWo BMPString ::= {0, 0, 14, 167}

-- laoLetterSoSung BMPString ::= {0, 0, 14, 170}

-- laoLetterHoSung BMPString ::= {0, 0, 14, 171}

-- laoLetterO BMPString ::= {0, 0, 14, 173}

-- laoLetterHoTam BMPString ::= {0, 0, 14, 174}

-- laoEllipsis BMPString ::= {0, 0, 14, 175}

-- laoVowelSignA BMPString ::= {0, 0, 14, 176}

-- laoVowelSignMaiKan BMPString ::= {0, 0, 14, 177}

-- laoVowelSignAa BMPString ::= {0, 0, 14, 178}

-- laoVowelSignAm BMPString ::= {0, 0, 14, 179}

-- laoVowelSignI BMPString ::= {0, 0, 14, 180}

-- laoVowelSignIi BMPString ::= {0, 0, 14, 181}

-- laoVowelSignY BMPString ::= {0, 0, 14, 182}

-- laoVowelSignYy BMPString ::= {0, 0, 14, 183}

-- laoVowelSignU BMPString ::= {0, 0, 14, 184}

-- laoVowelSignUu BMPString ::= {0, 0, 14, 185}

-- laoVowelSignMaiKon BMPString ::= {0, 0, 14, 187}

-- laoSemivowelSignLo BMPString ::= {0, 0, 14, 188}

-- laoSemivowelSignNyo BMPString ::= {0, 0, 14, 189}

-- laoVowelSignE BMPString ::= {0, 0, 14, 192}

-- laoVowelSignEi BMPString ::= {0, 0, 14, 193}

-- laoVowelSignO BMPString ::= {0, 0, 14, 194}

-- laoVowelSignAy BMPString ::= {0, 0, 14, 195}

-- laoVowelSignAi BMPString ::= {0, 0, 14, 196}

-- laoKoLa BMPString ::= {0, 0, 14, 198}

-- laoToneMaiEk BMPString ::= {0, 0, 14, 200}

-- laoToneMaiTho BMPString ::= {0, 0, 14, 201}

-- laoToneMaiTi BMPString ::= {0, 0, 14, 202}

-- laoToneMaiCatawa BMPString ::= {0, 0, 14, 203}

-- laoCancellationMark BMPString ::= {0, 0, 14, 204}

-- laoNiggahita BMPString ::= {0, 0, 14, 205}

-- laoDigitZero BMPString ::= {0, 0, 14, 208}

-- laoDigitOne BMPString ::= {0, 0, 14, 209}

-- laoDigitTwo BMPString ::= {0, 0, 14, 210}

-- laoDigitThree BMPString ::= {0, 0, 14, 211}

-- laoDigitFour BMPString ::= {0, 0, 14, 212}

-- laoDigitFive BMPString ::= {0, 0, 14, 213}

-- laoDigitSix BMPString ::= {0, 0, 14, 214}

-- laoDigitSeven BMPString ::= {0, 0, 14, 215}

-- laoDigitEight BMPString ::= {0, 0, 14, 216}

-- laoDigitNine BMPString ::= {0, 0, 14, 217}

-- laoHoNo BMPString ::= {0, 0, 14, 220}

-- laoHoMo BMPString ::= {0, 0, 14, 221}

-- tibetanSyllableOm BMPString ::= {0, 0, 15, 0}

-- tibetanMarkGterYigMgoTruncatedA BMPString ::= {0, 0, 15, 1}

-- tibetanMarkGterYigMgo-umRnamBcadMa BMPString ::= {0, 0, 15, 2}

-- tibetanMarkGterYigMgo-umGterTshegMa BMPString ::= {0, 0, 15, 3}

-- tibetanMarkInitialYigMgoMdunMa BMPString ::= {0, 0, 15, 4}

-- tibetanMarkClosingYigMgoSgabMa BMPString ::= {0, 0, 15, 5}

-- tibetanMarkCaretYigMgoPhurShadMa BMPString ::= {0, 0, 15, 6}

-- tibetanMarkYigMgoTshegShadMa BMPString ::= {0, 0, 15, 7}

-- tibetanMarkSbrulShad BMPString ::= {0, 0, 15, 8}

-- tibetanMarkBskurYigMgo BMPString ::= {0, 0, 15, 9}

-- tibetanMarkBka-ShogYigMgo BMPString ::= {0, 0, 15, 10}

-- tibetanMarkIntersyllabicTsheg BMPString ::= {0, 0, 15, 11}

-- tibetanMarkDelimiterTshegBstar BMPString ::= {0, 0, 15, 12}

-- tibetanMarkShad BMPString ::= {0, 0, 15, 13}

-- tibetanMarkNyisShad BMPString ::= {0, 0, 15, 14}

-- tibetanMarkTshegShad BMPString ::= {0, 0, 15, 15}

-- tibetanMarkNyisTshegShad BMPString ::= {0, 0, 15, 16}

-- tibetanMarkRinChenSpungsShad BMPString ::= {0, 0, 15, 17}

-- tibetanMarkRgyaGramShad BMPString ::= {0, 0, 15, 18}

-- tibetanMarkCaret-dzudRtagsMeLongCan BMPString ::= {0, 0, 15, 19}

-- tibetanMarkGterTsheg BMPString ::= {0, 0, 15, 20}

-- tibetanLogotypeSignChadRtags BMPString ::= {0, 0, 15, 21}

-- tibetanLogotypeSignLhagRtags BMPString ::= {0, 0, 15, 22}

-- tibetanAstrologicalSignSgraGcan-charRtags BMPString ::= {0, 0, 15, 23}

-- tibetanAstrologicalSign-khyudPa BMPString ::= {0, 0, 15, 24}

-- tibetanAstrologicalSignSdongTshugs BMPString ::= {0, 0, 15, 25}

-- tibetanSignRdelDkarGcig BMPString ::= {0, 0, 15, 26}

-- tibetanSignRdelDkarGnyis BMPString ::= {0, 0, 15, 27}

-- tibetanSignRdelDkarGsum BMPString ::= {0, 0, 15, 28}

-- tibetanSignRdelNagGcig BMPString ::= {0, 0, 15, 29}

-- tibetanSignRdelNagGnyis BMPString ::= {0, 0, 15, 30}

-- tibetanSignRdelDkarRdelNag BMPString ::= {0, 0, 15, 31}

-- tibetanDigitZero BMPString ::= {0, 0, 15, 32}

-- tibetanDigitOne BMPString ::= {0, 0, 15, 33}

-- tibetanDigitTwo BMPString ::= {0, 0, 15, 34}

-- tibetanDigitThree BMPString ::= {0, 0, 15, 35}

-- tibetanDigitFour BMPString ::= {0, 0, 15, 36}

-- tibetanDigitFive BMPString ::= {0, 0, 15, 37}

-- tibetanDigitSix BMPString ::= {0, 0, 15, 38}

-- tibetanDigitSeven BMPString ::= {0, 0, 15, 39}

-- tibetanDigitEight BMPString ::= {0, 0, 15, 40}

-- tibetanDigitNine BMPString ::= {0, 0, 15, 41}

-- tibetanDigitHalfOne BMPString ::= {0, 0, 15, 42}

-- tibetanDigitHalfTwo BMPString ::= {0, 0, 15, 43}

-- tibetanDigitHalfThree BMPString ::= {0, 0, 15, 44}

-- tibetanDigitHalfFour BMPString ::= {0, 0, 15, 45}

-- tibetanDigitHalfFive BMPString ::= {0, 0, 15, 46}

-- tibetanDigitHalfSix BMPString ::= {0, 0, 15, 47}

-- tibetanDigitHalfSeven BMPString ::= {0, 0, 15, 48}

-- tibetanDigitHalfEight BMPString ::= {0, 0, 15, 49}

-- tibetanDigitHalfNine BMPString ::= {0, 0, 15, 50}

-- tibetanDigitHalfZero BMPString ::= {0, 0, 15, 51}

-- tibetanMarkBsdusRtags BMPString ::= {0, 0, 15, 52}

-- tibetanMarkNgasBzungNyiZla BMPString ::= {0, 0, 15, 53}

-- tibetanMarkCaret-dzudRtagsBzhiMigCan BMPString ::= {0, 0, 15, 54}

-- tibetanMarkNgasBzungSgorRtags BMPString ::= {0, 0, 15, 55}

-- tibetanMarkCheMgo BMPString ::= {0, 0, 15, 56}

-- tibetanMarkTsa-phru BMPString ::= {0, 0, 15, 57}

-- tibetanMarkGugRtagsGyon BMPString ::= {0, 0, 15, 58}

-- tibetanMarkGugRtagsGyas BMPString ::= {0, 0, 15, 59}

-- tibetanMarkAngKhangGyon BMPString ::= {0, 0, 15, 60}

-- tibetanMarkAngKhangGyas BMPString ::= {0, 0, 15, 61}

-- tibetanSignYarTshes BMPString ::= {0, 0, 15, 62}

-- tibetanSignMarTshes BMPString ::= {0, 0, 15, 63}

-- tibetanLetterKa BMPString ::= {0, 0, 15, 64}

-- tibetanLetterKha BMPString ::= {0, 0, 15, 65}

-- tibetanLetterGa BMPString ::= {0, 0, 15, 66}

-- tibetanLetterGha BMPString ::= {0, 0, 15, 67}

-- tibetanLetterNga BMPString ::= {0, 0, 15, 68}

-- tibetanLetterCa BMPString ::= {0, 0, 15, 69}

-- tibetanLetterCha BMPString ::= {0, 0, 15, 70}

-- tibetanLetterJa BMPString ::= {0, 0, 15, 71}

-- tibetanLetterNya BMPString ::= {0, 0, 15, 73}

-- tibetanLetterTta BMPString ::= {0, 0, 15, 74}

-- tibetanLetterTtha BMPString ::= {0, 0, 15, 75}

-- tibetanLetterDda BMPString ::= {0, 0, 15, 76}

-- tibetanLetterDdha BMPString ::= {0, 0, 15, 77}

-- tibetanLetterNna BMPString ::= {0, 0, 15, 78}

-- tibetanLetterTa BMPString ::= {0, 0, 15, 79}

-- tibetanLetterTha BMPString ::= {0, 0, 15, 80}

-- tibetanLetterDa BMPString ::= {0, 0, 15, 81}

-- tibetanLetterDha BMPString ::= {0, 0, 15, 82}

-- tibetanLetterNa BMPString ::= {0, 0, 15, 83}

-- tibetanLetterPa BMPString ::= {0, 0, 15, 84}

-- tibetanLetterPha BMPString ::= {0, 0, 15, 85}

-- tibetanLetterBa BMPString ::= {0, 0, 15, 86}

-- tibetanLetterBha BMPString ::= {0, 0, 15, 87}

-- tibetanLetterMa BMPString ::= {0, 0, 15, 88}

-- tibetanLetterTsa BMPString ::= {0, 0, 15, 89}

-- tibetanLetterTsha BMPString ::= {0, 0, 15, 90}

-- tibetanLetterDza BMPString ::= {0, 0, 15, 91}

-- tibetanLetterDzha BMPString ::= {0, 0, 15, 92}

-- tibetanLetterWa BMPString ::= {0, 0, 15, 93}

-- tibetanLetterZha BMPString ::= {0, 0, 15, 94}

-- tibetanLetterZa BMPString ::= {0, 0, 15, 95}

-- tibetanLetter-a BMPString ::= {0, 0, 15, 96}

-- tibetanLetterYa BMPString ::= {0, 0, 15, 97}

-- tibetanLetterRa BMPString ::= {0, 0, 15, 98}

-- tibetanLetterLa BMPString ::= {0, 0, 15, 99}

-- tibetanLetterSha BMPString ::= {0, 0, 15, 100}

-- tibetanLetterSsa BMPString ::= {0, 0, 15, 101}

-- tibetanLetterSa BMPString ::= {0, 0, 15, 102}

-- tibetanLetterHa BMPString ::= {0, 0, 15, 103}

-- tibetanLetterA BMPString ::= {0, 0, 15, 104}

-- tibetanLetterKssa BMPString ::= {0, 0, 15, 105}

-- tibetanLetterFixed-formRa BMPString ::= {0, 0, 15, 106}

-- tibetanVowelSignAa BMPString ::= {0, 0, 15, 113}

-- tibetanVowelSignI BMPString ::= {0, 0, 15, 114}

-- tibetanVowelSignIi BMPString ::= {0, 0, 15, 115}

-- tibetanVowelSignU BMPString ::= {0, 0, 15, 116}

-- tibetanVowelSignUu BMPString ::= {0, 0, 15, 117}

-- tibetanVowelSignVocalicR BMPString ::= {0, 0, 15, 118}

-- tibetanVowelSignVocalicRr BMPString ::= {0, 0, 15, 119}

-- tibetanVowelSignVocalicL BMPString ::= {0, 0, 15, 120}

-- tibetanVowelSignVocalicLl BMPString ::= {0, 0, 15, 121}

-- tibetanVowelSignE BMPString ::= {0, 0, 15, 122}

-- tibetanVowelSignEe BMPString ::= {0, 0, 15, 123}

-- tibetanVowelSignO BMPString ::= {0, 0, 15, 124}

-- tibetanVowelSignOo BMPString ::= {0, 0, 15, 125}

-- tibetanSignRjesSuNgaRo BMPString ::= {0, 0, 15, 126}

-- tibetanSignRnamBcad BMPString ::= {0, 0, 15, 127}

-- tibetanVowelSignReversedI BMPString ::= {0, 0, 15, 128}

-- tibetanVowelSignReversedIi BMPString ::= {0, 0, 15, 129}

-- tibetanSignNyiZlaNaaDa BMPString ::= {0, 0, 15, 130}

-- tibetanSignSnaLdan BMPString ::= {0, 0, 15, 131}

-- tibetanMarkHalanta BMPString ::= {0, 0, 15, 132}

-- tibetanMarkPaluta BMPString ::= {0, 0, 15, 133}

-- tibetanSignLciRtags BMPString ::= {0, 0, 15, 134}

-- tibetanSignYangRtags BMPString ::= {0, 0, 15, 135}

-- tibetanSignLceTsaCan BMPString ::= {0, 0, 15, 136}

-- tibetanSignMchuCan BMPString ::= {0, 0, 15, 137}

-- tibetanSignGruCanRgyings BMPString ::= {0, 0, 15, 138}

-- tibetanSignGruMedRgyings BMPString ::= {0, 0, 15, 139}

-- tibetanSubjoinedLetterKa BMPString ::= {0, 0, 15, 144}

-- tibetanSubjoinedLetterKha BMPString ::= {0, 0, 15, 145}

-- tibetanSubjoinedLetterGa BMPString ::= {0, 0, 15, 146}

-- tibetanSubjoinedLetterGha BMPString ::= {0, 0, 15, 147}

-- tibetanSubjoinedLetterNga BMPString ::= {0, 0, 15, 148}

-- tibetanSubjoinedLetterCa BMPString ::= {0, 0, 15, 149}

-- tibetanSubjoinedLetterCha BMPString ::= {0, 0, 15, 150}

-- tibetanSubjoinedLetterJa BMPString ::= {0, 0, 15, 151}

-- tibetanSubjoinedLetterNya BMPString ::= {0, 0, 15, 153}

-- tibetanSubjoinedLetterTta BMPString ::= {0, 0, 15, 154}

-- tibetanSubjoinedLetterTtha BMPString ::= {0, 0, 15, 155}

-- tibetanSubjoinedLetterDda BMPString ::= {0, 0, 15, 156}

-- tibetanSubjoinedLetterDdha BMPString ::= {0, 0, 15, 157}

-- tibetanSubjoinedLetterNna BMPString ::= {0, 0, 15, 158}

-- tibetanSubjoinedLetterTa BMPString ::= {0, 0, 15, 159}

-- tibetanSubjoinedLetterTha BMPString ::= {0, 0, 15, 160}

-- tibetanSubjoinedLetterDa BMPString ::= {0, 0, 15, 161}

-- tibetanSubjoinedLetterDha BMPString ::= {0, 0, 15, 162}

-- tibetanSubjoinedLetterNa BMPString ::= {0, 0, 15, 163}

-- tibetanSubjoinedLetterPa BMPString ::= {0, 0, 15, 164}

-- tibetanSubjoinedLetterPha BMPString ::= {0, 0, 15, 165}

-- tibetanSubjoinedLetterBa BMPString ::= {0, 0, 15, 166}

-- tibetanSubjoinedLetterBha BMPString ::= {0, 0, 15, 167}

-- tibetanSubjoinedLetterMa BMPString ::= {0, 0, 15, 168}

-- tibetanSubjoinedLetterTsa BMPString ::= {0, 0, 15, 169}

-- tibetanSubjoinedLetterTsha BMPString ::= {0, 0, 15, 170}

-- tibetanSubjoinedLetterDza BMPString ::= {0, 0, 15, 171}

-- tibetanSubjoinedLetterDzha BMPString ::= {0, 0, 15, 172}

-- tibetanSubjoinedLetterWa BMPString ::= {0, 0, 15, 173}

-- tibetanSubjoinedLetterZha BMPString ::= {0, 0, 15, 174}

-- tibetanSubjoinedLetterZa BMPString ::= {0, 0, 15, 175}

-- tibetanSubjoinedLetter-a BMPString ::= {0, 0, 15, 176}

-- tibetanSubjoinedLetterYa BMPString ::= {0, 0, 15, 177}

-- tibetanSubjoinedLetterRa BMPString ::= {0, 0, 15, 178}

-- tibetanSubjoinedLetterLa BMPString ::= {0, 0, 15, 179}

-- tibetanSubjoinedLetterSha BMPString ::= {0, 0, 15, 180}

-- tibetanSubjoinedLetterSsa BMPString ::= {0, 0, 15, 181}

-- tibetanSubjoinedLetterSa BMPString ::= {0, 0, 15, 182}

-- tibetanSubjoinedLetterHa BMPString ::= {0, 0, 15, 183}

-- tibetanSubjoinedLetterA BMPString ::= {0, 0, 15, 184}

-- tibetanSubjoinedLetterKssa BMPString ::= {0, 0, 15, 185}

-- tibetanSubjoinedLetterFixed-formWa BMPString ::= {0, 0, 15, 186}

-- tibetanSubjoinedLetterFixed-formYa BMPString ::= {0, 0, 15, 187}

-- tibetanSubjoinedLetterFixed-formRa BMPString ::= {0, 0, 15, 188}

-- tibetanKuRuKha BMPString ::= {0, 0, 15, 190}

-- tibetanKuRuKhaBzhiMigCan BMPString ::= {0, 0, 15, 191}

-- tibetanCantillationSignHeavyBeat BMPString ::= {0, 0, 15, 192}

-- tibetanCantillationSignLightBeat BMPString ::= {0, 0, 15, 193}

-- tibetanCantillationSignCangTe-u BMPString ::= {0, 0, 15, 194}

-- tibetanCantillationSignSbub-chal BMPString ::= {0, 0, 15, 195}

-- tibetanSymbolDrilBu BMPString ::= {0, 0, 15, 196}

-- tibetanSymbolRdoRje BMPString ::= {0, 0, 15, 197}

-- tibetanSymbolPadmaGdan BMPString ::= {0, 0, 15, 198}

-- tibetanSymbolRdoRjeRgyaGram BMPString ::= {0, 0, 15, 199}

-- tibetanSymbolPhurPa BMPString ::= {0, 0, 15, 200}

-- tibetanSymbolNorBu BMPString ::= {0, 0, 15, 201}

-- tibetanSymbolNorBuNyis-khyil BMPString ::= {0, 0, 15, 202}

-- tibetanSymbolNorBuGsum-khyil BMPString ::= {0, 0, 15, 203}

-- tibetanSymbolNorBuBzhi-khyil BMPString ::= {0, 0, 15, 204}

-- tibetanSignRdelNagGsum BMPString ::= {0, 0, 15, 207}

-- myanmarLetterKa BMPString ::= {0, 0, 16, 0}

-- myanmarLetterKha BMPString ::= {0, 0, 16, 1}

-- myanmarLetterGa BMPString ::= {0, 0, 16, 2}

-- myanmarLetterGha BMPString ::= {0, 0, 16, 3}

-- myanmarLetterNga BMPString ::= {0, 0, 16, 4}

-- myanmarLetterCa BMPString ::= {0, 0, 16, 5}

-- myanmarLetterCha BMPString ::= {0, 0, 16, 6}

-- myanmarLetterJa BMPString ::= {0, 0, 16, 7}

-- myanmarLetterJha BMPString ::= {0, 0, 16, 8}

-- myanmarLetterNya BMPString ::= {0, 0, 16, 9}

-- myanmarLetterNnya BMPString ::= {0, 0, 16, 10}

-- myanmarLetterTta BMPString ::= {0, 0, 16, 11}

-- myanmarLetterTtha BMPString ::= {0, 0, 16, 12}

-- myanmarLetterDda BMPString ::= {0, 0, 16, 13}

-- myanmarLetterDdha BMPString ::= {0, 0, 16, 14}

-- myanmarLetterNna BMPString ::= {0, 0, 16, 15}

-- myanmarLetterTa BMPString ::= {0, 0, 16, 16}

-- myanmarLetterTha BMPString ::= {0, 0, 16, 17}

-- myanmarLetterDa BMPString ::= {0, 0, 16, 18}

-- myanmarLetterDha BMPString ::= {0, 0, 16, 19}

-- myanmarLetterNa BMPString ::= {0, 0, 16, 20}

-- myanmarLetterPa BMPString ::= {0, 0, 16, 21}

-- myanmarLetterPha BMPString ::= {0, 0, 16, 22}

-- myanmarLetterBa BMPString ::= {0, 0, 16, 23}

-- myanmarLetterBha BMPString ::= {0, 0, 16, 24}

-- myanmarLetterMa BMPString ::= {0, 0, 16, 25}

-- myanmarLetterYa BMPString ::= {0, 0, 16, 26}

-- myanmarLetterRa BMPString ::= {0, 0, 16, 27}

-- myanmarLetterLa BMPString ::= {0, 0, 16, 28}

-- myanmarLetterWa BMPString ::= {0, 0, 16, 29}

-- myanmarLetterSa BMPString ::= {0, 0, 16, 30}

-- myanmarLetterHa BMPString ::= {0, 0, 16, 31}

-- myanmarLetterLla BMPString ::= {0, 0, 16, 32}

-- myanmarLetterA BMPString ::= {0, 0, 16, 33}

-- myanmarLetterI BMPString ::= {0, 0, 16, 35}

-- myanmarLetterIi BMPString ::= {0, 0, 16, 36}

-- myanmarLetterU BMPString ::= {0, 0, 16, 37}

-- myanmarLetterUu BMPString ::= {0, 0, 16, 38}

-- myanmarLetterE BMPString ::= {0, 0, 16, 39}

-- myanmarLetterO BMPString ::= {0, 0, 16, 41}

-- myanmarLetterAu BMPString ::= {0, 0, 16, 42}

-- myanmarVowelSignAa BMPString ::= {0, 0, 16, 44}

-- myanmarVowelSignI BMPString ::= {0, 0, 16, 45}

-- myanmarVowelSignIi BMPString ::= {0, 0, 16, 46}

-- myanmarVowelSignU BMPString ::= {0, 0, 16, 47}

-- myanmarVowelSignUu BMPString ::= {0, 0, 16, 48}

-- myanmarVowelSignE BMPString ::= {0, 0, 16, 49}

-- myanmarVowelSignAi BMPString ::= {0, 0, 16, 50}

-- myanmarSignAnusvara BMPString ::= {0, 0, 16, 54}

-- myanmarSignDotBelow BMPString ::= {0, 0, 16, 55}

-- myanmarSignVisarga BMPString ::= {0, 0, 16, 56}

-- myanmarSignVirama BMPString ::= {0, 0, 16, 57}

-- myanmarDigitZero BMPString ::= {0, 0, 16, 64}

-- myanmarDigitOne BMPString ::= {0, 0, 16, 65}

-- myanmarDigitTwo BMPString ::= {0, 0, 16, 66}

-- myanmarDigitThree BMPString ::= {0, 0, 16, 67}

-- myanmarDigitFour BMPString ::= {0, 0, 16, 68}

-- myanmarDigitFive BMPString ::= {0, 0, 16, 69}

-- myanmarDigitSix BMPString ::= {0, 0, 16, 70}

-- myanmarDigitSeven BMPString ::= {0, 0, 16, 71}

-- myanmarDigitEight BMPString ::= {0, 0, 16, 72}

-- myanmarDigitNine BMPString ::= {0, 0, 16, 73}

-- myanmarSignLittleSection BMPString ::= {0, 0, 16, 74}

-- myanmarSignSection BMPString ::= {0, 0, 16, 75}

-- myanmarSymbolLocative BMPString ::= {0, 0, 16, 76}

-- myanmarSymbolCompleted BMPString ::= {0, 0, 16, 77}

-- myanmarSymbolAforementioned BMPString ::= {0, 0, 16, 78}

-- myanmarSymbolGenitive BMPString ::= {0, 0, 16, 79}

-- myanmarLetterSha BMPString ::= {0, 0, 16, 80}

-- myanmarLetterSsa BMPString ::= {0, 0, 16, 81}

-- myanmarLetterVocalicR BMPString ::= {0, 0, 16, 82}

-- myanmarLetterVocalicRr BMPString ::= {0, 0, 16, 83}

-- myanmarLetterVocalicL BMPString ::= {0, 0, 16, 84}

-- myanmarLetterVocalicLl BMPString ::= {0, 0, 16, 85}

-- myanmarVowelSignVocalicR BMPString ::= {0, 0, 16, 86}

-- myanmarVowelSignVocalicRr BMPString ::= {0, 0, 16, 87}

-- myanmarVowelSignVocalicL BMPString ::= {0, 0, 16, 88}

-- myanmarVowelSignVocalicLl BMPString ::= {0, 0, 16, 89}

-- georgianCapitalLetterAn BMPString ::= {0, 0, 16, 160}

-- georgianCapitalLetterBan BMPString ::= {0, 0, 16, 161}

-- georgianCapitalLetterGan BMPString ::= {0, 0, 16, 162}

-- georgianCapitalLetterDon BMPString ::= {0, 0, 16, 163}

-- georgianCapitalLetterEn BMPString ::= {0, 0, 16, 164}

-- georgianCapitalLetterVin BMPString ::= {0, 0, 16, 165}

-- georgianCapitalLetterZen BMPString ::= {0, 0, 16, 166}

-- georgianCapitalLetterTan BMPString ::= {0, 0, 16, 167}

-- georgianCapitalLetterIn BMPString ::= {0, 0, 16, 168}

-- georgianCapitalLetterKan BMPString ::= {0, 0, 16, 169}

-- georgianCapitalLetterLas BMPString ::= {0, 0, 16, 170}

-- georgianCapitalLetterMan BMPString ::= {0, 0, 16, 171}

-- georgianCapitalLetterNar BMPString ::= {0, 0, 16, 172}

-- georgianCapitalLetterOn BMPString ::= {0, 0, 16, 173}

-- georgianCapitalLetterPar BMPString ::= {0, 0, 16, 174}

-- georgianCapitalLetterZhar BMPString ::= {0, 0, 16, 175}

-- georgianCapitalLetterRae BMPString ::= {0, 0, 16, 176}

-- georgianCapitalLetterSan BMPString ::= {0, 0, 16, 177}

-- georgianCapitalLetterTar BMPString ::= {0, 0, 16, 178}

-- georgianCapitalLetterUn BMPString ::= {0, 0, 16, 179}

-- georgianCapitalLetterPhar BMPString ::= {0, 0, 16, 180}

-- georgianCapitalLetterKhar BMPString ::= {0, 0, 16, 181}

-- georgianCapitalLetterGhan BMPString ::= {0, 0, 16, 182}

-- georgianCapitalLetterQar BMPString ::= {0, 0, 16, 183}

-- georgianCapitalLetterShin BMPString ::= {0, 0, 16, 184}

-- georgianCapitalLetterChin BMPString ::= {0, 0, 16, 185}

-- georgianCapitalLetterCan BMPString ::= {0, 0, 16, 186}

-- georgianCapitalLetterJil BMPString ::= {0, 0, 16, 187}

-- georgianCapitalLetterCil BMPString ::= {0, 0, 16, 188}

-- georgianCapitalLetterChar BMPString ::= {0, 0, 16, 189}

-- georgianCapitalLetterXan BMPString ::= {0, 0, 16, 190}

-- georgianCapitalLetterJhan BMPString ::= {0, 0, 16, 191}

-- georgianCapitalLetterHae BMPString ::= {0, 0, 16, 192}

-- georgianCapitalLetterHe BMPString ::= {0, 0, 16, 193}

-- georgianCapitalLetterHie BMPString ::= {0, 0, 16, 194}

-- georgianCapitalLetterWe BMPString ::= {0, 0, 16, 195}

-- georgianCapitalLetterHar BMPString ::= {0, 0, 16, 196}

-- georgianCapitalLetterHoe BMPString ::= {0, 0, 16, 197}

-- georgianLetterAn BMPString ::= {0, 0, 16, 208}

-- georgianLetterBan BMPString ::= {0, 0, 16, 209}

-- georgianLetterGan BMPString ::= {0, 0, 16, 210}

-- georgianLetterDon BMPString ::= {0, 0, 16, 211}

-- georgianLetterEn BMPString ::= {0, 0, 16, 212}

-- georgianLetterVin BMPString ::= {0, 0, 16, 213}

-- georgianLetterZen BMPString ::= {0, 0, 16, 214}

-- georgianLetterTan BMPString ::= {0, 0, 16, 215}

-- georgianLetterIn BMPString ::= {0, 0, 16, 216}

-- georgianLetterKan BMPString ::= {0, 0, 16, 217}

-- georgianLetterLas BMPString ::= {0, 0, 16, 218}

-- georgianLetterMan BMPString ::= {0, 0, 16, 219}

-- georgianLetterNar BMPString ::= {0, 0, 16, 220}

-- georgianLetterOn BMPString ::= {0, 0, 16, 221}

-- georgianLetterPar BMPString ::= {0, 0, 16, 222}

-- georgianLetterZhar BMPString ::= {0, 0, 16, 223}

-- georgianLetterRae BMPString ::= {0, 0, 16, 224}

-- georgianLetterSan BMPString ::= {0, 0, 16, 225}

-- georgianLetterTar BMPString ::= {0, 0, 16, 226}

-- georgianLetterUn BMPString ::= {0, 0, 16, 227}

-- georgianLetterPhar BMPString ::= {0, 0, 16, 228}

-- georgianLetterKhar BMPString ::= {0, 0, 16, 229}

-- georgianLetterGhan BMPString ::= {0, 0, 16, 230}

-- georgianLetterQar BMPString ::= {0, 0, 16, 231}

-- georgianLetterShin BMPString ::= {0, 0, 16, 232}

-- georgianLetterChin BMPString ::= {0, 0, 16, 233}

-- georgianLetterCan BMPString ::= {0, 0, 16, 234}

-- georgianLetterJil BMPString ::= {0, 0, 16, 235}

-- georgianLetterCil BMPString ::= {0, 0, 16, 236}

-- georgianLetterChar BMPString ::= {0, 0, 16, 237}

-- georgianLetterXan BMPString ::= {0, 0, 16, 238}

-- georgianLetterJhan BMPString ::= {0, 0, 16, 239}

-- georgianLetterHae BMPString ::= {0, 0, 16, 240}

-- georgianLetterHe BMPString ::= {0, 0, 16, 241}

-- georgianLetterHie BMPString ::= {0, 0, 16, 242}

-- georgianLetterWe BMPString ::= {0, 0, 16, 243}

-- georgianLetterHar BMPString ::= {0, 0, 16, 244}

-- georgianLetterHoe BMPString ::= {0, 0, 16, 245}

-- georgianLetterFi BMPString ::= {0, 0, 16, 246}

-- georgianLetterYn BMPString ::= {0, 0, 16, 247}

-- georgianLetterElifi BMPString ::= {0, 0, 16, 248}

-- georgianParagraphSeparator BMPString ::= {0, 0, 16, 251}

-- hangulChoseongKiyeok BMPString ::= {0, 0, 17, 0}

-- hangulChoseongSsangkiyeok BMPString ::= {0, 0, 17, 1}

-- hangulChoseongNieun BMPString ::= {0, 0, 17, 2}

-- hangulChoseongTikeut BMPString ::= {0, 0, 17, 3}

-- hangulChoseongSsangtikeut BMPString ::= {0, 0, 17, 4}

-- hangulChoseongRieul BMPString ::= {0, 0, 17, 5}

-- hangulChoseongMieum BMPString ::= {0, 0, 17, 6}

-- hangulChoseongPieup BMPString ::= {0, 0, 17, 7}

-- hangulChoseongSsangpieup BMPString ::= {0, 0, 17, 8}

-- hangulChoseongSios BMPString ::= {0, 0, 17, 9}

-- hangulChoseongSsangsios BMPString ::= {0, 0, 17, 10}

-- hangulChoseongIeung BMPString ::= {0, 0, 17, 11}

-- hangulChoseongCieuc BMPString ::= {0, 0, 17, 12}

-- hangulChoseongSsangcieuc BMPString ::= {0, 0, 17, 13}

-- hangulChoseongChieuch BMPString ::= {0, 0, 17, 14}

-- hangulChoseongKhieukh BMPString ::= {0, 0, 17, 15}

-- hangulChoseongThieuth BMPString ::= {0, 0, 17, 16}

-- hangulChoseongPhieuph BMPString ::= {0, 0, 17, 17}

-- hangulChoseongHieuh BMPString ::= {0, 0, 17, 18}

-- hangulChoseongNieun-kiyeok BMPString ::= {0, 0, 17, 19}

-- hangulChoseongSsangnieun BMPString ::= {0, 0, 17, 20}

-- hangulChoseongNieun-tikeut BMPString ::= {0, 0, 17, 21}

-- hangulChoseongNieun-pieup BMPString ::= {0, 0, 17, 22}

-- hangulChoseongTikeut-kiyeok BMPString ::= {0, 0, 17, 23}

-- hangulChoseongRieul-nieun BMPString ::= {0, 0, 17, 24}

-- hangulChoseongSsangrieul BMPString ::= {0, 0, 17, 25}

-- hangulChoseongRieul-hieuh BMPString ::= {0, 0, 17, 26}

-- hangulChoseongKapyeounrieul BMPString ::= {0, 0, 17, 27}

-- hangulChoseongMieum-pieup BMPString ::= {0, 0, 17, 28}

-- hangulChoseongKapyeounmieum BMPString ::= {0, 0, 17, 29}

-- hangulChoseongPieup-kiyeok BMPString ::= {0, 0, 17, 30}

-- hangulChoseongPieup-nieun BMPString ::= {0, 0, 17, 31}

-- hangulChoseongPieup-tikeut BMPString ::= {0, 0, 17, 32}

-- hangulChoseongPieup-sios BMPString ::= {0, 0, 17, 33}

-- hangulChoseongPieup-sios-kiyeok BMPString ::= {0, 0, 17, 34}

-- hangulChoseongPieup-sios-tikeut BMPString ::= {0, 0, 17, 35}

-- hangulChoseongPieup-sios-pieup BMPString ::= {0, 0, 17, 36}

-- hangulChoseongPieup-ssangsios BMPString ::= {0, 0, 17, 37}

-- hangulChoseongPieup-sios-cieuc BMPString ::= {0, 0, 17, 38}

-- hangulChoseongPieup-cieuc BMPString ::= {0, 0, 17, 39}

-- hangulChoseongPieup-chieuch BMPString ::= {0, 0, 17, 40}

-- hangulChoseongPieup-thieuth BMPString ::= {0, 0, 17, 41}

-- hangulChoseongPieup-phieuph BMPString ::= {0, 0, 17, 42}

-- hangulChoseongKapyeounpieup BMPString ::= {0, 0, 17, 43}

-- hangulChoseongKapyeounssangpieup BMPString ::= {0, 0, 17, 44}

-- hangulChoseongSios-kiyeok BMPString ::= {0, 0, 17, 45}

-- hangulChoseongSios-nieun BMPString ::= {0, 0, 17, 46}

-- hangulChoseongSios-tikeut BMPString ::= {0, 0, 17, 47}

-- hangulChoseongSios-rieul BMPString ::= {0, 0, 17, 48}

-- hangulChoseongSios-mieum BMPString ::= {0, 0, 17, 49}

-- hangulChoseongSios-pieup BMPString ::= {0, 0, 17, 50}

-- hangulChoseongSios-pieup-kiyeok BMPString ::= {0, 0, 17, 51}

-- hangulChoseongSios-ssangsios BMPString ::= {0, 0, 17, 52}

-- hangulChoseongSios-ieung BMPString ::= {0, 0, 17, 53}

-- hangulChoseongSios-cieuc BMPString ::= {0, 0, 17, 54}

-- hangulChoseongSios-chieuch BMPString ::= {0, 0, 17, 55}

-- hangulChoseongSios-khieukh BMPString ::= {0, 0, 17, 56}

-- hangulChoseongSios-thieuth BMPString ::= {0, 0, 17, 57}

-- hangulChoseongSios-phieuph BMPString ::= {0, 0, 17, 58}

-- hangulChoseongSios-hieuh BMPString ::= {0, 0, 17, 59}

-- hangulChoseongChitueumsios BMPString ::= {0, 0, 17, 60}

-- hangulChoseongChitueumssangsios BMPString ::= {0, 0, 17, 61}

-- hangulChoseongCeongchieumsios BMPString ::= {0, 0, 17, 62}

-- hangulChoseongCeongchieumssangsios BMPString ::= {0, 0, 17, 63}

-- hangulChoseongPansios BMPString ::= {0, 0, 17, 64}

-- hangulChoseongIeung-kiyeok BMPString ::= {0, 0, 17, 65}

-- hangulChoseongIeung-tikeut BMPString ::= {0, 0, 17, 66}

-- hangulChoseongIeung-mieum BMPString ::= {0, 0, 17, 67}

-- hangulChoseongIeung-pieup BMPString ::= {0, 0, 17, 68}

-- hangulChoseongIeung-sios BMPString ::= {0, 0, 17, 69}

-- hangulChoseongIeung-pansios BMPString ::= {0, 0, 17, 70}

-- hangulChoseongSsangieung BMPString ::= {0, 0, 17, 71}

-- hangulChoseongIeung-cieuc BMPString ::= {0, 0, 17, 72}

-- hangulChoseongIeung-chieuch BMPString ::= {0, 0, 17, 73}

-- hangulChoseongIeung-thieuth BMPString ::= {0, 0, 17, 74}

-- hangulChoseongIeung-phieuph BMPString ::= {0, 0, 17, 75}

-- hangulChoseongYesieung BMPString ::= {0, 0, 17, 76}

-- hangulChoseongCieuc-ieung BMPString ::= {0, 0, 17, 77}

-- hangulChoseongChitueumcieuc BMPString ::= {0, 0, 17, 78}

-- hangulChoseongChitueumssangcieuc BMPString ::= {0, 0, 17, 79}

-- hangulChoseongCeongchieumcieuc BMPString ::= {0, 0, 17, 80}

-- hangulChoseongCeongchieumssangcieuc BMPString ::= {0, 0, 17, 81}

-- hangulChoseongChieuch-khieukh BMPString ::= {0, 0, 17, 82}

-- hangulChoseongChieuch-hieuh BMPString ::= {0, 0, 17, 83}

-- hangulChoseongChitueumchieuch BMPString ::= {0, 0, 17, 84}

-- hangulChoseongCeongchieumchieuch BMPString ::= {0, 0, 17, 85}

-- hangulChoseongPhieuph-pieup BMPString ::= {0, 0, 17, 86}

-- hangulChoseongKapyeounphieuph BMPString ::= {0, 0, 17, 87}

-- hangulChoseongSsanghieuh BMPString ::= {0, 0, 17, 88}

-- hangulChoseongYeorinhieuh BMPString ::= {0, 0, 17, 89}

-- hangulChoseongFiller BMPString ::= {0, 0, 17, 95}

-- hangulJungseongFiller BMPString ::= {0, 0, 17, 96}

-- hangulJungseongA BMPString ::= {0, 0, 17, 97}

-- hangulJungseongAe BMPString ::= {0, 0, 17, 98}

-- hangulJungseongYa BMPString ::= {0, 0, 17, 99}

-- hangulJungseongYae BMPString ::= {0, 0, 17, 100}

-- hangulJungseongEo BMPString ::= {0, 0, 17, 101}

-- hangulJungseongE BMPString ::= {0, 0, 17, 102}

-- hangulJungseongYeo BMPString ::= {0, 0, 17, 103}

-- hangulJungseongYe BMPString ::= {0, 0, 17, 104}

-- hangulJungseongO BMPString ::= {0, 0, 17, 105}

-- hangulJungseongWa BMPString ::= {0, 0, 17, 106}

-- hangulJungseongWae BMPString ::= {0, 0, 17, 107}

-- hangulJungseongOe BMPString ::= {0, 0, 17, 108}

-- hangulJungseongYo BMPString ::= {0, 0, 17, 109}

-- hangulJungseongU BMPString ::= {0, 0, 17, 110}

-- hangulJungseongWeo BMPString ::= {0, 0, 17, 111}

-- hangulJungseongWe BMPString ::= {0, 0, 17, 112}

-- hangulJungseongWi BMPString ::= {0, 0, 17, 113}

-- hangulJungseongYu BMPString ::= {0, 0, 17, 114}

-- hangulJungseongEu BMPString ::= {0, 0, 17, 115}

-- hangulJungseongYi BMPString ::= {0, 0, 17, 116}

-- hangulJungseongI BMPString ::= {0, 0, 17, 117}

-- hangulJungseongA-o BMPString ::= {0, 0, 17, 118}

-- hangulJungseongA-u BMPString ::= {0, 0, 17, 119}

-- hangulJungseongYa-o BMPString ::= {0, 0, 17, 120}

-- hangulJungseongYa-yo BMPString ::= {0, 0, 17, 121}

-- hangulJungseongEo-o BMPString ::= {0, 0, 17, 122}

-- hangulJungseongEo-u BMPString ::= {0, 0, 17, 123}

-- hangulJungseongEo-eu BMPString ::= {0, 0, 17, 124}

-- hangulJungseongYeo-o BMPString ::= {0, 0, 17, 125}

-- hangulJungseongYeo-u BMPString ::= {0, 0, 17, 126}

-- hangulJungseongO-eo BMPString ::= {0, 0, 17, 127}

-- hangulJungseongO-e BMPString ::= {0, 0, 17, 128}

-- hangulJungseongO-ye BMPString ::= {0, 0, 17, 129}

-- hangulJungseongO-o BMPString ::= {0, 0, 17, 130}

-- hangulJungseongO-u BMPString ::= {0, 0, 17, 131}

-- hangulJungseongYo-ya BMPString ::= {0, 0, 17, 132}

-- hangulJungseongYo-yae BMPString ::= {0, 0, 17, 133}

-- hangulJungseongYo-yeo BMPString ::= {0, 0, 17, 134}

-- hangulJungseongYo-o BMPString ::= {0, 0, 17, 135}

-- hangulJungseongYo-i BMPString ::= {0, 0, 17, 136}

-- hangulJungseongU-a BMPString ::= {0, 0, 17, 137}

-- hangulJungseongU-ae BMPString ::= {0, 0, 17, 138}

-- hangulJungseongU-eo-eu BMPString ::= {0, 0, 17, 139}

-- hangulJungseongU-ye BMPString ::= {0, 0, 17, 140}

-- hangulJungseongU-u BMPString ::= {0, 0, 17, 141}

-- hangulJungseongYu-a BMPString ::= {0, 0, 17, 142}

-- hangulJungseongYu-eo BMPString ::= {0, 0, 17, 143}

-- hangulJungseongYu-e BMPString ::= {0, 0, 17, 144}

-- hangulJungseongYu-yeo BMPString ::= {0, 0, 17, 145}

-- hangulJungseongYu-ye BMPString ::= {0, 0, 17, 146}

-- hangulJungseongYu-u BMPString ::= {0, 0, 17, 147}

-- hangulJungseongYu-i BMPString ::= {0, 0, 17, 148}

-- hangulJungseongEu-u BMPString ::= {0, 0, 17, 149}

-- hangulJungseongEu-eu BMPString ::= {0, 0, 17, 150}

-- hangulJungseongYi-u BMPString ::= {0, 0, 17, 151}

-- hangulJungseongI-a BMPString ::= {0, 0, 17, 152}

-- hangulJungseongI-ya BMPString ::= {0, 0, 17, 153}

-- hangulJungseongI-o BMPString ::= {0, 0, 17, 154}

-- hangulJungseongI-u BMPString ::= {0, 0, 17, 155}

-- hangulJungseongI-eu BMPString ::= {0, 0, 17, 156}

-- hangulJungseongI-araea BMPString ::= {0, 0, 17, 157}

-- hangulJungseongAraea BMPString ::= {0, 0, 17, 158}

-- hangulJungseongAraea-eo BMPString ::= {0, 0, 17, 159}

-- hangulJungseongAraea-u BMPString ::= {0, 0, 17, 160}

-- hangulJungseongAraea-i BMPString ::= {0, 0, 17, 161}

-- hangulJungseongSsangaraea BMPString ::= {0, 0, 17, 162}

-- hangulJongseongKiyeok BMPString ::= {0, 0, 17, 168}

-- hangulJongseongSsangkiyeok BMPString ::= {0, 0, 17, 169}

-- hangulJongseongKiyeok-sios BMPString ::= {0, 0, 17, 170}

-- hangulJongseongNieun BMPString ::= {0, 0, 17, 171}

-- hangulJongseongNieun-cieuc BMPString ::= {0, 0, 17, 172}

-- hangulJongseongNieun-hieuh BMPString ::= {0, 0, 17, 173}

-- hangulJongseongTikeut BMPString ::= {0, 0, 17, 174}

-- hangulJongseongRieul BMPString ::= {0, 0, 17, 175}

-- hangulJongseongRieul-kiyeok BMPString ::= {0, 0, 17, 176}

-- hangulJongseongRieul-mieum BMPString ::= {0, 0, 17, 177}

-- hangulJongseongRieul-pieup BMPString ::= {0, 0, 17, 178}

-- hangulJongseongRieul-sios BMPString ::= {0, 0, 17, 179}

-- hangulJongseongRieul-thieuth BMPString ::= {0, 0, 17, 180}

-- hangulJongseongRieul-phieuph BMPString ::= {0, 0, 17, 181}

-- hangulJongseongRieul-hieuh BMPString ::= {0, 0, 17, 182}

-- hangulJongseongMieum BMPString ::= {0, 0, 17, 183}

-- hangulJongseongPieup BMPString ::= {0, 0, 17, 184}

-- hangulJongseongPieup-sios BMPString ::= {0, 0, 17, 185}

-- hangulJongseongSios BMPString ::= {0, 0, 17, 186}

-- hangulJongseongSsangsios BMPString ::= {0, 0, 17, 187}

-- hangulJongseongIeung BMPString ::= {0, 0, 17, 188}

-- hangulJongseongCieuc BMPString ::= {0, 0, 17, 189}

-- hangulJongseongChieuch BMPString ::= {0, 0, 17, 190}

-- hangulJongseongKhieukh BMPString ::= {0, 0, 17, 191}

-- hangulJongseongThieuth BMPString ::= {0, 0, 17, 192}

-- hangulJongseongPhieuph BMPString ::= {0, 0, 17, 193}

-- hangulJongseongHieuh BMPString ::= {0, 0, 17, 194}

-- hangulJongseongKiyeok-rieul BMPString ::= {0, 0, 17, 195}

-- hangulJongseongKiyeok-sios-kiyeok BMPString ::= {0, 0, 17, 196}

-- hangulJongseongNieun-kiyeok BMPString ::= {0, 0, 17, 197}

-- hangulJongseongNieun-tikeut BMPString ::= {0, 0, 17, 198}

-- hangulJongseongNieun-sios BMPString ::= {0, 0, 17, 199}

-- hangulJongseongNieun-pansios BMPString ::= {0, 0, 17, 200}

-- hangulJongseongNieun-thieuth BMPString ::= {0, 0, 17, 201}

-- hangulJongseongTikeut-kiyeok BMPString ::= {0, 0, 17, 202}

-- hangulJongseongTikeut-rieul BMPString ::= {0, 0, 17, 203}

-- hangulJongseongRieul-kiyeok-sios BMPString ::= {0, 0, 17, 204}

-- hangulJongseongRieul-nieun BMPString ::= {0, 0, 17, 205}

-- hangulJongseongRieul-tikeut BMPString ::= {0, 0, 17, 206}

-- hangulJongseongRieul-tikeut-hieuh BMPString ::= {0, 0, 17, 207}

-- hangulJongseongSsangrieul BMPString ::= {0, 0, 17, 208}

-- hangulJongseongRieul-mieum-kiyeok BMPString ::= {0, 0, 17, 209}

-- hangulJongseongRieul-mieum-sios BMPString ::= {0, 0, 17, 210}

-- hangulJongseongRieul-pieup-sios BMPString ::= {0, 0, 17, 211}

-- hangulJongseongRieul-pieup-hieuh BMPString ::= {0, 0, 17, 212}

-- hangulJongseongRieul-kapyeounpieup BMPString ::= {0, 0, 17, 213}

-- hangulJongseongRieul-ssangsios BMPString ::= {0, 0, 17, 214}

-- hangulJongseongRieul-pansios BMPString ::= {0, 0, 17, 215}

-- hangulJongseongRieul-khieukh BMPString ::= {0, 0, 17, 216}

-- hangulJongseongRieul-yeorinhieuh BMPString ::= {0, 0, 17, 217}

-- hangulJongseongMieum-kiyeok BMPString ::= {0, 0, 17, 218}

-- hangulJongseongMieum-rieul BMPString ::= {0, 0, 17, 219}

-- hangulJongseongMieum-pieup BMPString ::= {0, 0, 17, 220}

-- hangulJongseongMieum-sios BMPString ::= {0, 0, 17, 221}

-- hangulJongseongMieum-ssangsios BMPString ::= {0, 0, 17, 222}

-- hangulJongseongMieum-pansios BMPString ::= {0, 0, 17, 223}

-- hangulJongseongMieum-chieuch BMPString ::= {0, 0, 17, 224}

-- hangulJongseongMieum-hieuh BMPString ::= {0, 0, 17, 225}

-- hangulJongseongKapyeounmieum BMPString ::= {0, 0, 17, 226}

-- hangulJongseongPieup-rieul BMPString ::= {0, 0, 17, 227}

-- hangulJongseongPieup-phieuph BMPString ::= {0, 0, 17, 228}

-- hangulJongseongPieup-hieuh BMPString ::= {0, 0, 17, 229}

-- hangulJongseongKapyeounpieup BMPString ::= {0, 0, 17, 230}

-- hangulJongseongSios-kiyeok BMPString ::= {0, 0, 17, 231}

-- hangulJongseongSios-tikeut BMPString ::= {0, 0, 17, 232}

-- hangulJongseongSios-rieul BMPString ::= {0, 0, 17, 233}

-- hangulJongseongSios-pieup BMPString ::= {0, 0, 17, 234}

-- hangulJongseongPansios BMPString ::= {0, 0, 17, 235}

-- hangulJongseongIeung-kiyeok BMPString ::= {0, 0, 17, 236}

-- hangulJongseongIeung-ssangkiyeok BMPString ::= {0, 0, 17, 237}

-- hangulJongseongSsangieung BMPString ::= {0, 0, 17, 238}

-- hangulJongseongIeung-khieukh BMPString ::= {0, 0, 17, 239}

-- hangulJongseongYesieung BMPString ::= {0, 0, 17, 240}

-- hangulJongseongYesieung-sios BMPString ::= {0, 0, 17, 241}

-- hangulJongseongYesieung-pansios BMPString ::= {0, 0, 17, 242}

-- hangulJongseongPhieuph-pieup BMPString ::= {0, 0, 17, 243}

-- hangulJongseongKapyeounphieuph BMPString ::= {0, 0, 17, 244}

-- hangulJongseongHieuh-nieun BMPString ::= {0, 0, 17, 245}

-- hangulJongseongHieuh-rieul BMPString ::= {0, 0, 17, 246}

-- hangulJongseongHieuh-mieum BMPString ::= {0, 0, 17, 247}

-- hangulJongseongHieuh-pieup BMPString ::= {0, 0, 17, 248}

-- hangulJongseongYeorinhieuh BMPString ::= {0, 0, 17, 249}

-- ethiopicSyllableHa BMPString ::= {0, 0, 18, 0}

-- ethiopicSyllableHu BMPString ::= {0, 0, 18, 1}

-- ethiopicSyllableHi BMPString ::= {0, 0, 18, 2}

-- ethiopicSyllableHaa BMPString ::= {0, 0, 18, 3}

-- ethiopicSyllableHee BMPString ::= {0, 0, 18, 4}

-- ethiopicSyllableHe BMPString ::= {0, 0, 18, 5}

-- ethiopicSyllableHo BMPString ::= {0, 0, 18, 6}

-- ethiopicSyllableLa BMPString ::= {0, 0, 18, 8}

-- ethiopicSyllableLu BMPString ::= {0, 0, 18, 9}

-- ethiopicSyllableLi BMPString ::= {0, 0, 18, 10}

-- ethiopicSyllableLaa BMPString ::= {0, 0, 18, 11}

-- ethiopicSyllableLee BMPString ::= {0, 0, 18, 12}

-- ethiopicSyllableLe BMPString ::= {0, 0, 18, 13}

-- ethiopicSyllableLo BMPString ::= {0, 0, 18, 14}

-- ethiopicSyllableLwa BMPString ::= {0, 0, 18, 15}

-- ethiopicSyllableHha BMPString ::= {0, 0, 18, 16}

-- ethiopicSyllableHhu BMPString ::= {0, 0, 18, 17}

-- ethiopicSyllableHhi BMPString ::= {0, 0, 18, 18}

-- ethiopicSyllableHhaa BMPString ::= {0, 0, 18, 19}

-- ethiopicSyllableHhee BMPString ::= {0, 0, 18, 20}

-- ethiopicSyllableHhe BMPString ::= {0, 0, 18, 21}

-- ethiopicSyllableHho BMPString ::= {0, 0, 18, 22}

-- ethiopicSyllableHhwa BMPString ::= {0, 0, 18, 23}

-- ethiopicSyllableMa BMPString ::= {0, 0, 18, 24}

-- ethiopicSyllableMu BMPString ::= {0, 0, 18, 25}

-- ethiopicSyllableMi BMPString ::= {0, 0, 18, 26}

-- ethiopicSyllableMaa BMPString ::= {0, 0, 18, 27}

-- ethiopicSyllableMee BMPString ::= {0, 0, 18, 28}

-- ethiopicSyllableMe BMPString ::= {0, 0, 18, 29}

-- ethiopicSyllableMo BMPString ::= {0, 0, 18, 30}

-- ethiopicSyllableMwa BMPString ::= {0, 0, 18, 31}

-- ethiopicSyllableSza BMPString ::= {0, 0, 18, 32}

-- ethiopicSyllableSzu BMPString ::= {0, 0, 18, 33}

-- ethiopicSyllableSzi BMPString ::= {0, 0, 18, 34}

-- ethiopicSyllableSzaa BMPString ::= {0, 0, 18, 35}

-- ethiopicSyllableSzee BMPString ::= {0, 0, 18, 36}

-- ethiopicSyllableSze BMPString ::= {0, 0, 18, 37}

-- ethiopicSyllableSzo BMPString ::= {0, 0, 18, 38}

-- ethiopicSyllableSzwa BMPString ::= {0, 0, 18, 39}

-- ethiopicSyllableRa BMPString ::= {0, 0, 18, 40}

-- ethiopicSyllableRu BMPString ::= {0, 0, 18, 41}

-- ethiopicSyllableRi BMPString ::= {0, 0, 18, 42}

-- ethiopicSyllableRaa BMPString ::= {0, 0, 18, 43}

-- ethiopicSyllableRee BMPString ::= {0, 0, 18, 44}

-- ethiopicSyllableRe BMPString ::= {0, 0, 18, 45}

-- ethiopicSyllableRo BMPString ::= {0, 0, 18, 46}

-- ethiopicSyllableRwa BMPString ::= {0, 0, 18, 47}

-- ethiopicSyllableSa BMPString ::= {0, 0, 18, 48}

-- ethiopicSyllableSu BMPString ::= {0, 0, 18, 49}

-- ethiopicSyllableSi BMPString ::= {0, 0, 18, 50}

-- ethiopicSyllableSaa BMPString ::= {0, 0, 18, 51}

-- ethiopicSyllableSee BMPString ::= {0, 0, 18, 52}

-- ethiopicSyllableSe BMPString ::= {0, 0, 18, 53}

-- ethiopicSyllableSo BMPString ::= {0, 0, 18, 54}

-- ethiopicSyllableSwa BMPString ::= {0, 0, 18, 55}

-- ethiopicSyllableSha BMPString ::= {0, 0, 18, 56}

-- ethiopicSyllableShu BMPString ::= {0, 0, 18, 57}

-- ethiopicSyllableShi BMPString ::= {0, 0, 18, 58}

-- ethiopicSyllableShaa BMPString ::= {0, 0, 18, 59}

-- ethiopicSyllableShee BMPString ::= {0, 0, 18, 60}

-- ethiopicSyllableShe BMPString ::= {0, 0, 18, 61}

-- ethiopicSyllableSho BMPString ::= {0, 0, 18, 62}

-- ethiopicSyllableShwa BMPString ::= {0, 0, 18, 63}

-- ethiopicSyllableQa BMPString ::= {0, 0, 18, 64}

-- ethiopicSyllableQu BMPString ::= {0, 0, 18, 65}

-- ethiopicSyllableQi BMPString ::= {0, 0, 18, 66}

-- ethiopicSyllableQaa BMPString ::= {0, 0, 18, 67}

-- ethiopicSyllableQee BMPString ::= {0, 0, 18, 68}

-- ethiopicSyllableQe BMPString ::= {0, 0, 18, 69}

-- ethiopicSyllableQo BMPString ::= {0, 0, 18, 70}

-- ethiopicSyllableQwa BMPString ::= {0, 0, 18, 72}

-- ethiopicSyllableQwi BMPString ::= {0, 0, 18, 74}

-- ethiopicSyllableQwaa BMPString ::= {0, 0, 18, 75}

-- ethiopicSyllableQwee BMPString ::= {0, 0, 18, 76}

-- ethiopicSyllableQwe BMPString ::= {0, 0, 18, 77}

-- ethiopicSyllableQha BMPString ::= {0, 0, 18, 80}

-- ethiopicSyllableQhu BMPString ::= {0, 0, 18, 81}

-- ethiopicSyllableQhi BMPString ::= {0, 0, 18, 82}

-- ethiopicSyllableQhaa BMPString ::= {0, 0, 18, 83}

-- ethiopicSyllableQhee BMPString ::= {0, 0, 18, 84}

-- ethiopicSyllableQhe BMPString ::= {0, 0, 18, 85}

-- ethiopicSyllableQho BMPString ::= {0, 0, 18, 86}

-- ethiopicSyllableQhwa BMPString ::= {0, 0, 18, 88}

-- ethiopicSyllableQhwi BMPString ::= {0, 0, 18, 90}

-- ethiopicSyllableQhwaa BMPString ::= {0, 0, 18, 91}

-- ethiopicSyllableQhwee BMPString ::= {0, 0, 18, 92}

-- ethiopicSyllableQhwe BMPString ::= {0, 0, 18, 93}

-- ethiopicSyllableBa BMPString ::= {0, 0, 18, 96}

-- ethiopicSyllableBu BMPString ::= {0, 0, 18, 97}

-- ethiopicSyllableBi BMPString ::= {0, 0, 18, 98}

-- ethiopicSyllableBaa BMPString ::= {0, 0, 18, 99}

-- ethiopicSyllableBee BMPString ::= {0, 0, 18, 100}

-- ethiopicSyllableBe BMPString ::= {0, 0, 18, 101}

-- ethiopicSyllableBo BMPString ::= {0, 0, 18, 102}

-- ethiopicSyllableBwa BMPString ::= {0, 0, 18, 103}

-- ethiopicSyllableVa BMPString ::= {0, 0, 18, 104}

-- ethiopicSyllableVu BMPString ::= {0, 0, 18, 105}

-- ethiopicSyllableVi BMPString ::= {0, 0, 18, 106}

-- ethiopicSyllableVaa BMPString ::= {0, 0, 18, 107}

-- ethiopicSyllableVee BMPString ::= {0, 0, 18, 108}

-- ethiopicSyllableVe BMPString ::= {0, 0, 18, 109}

-- ethiopicSyllableVo BMPString ::= {0, 0, 18, 110}

-- ethiopicSyllableVwa BMPString ::= {0, 0, 18, 111}

-- ethiopicSyllableTa BMPString ::= {0, 0, 18, 112}

-- ethiopicSyllableTu BMPString ::= {0, 0, 18, 113}

-- ethiopicSyllableTi BMPString ::= {0, 0, 18, 114}

-- ethiopicSyllableTaa BMPString ::= {0, 0, 18, 115}

-- ethiopicSyllableTee BMPString ::= {0, 0, 18, 116}

-- ethiopicSyllableTe BMPString ::= {0, 0, 18, 117}

-- ethiopicSyllableTo BMPString ::= {0, 0, 18, 118}

-- ethiopicSyllableTwa BMPString ::= {0, 0, 18, 119}

-- ethiopicSyllableCa BMPString ::= {0, 0, 18, 120}

-- ethiopicSyllableCu BMPString ::= {0, 0, 18, 121}

-- ethiopicSyllableCi BMPString ::= {0, 0, 18, 122}

-- ethiopicSyllableCaa BMPString ::= {0, 0, 18, 123}

-- ethiopicSyllableCee BMPString ::= {0, 0, 18, 124}

-- ethiopicSyllableCe BMPString ::= {0, 0, 18, 125}

-- ethiopicSyllableCo BMPString ::= {0, 0, 18, 126}

-- ethiopicSyllableCwa BMPString ::= {0, 0, 18, 127}

-- ethiopicSyllableXa BMPString ::= {0, 0, 18, 128}

-- ethiopicSyllableXu BMPString ::= {0, 0, 18, 129}

-- ethiopicSyllableXi BMPString ::= {0, 0, 18, 130}

-- ethiopicSyllableXaa BMPString ::= {0, 0, 18, 131}

-- ethiopicSyllableXee BMPString ::= {0, 0, 18, 132}

-- ethiopicSyllableXe BMPString ::= {0, 0, 18, 133}

-- ethiopicSyllableXo BMPString ::= {0, 0, 18, 134}

-- ethiopicSyllableXwa BMPString ::= {0, 0, 18, 136}

-- ethiopicSyllableXwi BMPString ::= {0, 0, 18, 138}

-- ethiopicSyllableXwaa BMPString ::= {0, 0, 18, 139}

-- ethiopicSyllableXwee BMPString ::= {0, 0, 18, 140}

-- ethiopicSyllableXwe BMPString ::= {0, 0, 18, 141}

-- ethiopicSyllableNa BMPString ::= {0, 0, 18, 144}

-- ethiopicSyllableNu BMPString ::= {0, 0, 18, 145}

-- ethiopicSyllableNi BMPString ::= {0, 0, 18, 146}

-- ethiopicSyllableNaa BMPString ::= {0, 0, 18, 147}

-- ethiopicSyllableNee BMPString ::= {0, 0, 18, 148}

-- ethiopicSyllableNe BMPString ::= {0, 0, 18, 149}

-- ethiopicSyllableNo BMPString ::= {0, 0, 18, 150}

-- ethiopicSyllableNwa BMPString ::= {0, 0, 18, 151}

-- ethiopicSyllableNya BMPString ::= {0, 0, 18, 152}

-- ethiopicSyllableNyu BMPString ::= {0, 0, 18, 153}

-- ethiopicSyllableNyi BMPString ::= {0, 0, 18, 154}

-- ethiopicSyllableNyaa BMPString ::= {0, 0, 18, 155}

-- ethiopicSyllableNyee BMPString ::= {0, 0, 18, 156}

-- ethiopicSyllableNye BMPString ::= {0, 0, 18, 157}

-- ethiopicSyllableNyo BMPString ::= {0, 0, 18, 158}

-- ethiopicSyllableNywa BMPString ::= {0, 0, 18, 159}

-- ethiopicSyllableGlottalA BMPString ::= {0, 0, 18, 160}

-- ethiopicSyllableGlottalU BMPString ::= {0, 0, 18, 161}

-- ethiopicSyllableGlottalI BMPString ::= {0, 0, 18, 162}

-- ethiopicSyllableGlottalAa BMPString ::= {0, 0, 18, 163}

-- ethiopicSyllableGlottalEe BMPString ::= {0, 0, 18, 164}

-- ethiopicSyllableGlottalE BMPString ::= {0, 0, 18, 165}

-- ethiopicSyllableGlottalO BMPString ::= {0, 0, 18, 166}

-- ethiopicSyllableGlottalWa BMPString ::= {0, 0, 18, 167}

-- ethiopicSyllableKa BMPString ::= {0, 0, 18, 168}

-- ethiopicSyllableKu BMPString ::= {0, 0, 18, 169}

-- ethiopicSyllableKi BMPString ::= {0, 0, 18, 170}

-- ethiopicSyllableKaa BMPString ::= {0, 0, 18, 171}

-- ethiopicSyllableKee BMPString ::= {0, 0, 18, 172}

-- ethiopicSyllableKe BMPString ::= {0, 0, 18, 173}

-- ethiopicSyllableKo BMPString ::= {0, 0, 18, 174}

-- ethiopicSyllableKwa BMPString ::= {0, 0, 18, 176}

-- ethiopicSyllableKwi BMPString ::= {0, 0, 18, 178}

-- ethiopicSyllableKwaa BMPString ::= {0, 0, 18, 179}

-- ethiopicSyllableKwee BMPString ::= {0, 0, 18, 180}

-- ethiopicSyllableKwe BMPString ::= {0, 0, 18, 181}

-- ethiopicSyllableKxa BMPString ::= {0, 0, 18, 184}

-- ethiopicSyllableKxu BMPString ::= {0, 0, 18, 185}

-- ethiopicSyllableKxi BMPString ::= {0, 0, 18, 186}

-- ethiopicSyllableKxaa BMPString ::= {0, 0, 18, 187}

-- ethiopicSyllableKxee BMPString ::= {0, 0, 18, 188}

-- ethiopicSyllableKxe BMPString ::= {0, 0, 18, 189}

-- ethiopicSyllableKxo BMPString ::= {0, 0, 18, 190}

-- ethiopicSyllableKxwa BMPString ::= {0, 0, 18, 192}

-- ethiopicSyllableKxwi BMPString ::= {0, 0, 18, 194}

-- ethiopicSyllableKxwaa BMPString ::= {0, 0, 18, 195}

-- ethiopicSyllableKxwee BMPString ::= {0, 0, 18, 196}

-- ethiopicSyllableKxwe BMPString ::= {0, 0, 18, 197}

-- ethiopicSyllableWa BMPString ::= {0, 0, 18, 200}

-- ethiopicSyllableWu BMPString ::= {0, 0, 18, 201}

-- ethiopicSyllableWi BMPString ::= {0, 0, 18, 202}

-- ethiopicSyllableWaa BMPString ::= {0, 0, 18, 203}

-- ethiopicSyllableWee BMPString ::= {0, 0, 18, 204}

-- ethiopicSyllableWe BMPString ::= {0, 0, 18, 205}

-- ethiopicSyllableWo BMPString ::= {0, 0, 18, 206}

-- ethiopicSyllablePharyngealA BMPString ::= {0, 0, 18, 208}

-- ethiopicSyllablePharyngealU BMPString ::= {0, 0, 18, 209}

-- ethiopicSyllablePharyngealI BMPString ::= {0, 0, 18, 210}

-- ethiopicSyllablePharyngealAa BMPString ::= {0, 0, 18, 211}

-- ethiopicSyllablePharyngealEe BMPString ::= {0, 0, 18, 212}

-- ethiopicSyllablePharyngealE BMPString ::= {0, 0, 18, 213}

-- ethiopicSyllablePharyngealO BMPString ::= {0, 0, 18, 214}

-- ethiopicSyllableZa BMPString ::= {0, 0, 18, 216}

-- ethiopicSyllableZu BMPString ::= {0, 0, 18, 217}

-- ethiopicSyllableZi BMPString ::= {0, 0, 18, 218}

-- ethiopicSyllableZaa BMPString ::= {0, 0, 18, 219}

-- ethiopicSyllableZee BMPString ::= {0, 0, 18, 220}

-- ethiopicSyllableZe BMPString ::= {0, 0, 18, 221}

-- ethiopicSyllableZo BMPString ::= {0, 0, 18, 222}

-- ethiopicSyllableZwa BMPString ::= {0, 0, 18, 223}

-- ethiopicSyllableZha BMPString ::= {0, 0, 18, 224}

-- ethiopicSyllableZhu BMPString ::= {0, 0, 18, 225}

-- ethiopicSyllableZhi BMPString ::= {0, 0, 18, 226}

-- ethiopicSyllableZhaa BMPString ::= {0, 0, 18, 227}

-- ethiopicSyllableZhee BMPString ::= {0, 0, 18, 228}

-- ethiopicSyllableZhe BMPString ::= {0, 0, 18, 229}

-- ethiopicSyllableZho BMPString ::= {0, 0, 18, 230}

-- ethiopicSyllableZhwa BMPString ::= {0, 0, 18, 231}

-- ethiopicSyllableYa BMPString ::= {0, 0, 18, 232}

-- ethiopicSyllableYu BMPString ::= {0, 0, 18, 233}

-- ethiopicSyllableYi BMPString ::= {0, 0, 18, 234}

-- ethiopicSyllableYaa BMPString ::= {0, 0, 18, 235}

-- ethiopicSyllableYee BMPString ::= {0, 0, 18, 236}

-- ethiopicSyllableYe BMPString ::= {0, 0, 18, 237}

-- ethiopicSyllableYo BMPString ::= {0, 0, 18, 238}

-- ethiopicSyllableDa BMPString ::= {0, 0, 18, 240}

-- ethiopicSyllableDu BMPString ::= {0, 0, 18, 241}

-- ethiopicSyllableDi BMPString ::= {0, 0, 18, 242}

-- ethiopicSyllableDaa BMPString ::= {0, 0, 18, 243}

-- ethiopicSyllableDee BMPString ::= {0, 0, 18, 244}

-- ethiopicSyllableDe BMPString ::= {0, 0, 18, 245}

-- ethiopicSyllableDo BMPString ::= {0, 0, 18, 246}

-- ethiopicSyllableDwa BMPString ::= {0, 0, 18, 247}

-- ethiopicSyllableDda BMPString ::= {0, 0, 18, 248}

-- ethiopicSyllableDdu BMPString ::= {0, 0, 18, 249}

-- ethiopicSyllableDdi BMPString ::= {0, 0, 18, 250}

-- ethiopicSyllableDdaa BMPString ::= {0, 0, 18, 251}

-- ethiopicSyllableDdee BMPString ::= {0, 0, 18, 252}

-- ethiopicSyllableDde BMPString ::= {0, 0, 18, 253}

-- ethiopicSyllableDdo BMPString ::= {0, 0, 18, 254}

-- ethiopicSyllableDdwa BMPString ::= {0, 0, 18, 255}

-- ethiopicSyllableJa BMPString ::= {0, 0, 19, 0}

-- ethiopicSyllableJu BMPString ::= {0, 0, 19, 1}

-- ethiopicSyllableJi BMPString ::= {0, 0, 19, 2}

-- ethiopicSyllableJaa BMPString ::= {0, 0, 19, 3}

-- ethiopicSyllableJee BMPString ::= {0, 0, 19, 4}

-- ethiopicSyllableJe BMPString ::= {0, 0, 19, 5}

-- ethiopicSyllableJo BMPString ::= {0, 0, 19, 6}

-- ethiopicSyllableJwa BMPString ::= {0, 0, 19, 7}

-- ethiopicSyllableGa BMPString ::= {0, 0, 19, 8}

-- ethiopicSyllableGu BMPString ::= {0, 0, 19, 9}

-- ethiopicSyllableGi BMPString ::= {0, 0, 19, 10}

-- ethiopicSyllableGaa BMPString ::= {0, 0, 19, 11}

-- ethiopicSyllableGee BMPString ::= {0, 0, 19, 12}

-- ethiopicSyllableGe BMPString ::= {0, 0, 19, 13}

-- ethiopicSyllableGo BMPString ::= {0, 0, 19, 14}

-- ethiopicSyllableGwa BMPString ::= {0, 0, 19, 16}

-- ethiopicSyllableGwi BMPString ::= {0, 0, 19, 18}

-- ethiopicSyllableGwaa BMPString ::= {0, 0, 19, 19}

-- ethiopicSyllableGwee BMPString ::= {0, 0, 19, 20}

-- ethiopicSyllableGwe BMPString ::= {0, 0, 19, 21}

-- ethiopicSyllableGga BMPString ::= {0, 0, 19, 24}

-- ethiopicSyllableGgu BMPString ::= {0, 0, 19, 25}

-- ethiopicSyllableGgi BMPString ::= {0, 0, 19, 26}

-- ethiopicSyllableGgaa BMPString ::= {0, 0, 19, 27}

-- ethiopicSyllableGgee BMPString ::= {0, 0, 19, 28}

-- ethiopicSyllableGge BMPString ::= {0, 0, 19, 29}

-- ethiopicSyllableGgo BMPString ::= {0, 0, 19, 30}

-- ethiopicSyllableTha BMPString ::= {0, 0, 19, 32}

-- ethiopicSyllableThu BMPString ::= {0, 0, 19, 33}

-- ethiopicSyllableThi BMPString ::= {0, 0, 19, 34}

-- ethiopicSyllableThaa BMPString ::= {0, 0, 19, 35}

-- ethiopicSyllableThee BMPString ::= {0, 0, 19, 36}

-- ethiopicSyllableThe BMPString ::= {0, 0, 19, 37}

-- ethiopicSyllableTho BMPString ::= {0, 0, 19, 38}

-- ethiopicSyllableThwa BMPString ::= {0, 0, 19, 39}

-- ethiopicSyllableCha BMPString ::= {0, 0, 19, 40}

-- ethiopicSyllableChu BMPString ::= {0, 0, 19, 41}

-- ethiopicSyllableChi BMPString ::= {0, 0, 19, 42}

-- ethiopicSyllableChaa BMPString ::= {0, 0, 19, 43}

-- ethiopicSyllableChee BMPString ::= {0, 0, 19, 44}

-- ethiopicSyllableChe BMPString ::= {0, 0, 19, 45}

-- ethiopicSyllableCho BMPString ::= {0, 0, 19, 46}

-- ethiopicSyllableChwa BMPString ::= {0, 0, 19, 47}

-- ethiopicSyllablePha BMPString ::= {0, 0, 19, 48}

-- ethiopicSyllablePhu BMPString ::= {0, 0, 19, 49}

-- ethiopicSyllablePhi BMPString ::= {0, 0, 19, 50}

-- ethiopicSyllablePhaa BMPString ::= {0, 0, 19, 51}

-- ethiopicSyllablePhee BMPString ::= {0, 0, 19, 52}

-- ethiopicSyllablePhe BMPString ::= {0, 0, 19, 53}

-- ethiopicSyllablePho BMPString ::= {0, 0, 19, 54}

-- ethiopicSyllablePhwa BMPString ::= {0, 0, 19, 55}

-- ethiopicSyllableTsa BMPString ::= {0, 0, 19, 56}

-- ethiopicSyllableTsu BMPString ::= {0, 0, 19, 57}

-- ethiopicSyllableTsi BMPString ::= {0, 0, 19, 58}

-- ethiopicSyllableTsaa BMPString ::= {0, 0, 19, 59}

-- ethiopicSyllableTsee BMPString ::= {0, 0, 19, 60}

-- ethiopicSyllableTse BMPString ::= {0, 0, 19, 61}

-- ethiopicSyllableTso BMPString ::= {0, 0, 19, 62}

-- ethiopicSyllableTswa BMPString ::= {0, 0, 19, 63}

-- ethiopicSyllableTza BMPString ::= {0, 0, 19, 64}

-- ethiopicSyllableTzu BMPString ::= {0, 0, 19, 65}

-- ethiopicSyllableTzi BMPString ::= {0, 0, 19, 66}

-- ethiopicSyllableTzaa BMPString ::= {0, 0, 19, 67}

-- ethiopicSyllableTzee BMPString ::= {0, 0, 19, 68}

-- ethiopicSyllableTze BMPString ::= {0, 0, 19, 69}

-- ethiopicSyllableTzo BMPString ::= {0, 0, 19, 70}

-- ethiopicSyllableFa BMPString ::= {0, 0, 19, 72}

-- ethiopicSyllableFu BMPString ::= {0, 0, 19, 73}

-- ethiopicSyllableFi BMPString ::= {0, 0, 19, 74}

-- ethiopicSyllableFaa BMPString ::= {0, 0, 19, 75}

-- ethiopicSyllableFee BMPString ::= {0, 0, 19, 76}

-- ethiopicSyllableFe BMPString ::= {0, 0, 19, 77}

-- ethiopicSyllableFo BMPString ::= {0, 0, 19, 78}

-- ethiopicSyllableFwa BMPString ::= {0, 0, 19, 79}

-- ethiopicSyllablePa BMPString ::= {0, 0, 19, 80}

-- ethiopicSyllablePu BMPString ::= {0, 0, 19, 81}

-- ethiopicSyllablePi BMPString ::= {0, 0, 19, 82}

-- ethiopicSyllablePaa BMPString ::= {0, 0, 19, 83}

-- ethiopicSyllablePee BMPString ::= {0, 0, 19, 84}

-- ethiopicSyllablePe BMPString ::= {0, 0, 19, 85}

-- ethiopicSyllablePo BMPString ::= {0, 0, 19, 86}

-- ethiopicSyllablePwa BMPString ::= {0, 0, 19, 87}

-- ethiopicSyllableRya BMPString ::= {0, 0, 19, 88}

-- ethiopicSyllableMya BMPString ::= {0, 0, 19, 89}

-- ethiopicSyllableFya BMPString ::= {0, 0, 19, 90}

-- ethiopicWordspace BMPString ::= {0, 0, 19, 97}

-- ethiopicFullStop BMPString ::= {0, 0, 19, 98}

-- ethiopicComma BMPString ::= {0, 0, 19, 99}

-- ethiopicSemicolon BMPString ::= {0, 0, 19, 100}

-- ethiopicColon BMPString ::= {0, 0, 19, 101}

-- ethiopicPrefaceColon BMPString ::= {0, 0, 19, 102}

-- ethiopicQuestionMark BMPString ::= {0, 0, 19, 103}

-- ethiopicParagraphSeparator BMPString ::= {0, 0, 19, 104}

-- ethiopicDigitOne BMPString ::= {0, 0, 19, 105}

-- ethiopicDigitTwo BMPString ::= {0, 0, 19, 106}

-- ethiopicDigitThree BMPString ::= {0, 0, 19, 107}

-- ethiopicDigitFour BMPString ::= {0, 0, 19, 108}

-- ethiopicDigitFive BMPString ::= {0, 0, 19, 109}

-- ethiopicDigitSix BMPString ::= {0, 0, 19, 110}

-- ethiopicDigitSeven BMPString ::= {0, 0, 19, 111}

-- ethiopicDigitEight BMPString ::= {0, 0, 19, 112}

-- ethiopicDigitNine BMPString ::= {0, 0, 19, 113}

-- ethiopicNumberTen BMPString ::= {0, 0, 19, 114}

-- ethiopicNumberTwenty BMPString ::= {0, 0, 19, 115}

-- ethiopicNumberThirty BMPString ::= {0, 0, 19, 116}

-- ethiopicNumberForty BMPString ::= {0, 0, 19, 117}

-- ethiopicNumberFifty BMPString ::= {0, 0, 19, 118}

-- ethiopicNumberSixty BMPString ::= {0, 0, 19, 119}

-- ethiopicNumberSeventy BMPString ::= {0, 0, 19, 120}

-- ethiopicNumberEighty BMPString ::= {0, 0, 19, 121}

-- ethiopicNumberNinety BMPString ::= {0, 0, 19, 122}

-- ethiopicNumberHundred BMPString ::= {0, 0, 19, 123}

-- ethiopicNumberTenThousand BMPString ::= {0, 0, 19, 124}

-- cherokeeLetterA BMPString ::= {0, 0, 19, 160}

-- cherokeeLetterE BMPString ::= {0, 0, 19, 161}

-- cherokeeLetterI BMPString ::= {0, 0, 19, 162}

-- cherokeeLetterO BMPString ::= {0, 0, 19, 163}

-- cherokeeLetterU BMPString ::= {0, 0, 19, 164}

-- cherokeeLetterV BMPString ::= {0, 0, 19, 165}

-- cherokeeLetterGa BMPString ::= {0, 0, 19, 166}

-- cherokeeLetterKa BMPString ::= {0, 0, 19, 167}

-- cherokeeLetterGe BMPString ::= {0, 0, 19, 168}

-- cherokeeLetterGi BMPString ::= {0, 0, 19, 169}

-- cherokeeLetterGo BMPString ::= {0, 0, 19, 170}

-- cherokeeLetterGu BMPString ::= {0, 0, 19, 171}

-- cherokeeLetterGv BMPString ::= {0, 0, 19, 172}

-- cherokeeLetterHa BMPString ::= {0, 0, 19, 173}

-- cherokeeLetterHe BMPString ::= {0, 0, 19, 174}

-- cherokeeLetterHi BMPString ::= {0, 0, 19, 175}

-- cherokeeLetterHo BMPString ::= {0, 0, 19, 176}

-- cherokeeLetterHu BMPString ::= {0, 0, 19, 177}

-- cherokeeLetterHv BMPString ::= {0, 0, 19, 178}

-- cherokeeLetterLa BMPString ::= {0, 0, 19, 179}

-- cherokeeLetterLe BMPString ::= {0, 0, 19, 180}

-- cherokeeLetterLi BMPString ::= {0, 0, 19, 181}

-- cherokeeLetterLo BMPString ::= {0, 0, 19, 182}

-- cherokeeLetterLu BMPString ::= {0, 0, 19, 183}

-- cherokeeLetterLv BMPString ::= {0, 0, 19, 184}

-- cherokeeLetterMa BMPString ::= {0, 0, 19, 185}

-- cherokeeLetterMe BMPString ::= {0, 0, 19, 186}

-- cherokeeLetterMi BMPString ::= {0, 0, 19, 187}

-- cherokeeLetterMo BMPString ::= {0, 0, 19, 188}

-- cherokeeLetterMu BMPString ::= {0, 0, 19, 189}

-- cherokeeLetterNa BMPString ::= {0, 0, 19, 190}

-- cherokeeLetterHna BMPString ::= {0, 0, 19, 191}

-- cherokeeLetterNah BMPString ::= {0, 0, 19, 192}

-- cherokeeLetterNe BMPString ::= {0, 0, 19, 193}

-- cherokeeLetterNi BMPString ::= {0, 0, 19, 194}

-- cherokeeLetterNo BMPString ::= {0, 0, 19, 195}

-- cherokeeLetterNu BMPString ::= {0, 0, 19, 196}

-- cherokeeLetterNv BMPString ::= {0, 0, 19, 197}

-- cherokeeLetterQua BMPString ::= {0, 0, 19, 198}

-- cherokeeLetterQue BMPString ::= {0, 0, 19, 199}

-- cherokeeLetterQui BMPString ::= {0, 0, 19, 200}

-- cherokeeLetterQuo BMPString ::= {0, 0, 19, 201}

-- cherokeeLetterQuu BMPString ::= {0, 0, 19, 202}

-- cherokeeLetterQuv BMPString ::= {0, 0, 19, 203}

-- cherokeeLetterSa BMPString ::= {0, 0, 19, 204}

-- cherokeeLetterS BMPString ::= {0, 0, 19, 205}

-- cherokeeLetterSe BMPString ::= {0, 0, 19, 206}

-- cherokeeLetterSi BMPString ::= {0, 0, 19, 207}

-- cherokeeLetterSo BMPString ::= {0, 0, 19, 208}

-- cherokeeLetterSu BMPString ::= {0, 0, 19, 209}

-- cherokeeLetterSv BMPString ::= {0, 0, 19, 210}

-- cherokeeLetterDa BMPString ::= {0, 0, 19, 211}

-- cherokeeLetterTa BMPString ::= {0, 0, 19, 212}

-- cherokeeLetterDe BMPString ::= {0, 0, 19, 213}

-- cherokeeLetterTe BMPString ::= {0, 0, 19, 214}

-- cherokeeLetterDi BMPString ::= {0, 0, 19, 215}

-- cherokeeLetterTi BMPString ::= {0, 0, 19, 216}

-- cherokeeLetterDo BMPString ::= {0, 0, 19, 217}

-- cherokeeLetterDu BMPString ::= {0, 0, 19, 218}

-- cherokeeLetterDv BMPString ::= {0, 0, 19, 219}

-- cherokeeLetterDla BMPString ::= {0, 0, 19, 220}

-- cherokeeLetterTla BMPString ::= {0, 0, 19, 221}

-- cherokeeLetterTle BMPString ::= {0, 0, 19, 222}

-- cherokeeLetterTli BMPString ::= {0, 0, 19, 223}

-- cherokeeLetterTlo BMPString ::= {0, 0, 19, 224}

-- cherokeeLetterTlu BMPString ::= {0, 0, 19, 225}

-- cherokeeLetterTlv BMPString ::= {0, 0, 19, 226}

-- cherokeeLetterTsa BMPString ::= {0, 0, 19, 227}

-- cherokeeLetterTse BMPString ::= {0, 0, 19, 228}

-- cherokeeLetterTsi BMPString ::= {0, 0, 19, 229}

-- cherokeeLetterTso BMPString ::= {0, 0, 19, 230}

-- cherokeeLetterTsu BMPString ::= {0, 0, 19, 231}

-- cherokeeLetterTsv BMPString ::= {0, 0, 19, 232}

-- cherokeeLetterWa BMPString ::= {0, 0, 19, 233}

-- cherokeeLetterWe BMPString ::= {0, 0, 19, 234}

-- cherokeeLetterWi BMPString ::= {0, 0, 19, 235}

-- cherokeeLetterWo BMPString ::= {0, 0, 19, 236}

-- cherokeeLetterWu BMPString ::= {0, 0, 19, 237}

-- cherokeeLetterWv BMPString ::= {0, 0, 19, 238}

-- cherokeeLetterYa BMPString ::= {0, 0, 19, 239}

-- cherokeeLetterYe BMPString ::= {0, 0, 19, 240}

-- cherokeeLetterYi BMPString ::= {0, 0, 19, 241}

-- cherokeeLetterYo BMPString ::= {0, 0, 19, 242}

-- cherokeeLetterYu BMPString ::= {0, 0, 19, 243}

-- cherokeeLetterYv BMPString ::= {0, 0, 19, 244}

-- canadianSyllabicsE BMPString ::= {0, 0, 20, 1}

-- canadianSyllabicsAai BMPString ::= {0, 0, 20, 2}

-- canadianSyllabicsI BMPString ::= {0, 0, 20, 3}

-- canadianSyllabicsIi BMPString ::= {0, 0, 20, 4}

-- canadianSyllabicsO BMPString ::= {0, 0, 20, 5}

-- canadianSyllabicsOo BMPString ::= {0, 0, 20, 6}

-- canadianSyllabicsY-creeOo BMPString ::= {0, 0, 20, 7}

-- canadianSyllabicsCarrierEe BMPString ::= {0, 0, 20, 8}

-- canadianSyllabicsCarrierI BMPString ::= {0, 0, 20, 9}

-- canadianSyllabicsA BMPString ::= {0, 0, 20, 10}

-- canadianSyllabicsAa BMPString ::= {0, 0, 20, 11}

-- canadianSyllabicsWe BMPString ::= {0, 0, 20, 12}

-- canadianSyllabicsWest-creeWe BMPString ::= {0, 0, 20, 13}

-- canadianSyllabicsWi BMPString ::= {0, 0, 20, 14}

-- canadianSyllabicsWest-creeWi BMPString ::= {0, 0, 20, 15}

-- canadianSyllabicsWii BMPString ::= {0, 0, 20, 16}

-- canadianSyllabicsWest-creeWii BMPString ::= {0, 0, 20, 17}

-- canadianSyllabicsWo BMPString ::= {0, 0, 20, 18}

-- canadianSyllabicsWest-creeWo BMPString ::= {0, 0, 20, 19}

-- canadianSyllabicsWoo BMPString ::= {0, 0, 20, 20}

-- canadianSyllabicsWest-creeWoo BMPString ::= {0, 0, 20, 21}

-- canadianSyllabicsNaskapiWoo BMPString ::= {0, 0, 20, 22}

-- canadianSyllabicsWa BMPString ::= {0, 0, 20, 23}

-- canadianSyllabicsWest-creeWa BMPString ::= {0, 0, 20, 24}

-- canadianSyllabicsWaa BMPString ::= {0, 0, 20, 25}

-- canadianSyllabicsWest-creeWaa BMPString ::= {0, 0, 20, 26}

-- canadianSyllabicsNaskapiWaa BMPString ::= {0, 0, 20, 27}

-- canadianSyllabicsAi BMPString ::= {0, 0, 20, 28}

-- canadianSyllabicsY-creeW BMPString ::= {0, 0, 20, 29}

-- canadianSyllabicsGlottalStop BMPString ::= {0, 0, 20, 30}

-- canadianSyllabicsFinalAcute BMPString ::= {0, 0, 20, 31}

-- canadianSyllabicsFinalGrave BMPString ::= {0, 0, 20, 32}

-- canadianSyllabicsFinalBottomHalfRing BMPString ::= {0, 0, 20, 33}

-- canadianSyllabicsFinalTopHalfRing BMPString ::= {0, 0, 20, 34}

-- canadianSyllabicsFinalRightHalfRing BMPString ::= {0, 0, 20, 35}

-- canadianSyllabicsFinalRing BMPString ::= {0, 0, 20, 36}

-- canadianSyllabicsFinalDoubleAcute BMPString ::= {0, 0, 20, 37}

-- canadianSyllabicsFinalDoubleShortVerticalStrokes BMPString ::= {0, 0, 20, 38}

-- canadianSyllabicsFinalMiddleDot BMPString ::= {0, 0, 20, 39}

-- canadianSyllabicsFinalShortHorizontalStroke BMPString ::= {0, 0, 20, 40}

-- canadianSyllabicsFinalPlus BMPString ::= {0, 0, 20, 41}

-- canadianSyllabicsFinalDownTack BMPString ::= {0, 0, 20, 42}

-- canadianSyllabicsEn BMPString ::= {0, 0, 20, 43}

-- canadianSyllabicsIn BMPString ::= {0, 0, 20, 44}

-- canadianSyllabicsOn BMPString ::= {0, 0, 20, 45}

-- canadianSyllabicsAn BMPString ::= {0, 0, 20, 46}

-- canadianSyllabicsPe BMPString ::= {0, 0, 20, 47}

-- canadianSyllabicsPaai BMPString ::= {0, 0, 20, 48}

-- canadianSyllabicsPi BMPString ::= {0, 0, 20, 49}

-- canadianSyllabicsPii BMPString ::= {0, 0, 20, 50}

-- canadianSyllabicsPo BMPString ::= {0, 0, 20, 51}

-- canadianSyllabicsPoo BMPString ::= {0, 0, 20, 52}

-- canadianSyllabicsY-creePoo BMPString ::= {0, 0, 20, 53}

-- canadianSyllabicsCarrierHee BMPString ::= {0, 0, 20, 54}

-- canadianSyllabicsCarrierHi BMPString ::= {0, 0, 20, 55}

-- canadianSyllabicsPa BMPString ::= {0, 0, 20, 56}

-- canadianSyllabicsPaa BMPString ::= {0, 0, 20, 57}

-- canadianSyllabicsPwe BMPString ::= {0, 0, 20, 58}

-- canadianSyllabicsWest-creePwe BMPString ::= {0, 0, 20, 59}

-- canadianSyllabicsPwi BMPString ::= {0, 0, 20, 60}

-- canadianSyllabicsWest-creePwi BMPString ::= {0, 0, 20, 61}

-- canadianSyllabicsPwii BMPString ::= {0, 0, 20, 62}

-- canadianSyllabicsWest-creePwii BMPString ::= {0, 0, 20, 63}

-- canadianSyllabicsPwo BMPString ::= {0, 0, 20, 64}

-- canadianSyllabicsWest-creePwo BMPString ::= {0, 0, 20, 65}

-- canadianSyllabicsPwoo BMPString ::= {0, 0, 20, 66}

-- canadianSyllabicsWest-creePwoo BMPString ::= {0, 0, 20, 67}

-- canadianSyllabicsPwa BMPString ::= {0, 0, 20, 68}

-- canadianSyllabicsWest-creePwa BMPString ::= {0, 0, 20, 69}

-- canadianSyllabicsPwaa BMPString ::= {0, 0, 20, 70}

-- canadianSyllabicsWest-creePwaa BMPString ::= {0, 0, 20, 71}

-- canadianSyllabicsY-creePwaa BMPString ::= {0, 0, 20, 72}

-- canadianSyllabicsP BMPString ::= {0, 0, 20, 73}

-- canadianSyllabicsWest-creeP BMPString ::= {0, 0, 20, 74}

-- canadianSyllabicsCarrierH BMPString ::= {0, 0, 20, 75}

-- canadianSyllabicsTe BMPString ::= {0, 0, 20, 76}

-- canadianSyllabicsTaai BMPString ::= {0, 0, 20, 77}

-- canadianSyllabicsTi BMPString ::= {0, 0, 20, 78}

-- canadianSyllabicsTii BMPString ::= {0, 0, 20, 79}

-- canadianSyllabicsTo BMPString ::= {0, 0, 20, 80}

-- canadianSyllabicsToo BMPString ::= {0, 0, 20, 81}

-- canadianSyllabicsY-creeToo BMPString ::= {0, 0, 20, 82}

-- canadianSyllabicsCarrierDee BMPString ::= {0, 0, 20, 83}

-- canadianSyllabicsCarrierDi BMPString ::= {0, 0, 20, 84}

-- canadianSyllabicsTa BMPString ::= {0, 0, 20, 85}

-- canadianSyllabicsTaa BMPString ::= {0, 0, 20, 86}

-- canadianSyllabicsTwe BMPString ::= {0, 0, 20, 87}

-- canadianSyllabicsWest-creeTwe BMPString ::= {0, 0, 20, 88}

-- canadianSyllabicsTwi BMPString ::= {0, 0, 20, 89}

-- canadianSyllabicsWest-creeTwi BMPString ::= {0, 0, 20, 90}

-- canadianSyllabicsTwii BMPString ::= {0, 0, 20, 91}

-- canadianSyllabicsWest-creeTwii BMPString ::= {0, 0, 20, 92}

-- canadianSyllabicsTwo BMPString ::= {0, 0, 20, 93}

-- canadianSyllabicsWest-creeTwo BMPString ::= {0, 0, 20, 94}

-- canadianSyllabicsTwoo BMPString ::= {0, 0, 20, 95}

-- canadianSyllabicsWest-creeTwoo BMPString ::= {0, 0, 20, 96}

-- canadianSyllabicsTwa BMPString ::= {0, 0, 20, 97}

-- canadianSyllabicsWest-creeTwa BMPString ::= {0, 0, 20, 98}

-- canadianSyllabicsTwaa BMPString ::= {0, 0, 20, 99}

-- canadianSyllabicsWest-creeTwaa BMPString ::= {0, 0, 20, 100}

-- canadianSyllabicsNaskapiTwaa BMPString ::= {0, 0, 20, 101}

-- canadianSyllabicsT BMPString ::= {0, 0, 20, 102}

-- canadianSyllabicsTte BMPString ::= {0, 0, 20, 103}

-- canadianSyllabicsTti BMPString ::= {0, 0, 20, 104}

-- canadianSyllabicsTto BMPString ::= {0, 0, 20, 105}

-- canadianSyllabicsTta BMPString ::= {0, 0, 20, 106}

-- canadianSyllabicsKe BMPString ::= {0, 0, 20, 107}

-- canadianSyllabicsKaai BMPString ::= {0, 0, 20, 108}

-- canadianSyllabicsKi BMPString ::= {0, 0, 20, 109}

-- canadianSyllabicsKii BMPString ::= {0, 0, 20, 110}

-- canadianSyllabicsKo BMPString ::= {0, 0, 20, 111}

-- canadianSyllabicsKoo BMPString ::= {0, 0, 20, 112}

-- canadianSyllabicsY-creeKoo BMPString ::= {0, 0, 20, 113}

-- canadianSyllabicsKa BMPString ::= {0, 0, 20, 114}

-- canadianSyllabicsKaa BMPString ::= {0, 0, 20, 115}

-- canadianSyllabicsKwe BMPString ::= {0, 0, 20, 116}

-- canadianSyllabicsWest-creeKwe BMPString ::= {0, 0, 20, 117}

-- canadianSyllabicsKwi BMPString ::= {0, 0, 20, 118}

-- canadianSyllabicsWest-creeKwi BMPString ::= {0, 0, 20, 119}

-- canadianSyllabicsKwii BMPString ::= {0, 0, 20, 120}

-- canadianSyllabicsWest-creeKwii BMPString ::= {0, 0, 20, 121}

-- canadianSyllabicsKwo BMPString ::= {0, 0, 20, 122}

-- canadianSyllabicsWest-creeKwo BMPString ::= {0, 0, 20, 123}

-- canadianSyllabicsKwoo BMPString ::= {0, 0, 20, 124}

-- canadianSyllabicsWest-creeKwoo BMPString ::= {0, 0, 20, 125}

-- canadianSyllabicsKwa BMPString ::= {0, 0, 20, 126}

-- canadianSyllabicsWest-creeKwa BMPString ::= {0, 0, 20, 127}

-- canadianSyllabicsKwaa BMPString ::= {0, 0, 20, 128}

-- canadianSyllabicsWest-creeKwaa BMPString ::= {0, 0, 20, 129}

-- canadianSyllabicsNaskapiKwaa BMPString ::= {0, 0, 20, 130}

-- canadianSyllabicsK BMPString ::= {0, 0, 20, 131}

-- canadianSyllabicsKw BMPString ::= {0, 0, 20, 132}

-- canadianSyllabicsSouth-slaveyKeh BMPString ::= {0, 0, 20, 133}

-- canadianSyllabicsSouth-slaveyKih BMPString ::= {0, 0, 20, 134}

-- canadianSyllabicsSouth-slaveyKoh BMPString ::= {0, 0, 20, 135}

-- canadianSyllabicsSouth-slaveyKah BMPString ::= {0, 0, 20, 136}

-- canadianSyllabicsCe BMPString ::= {0, 0, 20, 137}

-- canadianSyllabicsCaai BMPString ::= {0, 0, 20, 138}

-- canadianSyllabicsCi BMPString ::= {0, 0, 20, 139}

-- canadianSyllabicsCii BMPString ::= {0, 0, 20, 140}

-- canadianSyllabicsCo BMPString ::= {0, 0, 20, 141}

-- canadianSyllabicsCoo BMPString ::= {0, 0, 20, 142}

-- canadianSyllabicsY-creeCoo BMPString ::= {0, 0, 20, 143}

-- canadianSyllabicsCa BMPString ::= {0, 0, 20, 144}

-- canadianSyllabicsCaa BMPString ::= {0, 0, 20, 145}

-- canadianSyllabicsCwe BMPString ::= {0, 0, 20, 146}

-- canadianSyllabicsWest-creeCwe BMPString ::= {0, 0, 20, 147}

-- canadianSyllabicsCwi BMPString ::= {0, 0, 20, 148}

-- canadianSyllabicsWest-creeCwi BMPString ::= {0, 0, 20, 149}

-- canadianSyllabicsCwii BMPString ::= {0, 0, 20, 150}

-- canadianSyllabicsWest-creeCwii BMPString ::= {0, 0, 20, 151}

-- canadianSyllabicsCwo BMPString ::= {0, 0, 20, 152}

-- canadianSyllabicsWest-creeCwo BMPString ::= {0, 0, 20, 153}

-- canadianSyllabicsCwoo BMPString ::= {0, 0, 20, 154}

-- canadianSyllabicsWest-creeCwoo BMPString ::= {0, 0, 20, 155}

-- canadianSyllabicsCwa BMPString ::= {0, 0, 20, 156}

-- canadianSyllabicsWest-creeCwa BMPString ::= {0, 0, 20, 157}

-- canadianSyllabicsCwaa BMPString ::= {0, 0, 20, 158}

-- canadianSyllabicsWest-creeCwaa BMPString ::= {0, 0, 20, 159}

-- canadianSyllabicsNaskapiCwaa BMPString ::= {0, 0, 20, 160}

-- canadianSyllabicsC BMPString ::= {0, 0, 20, 161}

-- canadianSyllabicsSayisiTh BMPString ::= {0, 0, 20, 162}

-- canadianSyllabicsMe BMPString ::= {0, 0, 20, 163}

-- canadianSyllabicsMaai BMPString ::= {0, 0, 20, 164}

-- canadianSyllabicsMi BMPString ::= {0, 0, 20, 165}

-- canadianSyllabicsMii BMPString ::= {0, 0, 20, 166}

-- canadianSyllabicsMo BMPString ::= {0, 0, 20, 167}

-- canadianSyllabicsMoo BMPString ::= {0, 0, 20, 168}

-- canadianSyllabicsY-creeMoo BMPString ::= {0, 0, 20, 169}

-- canadianSyllabicsMa BMPString ::= {0, 0, 20, 170}

-- canadianSyllabicsMaa BMPString ::= {0, 0, 20, 171}

-- canadianSyllabicsMwe BMPString ::= {0, 0, 20, 172}

-- canadianSyllabicsWest-creeMwe BMPString ::= {0, 0, 20, 173}

-- canadianSyllabicsMwi BMPString ::= {0, 0, 20, 174}

-- canadianSyllabicsWest-creeMwi BMPString ::= {0, 0, 20, 175}

-- canadianSyllabicsMwii BMPString ::= {0, 0, 20, 176}

-- canadianSyllabicsWest-creeMwii BMPString ::= {0, 0, 20, 177}

-- canadianSyllabicsMwo BMPString ::= {0, 0, 20, 178}

-- canadianSyllabicsWest-creeMwo BMPString ::= {0, 0, 20, 179}

-- canadianSyllabicsMwoo BMPString ::= {0, 0, 20, 180}

-- canadianSyllabicsWest-creeMwoo BMPString ::= {0, 0, 20, 181}

-- canadianSyllabicsMwa BMPString ::= {0, 0, 20, 182}

-- canadianSyllabicsWest-creeMwa BMPString ::= {0, 0, 20, 183}

-- canadianSyllabicsMwaa BMPString ::= {0, 0, 20, 184}

-- canadianSyllabicsWest-creeMwaa BMPString ::= {0, 0, 20, 185}

-- canadianSyllabicsNaskapiMwaa BMPString ::= {0, 0, 20, 186}

-- canadianSyllabicsM BMPString ::= {0, 0, 20, 187}

-- canadianSyllabicsWest-creeM BMPString ::= {0, 0, 20, 188}

-- canadianSyllabicsMh BMPString ::= {0, 0, 20, 189}

-- canadianSyllabicsAthapascanM BMPString ::= {0, 0, 20, 190}

-- canadianSyllabicsSayisiM BMPString ::= {0, 0, 20, 191}

-- canadianSyllabicsNe BMPString ::= {0, 0, 20, 192}

-- canadianSyllabicsNaai BMPString ::= {0, 0, 20, 193}

-- canadianSyllabicsNi BMPString ::= {0, 0, 20, 194}

-- canadianSyllabicsNii BMPString ::= {0, 0, 20, 195}

-- canadianSyllabicsNo BMPString ::= {0, 0, 20, 196}

-- canadianSyllabicsNoo BMPString ::= {0, 0, 20, 197}

-- canadianSyllabicsY-creeNoo BMPString ::= {0, 0, 20, 198}

-- canadianSyllabicsNa BMPString ::= {0, 0, 20, 199}

-- canadianSyllabicsNaa BMPString ::= {0, 0, 20, 200}

-- canadianSyllabicsNwe BMPString ::= {0, 0, 20, 201}

-- canadianSyllabicsWest-creeNwe BMPString ::= {0, 0, 20, 202}

-- canadianSyllabicsNwa BMPString ::= {0, 0, 20, 203}

-- canadianSyllabicsWest-creeNwa BMPString ::= {0, 0, 20, 204}

-- canadianSyllabicsNwaa BMPString ::= {0, 0, 20, 205}

-- canadianSyllabicsWest-creeNwaa BMPString ::= {0, 0, 20, 206}

-- canadianSyllabicsNaskapiNwaa BMPString ::= {0, 0, 20, 207}

-- canadianSyllabicsN BMPString ::= {0, 0, 20, 208}

-- canadianSyllabicsCarrierNg BMPString ::= {0, 0, 20, 209}

-- canadianSyllabicsNh BMPString ::= {0, 0, 20, 210}

-- canadianSyllabicsLe BMPString ::= {0, 0, 20, 211}

-- canadianSyllabicsLaai BMPString ::= {0, 0, 20, 212}

-- canadianSyllabicsLi BMPString ::= {0, 0, 20, 213}

-- canadianSyllabicsLii BMPString ::= {0, 0, 20, 214}

-- canadianSyllabicsLo BMPString ::= {0, 0, 20, 215}

-- canadianSyllabicsLoo BMPString ::= {0, 0, 20, 216}

-- canadianSyllabicsY-creeLoo BMPString ::= {0, 0, 20, 217}

-- canadianSyllabicsLa BMPString ::= {0, 0, 20, 218}

-- canadianSyllabicsLaa BMPString ::= {0, 0, 20, 219}

-- canadianSyllabicsLwe BMPString ::= {0, 0, 20, 220}

-- canadianSyllabicsWest-creeLwe BMPString ::= {0, 0, 20, 221}

-- canadianSyllabicsLwi BMPString ::= {0, 0, 20, 222}

-- canadianSyllabicsWest-creeLwi BMPString ::= {0, 0, 20, 223}

-- canadianSyllabicsLwii BMPString ::= {0, 0, 20, 224}

-- canadianSyllabicsWest-creeLwii BMPString ::= {0, 0, 20, 225}

-- canadianSyllabicsLwo BMPString ::= {0, 0, 20, 226}

-- canadianSyllabicsWest-creeLwo BMPString ::= {0, 0, 20, 227}

-- canadianSyllabicsLwoo BMPString ::= {0, 0, 20, 228}

-- canadianSyllabicsWest-creeLwoo BMPString ::= {0, 0, 20, 229}

-- canadianSyllabicsLwa BMPString ::= {0, 0, 20, 230}

-- canadianSyllabicsWest-creeLwa BMPString ::= {0, 0, 20, 231}

-- canadianSyllabicsLwaa BMPString ::= {0, 0, 20, 232}

-- canadianSyllabicsWest-creeLwaa BMPString ::= {0, 0, 20, 233}

-- canadianSyllabicsL BMPString ::= {0, 0, 20, 234}

-- canadianSyllabicsWest-creeL BMPString ::= {0, 0, 20, 235}

-- canadianSyllabicsMedialL BMPString ::= {0, 0, 20, 236}

-- canadianSyllabicsSe BMPString ::= {0, 0, 20, 237}

-- canadianSyllabicsSaai BMPString ::= {0, 0, 20, 238}

-- canadianSyllabicsSi BMPString ::= {0, 0, 20, 239}

-- canadianSyllabicsSii BMPString ::= {0, 0, 20, 240}

-- canadianSyllabicsSo BMPString ::= {0, 0, 20, 241}

-- canadianSyllabicsSoo BMPString ::= {0, 0, 20, 242}

-- canadianSyllabicsY-creeSoo BMPString ::= {0, 0, 20, 243}

-- canadianSyllabicsSa BMPString ::= {0, 0, 20, 244}

-- canadianSyllabicsSaa BMPString ::= {0, 0, 20, 245}

-- canadianSyllabicsSwe BMPString ::= {0, 0, 20, 246}

-- canadianSyllabicsWest-creeSwe BMPString ::= {0, 0, 20, 247}

-- canadianSyllabicsSwi BMPString ::= {0, 0, 20, 248}

-- canadianSyllabicsWest-creeSwi BMPString ::= {0, 0, 20, 249}

-- canadianSyllabicsSwii BMPString ::= {0, 0, 20, 250}

-- canadianSyllabicsWest-creeSwii BMPString ::= {0, 0, 20, 251}

-- canadianSyllabicsSwo BMPString ::= {0, 0, 20, 252}

-- canadianSyllabicsWest-creeSwo BMPString ::= {0, 0, 20, 253}

-- canadianSyllabicsSwoo BMPString ::= {0, 0, 20, 254}

-- canadianSyllabicsWest-creeSwoo BMPString ::= {0, 0, 20, 255}

-- canadianSyllabicsSwa BMPString ::= {0, 0, 21, 0}

-- canadianSyllabicsWest-creeSwa BMPString ::= {0, 0, 21, 1}

-- canadianSyllabicsSwaa BMPString ::= {0, 0, 21, 2}

-- canadianSyllabicsWest-creeSwaa BMPString ::= {0, 0, 21, 3}

-- canadianSyllabicsNaskapiSwaa BMPString ::= {0, 0, 21, 4}

-- canadianSyllabicsS BMPString ::= {0, 0, 21, 5}

-- canadianSyllabicsAthapascanS BMPString ::= {0, 0, 21, 6}

-- canadianSyllabicsSw BMPString ::= {0, 0, 21, 7}

-- canadianSyllabicsBlackfootS BMPString ::= {0, 0, 21, 8}

-- canadianSyllabicsMoose-creeSk BMPString ::= {0, 0, 21, 9}

-- canadianSyllabicsNaskapiSkw BMPString ::= {0, 0, 21, 10}

-- canadianSyllabicsNaskapiS-w BMPString ::= {0, 0, 21, 11}

-- canadianSyllabicsNaskapiSpwa BMPString ::= {0, 0, 21, 12}

-- canadianSyllabicsNaskapiStwa BMPString ::= {0, 0, 21, 13}

-- canadianSyllabicsNaskapiSkwa BMPString ::= {0, 0, 21, 14}

-- canadianSyllabicsNaskapiScwa BMPString ::= {0, 0, 21, 15}

-- canadianSyllabicsShe BMPString ::= {0, 0, 21, 16}

-- canadianSyllabicsShi BMPString ::= {0, 0, 21, 17}

-- canadianSyllabicsShii BMPString ::= {0, 0, 21, 18}

-- canadianSyllabicsSho BMPString ::= {0, 0, 21, 19}

-- canadianSyllabicsShoo BMPString ::= {0, 0, 21, 20}

-- canadianSyllabicsSha BMPString ::= {0, 0, 21, 21}

-- canadianSyllabicsShaa BMPString ::= {0, 0, 21, 22}

-- canadianSyllabicsShwe BMPString ::= {0, 0, 21, 23}

-- canadianSyllabicsWest-creeShwe BMPString ::= {0, 0, 21, 24}

-- canadianSyllabicsShwi BMPString ::= {0, 0, 21, 25}

-- canadianSyllabicsWest-creeShwi BMPString ::= {0, 0, 21, 26}

-- canadianSyllabicsShwii BMPString ::= {0, 0, 21, 27}

-- canadianSyllabicsWest-creeShwii BMPString ::= {0, 0, 21, 28}

-- canadianSyllabicsShwo BMPString ::= {0, 0, 21, 29}

-- canadianSyllabicsWest-creeShwo BMPString ::= {0, 0, 21, 30}

-- canadianSyllabicsShwoo BMPString ::= {0, 0, 21, 31}

-- canadianSyllabicsWest-creeShwoo BMPString ::= {0, 0, 21, 32}

-- canadianSyllabicsShwa BMPString ::= {0, 0, 21, 33}

-- canadianSyllabicsWest-creeShwa BMPString ::= {0, 0, 21, 34}

-- canadianSyllabicsShwaa BMPString ::= {0, 0, 21, 35}

-- canadianSyllabicsWest-creeShwaa BMPString ::= {0, 0, 21, 36}

-- canadianSyllabicsSh BMPString ::= {0, 0, 21, 37}

-- canadianSyllabicsYe BMPString ::= {0, 0, 21, 38}

-- canadianSyllabicsYaai BMPString ::= {0, 0, 21, 39}

-- canadianSyllabicsYi BMPString ::= {0, 0, 21, 40}

-- canadianSyllabicsYii BMPString ::= {0, 0, 21, 41}

-- canadianSyllabicsYo BMPString ::= {0, 0, 21, 42}

-- canadianSyllabicsYoo BMPString ::= {0, 0, 21, 43}

-- canadianSyllabicsY-creeYoo BMPString ::= {0, 0, 21, 44}

-- canadianSyllabicsYa BMPString ::= {0, 0, 21, 45}

-- canadianSyllabicsYaa BMPString ::= {0, 0, 21, 46}

-- canadianSyllabicsYwe BMPString ::= {0, 0, 21, 47}

-- canadianSyllabicsWest-creeYwe BMPString ::= {0, 0, 21, 48}

-- canadianSyllabicsYwi BMPString ::= {0, 0, 21, 49}

-- canadianSyllabicsWest-creeYwi BMPString ::= {0, 0, 21, 50}

-- canadianSyllabicsYwii BMPString ::= {0, 0, 21, 51}

-- canadianSyllabicsWest-creeYwii BMPString ::= {0, 0, 21, 52}

-- canadianSyllabicsYwo BMPString ::= {0, 0, 21, 53}

-- canadianSyllabicsWest-creeYwo BMPString ::= {0, 0, 21, 54}

-- canadianSyllabicsYwoo BMPString ::= {0, 0, 21, 55}

-- canadianSyllabicsWest-creeYwoo BMPString ::= {0, 0, 21, 56}

-- canadianSyllabicsYwa BMPString ::= {0, 0, 21, 57}

-- canadianSyllabicsWest-creeYwa BMPString ::= {0, 0, 21, 58}

-- canadianSyllabicsYwaa BMPString ::= {0, 0, 21, 59}

-- canadianSyllabicsWest-creeYwaa BMPString ::= {0, 0, 21, 60}

-- canadianSyllabicsNaskapiYwaa BMPString ::= {0, 0, 21, 61}

-- canadianSyllabicsY BMPString ::= {0, 0, 21, 62}

-- canadianSyllabicsBible-creeY BMPString ::= {0, 0, 21, 63}

-- canadianSyllabicsWest-creeY BMPString ::= {0, 0, 21, 64}

-- canadianSyllabicsSayisiYi BMPString ::= {0, 0, 21, 65}

-- canadianSyllabicsRe BMPString ::= {0, 0, 21, 66}

-- canadianSyllabicsR-creeRe BMPString ::= {0, 0, 21, 67}

-- canadianSyllabicsWest-creeLe BMPString ::= {0, 0, 21, 68}

-- canadianSyllabicsRaai BMPString ::= {0, 0, 21, 69}

-- canadianSyllabicsRi BMPString ::= {0, 0, 21, 70}

-- canadianSyllabicsRii BMPString ::= {0, 0, 21, 71}

-- canadianSyllabicsRo BMPString ::= {0, 0, 21, 72}

-- canadianSyllabicsRoo BMPString ::= {0, 0, 21, 73}

-- canadianSyllabicsWest-creeLo BMPString ::= {0, 0, 21, 74}

-- canadianSyllabicsRa BMPString ::= {0, 0, 21, 75}

-- canadianSyllabicsRaa BMPString ::= {0, 0, 21, 76}

-- canadianSyllabicsWest-creeLa BMPString ::= {0, 0, 21, 77}

-- canadianSyllabicsRwaa BMPString ::= {0, 0, 21, 78}

-- canadianSyllabicsWest-creeRwaa BMPString ::= {0, 0, 21, 79}

-- canadianSyllabicsR BMPString ::= {0, 0, 21, 80}

-- canadianSyllabicsWest-creeR BMPString ::= {0, 0, 21, 81}

-- canadianSyllabicsMedialR BMPString ::= {0, 0, 21, 82}

-- canadianSyllabicsFe BMPString ::= {0, 0, 21, 83}

-- canadianSyllabicsFaai BMPString ::= {0, 0, 21, 84}

-- canadianSyllabicsFi BMPString ::= {0, 0, 21, 85}

-- canadianSyllabicsFii BMPString ::= {0, 0, 21, 86}

-- canadianSyllabicsFo BMPString ::= {0, 0, 21, 87}

-- canadianSyllabicsFoo BMPString ::= {0, 0, 21, 88}

-- canadianSyllabicsFa BMPString ::= {0, 0, 21, 89}

-- canadianSyllabicsFaa BMPString ::= {0, 0, 21, 90}

-- canadianSyllabicsFwaa BMPString ::= {0, 0, 21, 91}

-- canadianSyllabicsWest-creeFwaa BMPString ::= {0, 0, 21, 92}

-- canadianSyllabicsF BMPString ::= {0, 0, 21, 93}

-- canadianSyllabicsThe BMPString ::= {0, 0, 21, 94}

-- canadianSyllabicsN-creeThe BMPString ::= {0, 0, 21, 95}

-- canadianSyllabicsThi BMPString ::= {0, 0, 21, 96}

-- canadianSyllabicsN-creeThi BMPString ::= {0, 0, 21, 97}

-- canadianSyllabicsThii BMPString ::= {0, 0, 21, 98}

-- canadianSyllabicsN-creeThii BMPString ::= {0, 0, 21, 99}

-- canadianSyllabicsTho BMPString ::= {0, 0, 21, 100}

-- canadianSyllabicsThoo BMPString ::= {0, 0, 21, 101}

-- canadianSyllabicsTha BMPString ::= {0, 0, 21, 102}

-- canadianSyllabicsThaa BMPString ::= {0, 0, 21, 103}

-- canadianSyllabicsThwaa BMPString ::= {0, 0, 21, 104}

-- canadianSyllabicsWest-creeThwaa BMPString ::= {0, 0, 21, 105}

-- canadianSyllabicsTh BMPString ::= {0, 0, 21, 106}

-- canadianSyllabicsTthe BMPString ::= {0, 0, 21, 107}

-- canadianSyllabicsTthi BMPString ::= {0, 0, 21, 108}

-- canadianSyllabicsTtho BMPString ::= {0, 0, 21, 109}

-- canadianSyllabicsTtha BMPString ::= {0, 0, 21, 110}

-- canadianSyllabicsTth BMPString ::= {0, 0, 21, 111}

-- canadianSyllabicsTye BMPString ::= {0, 0, 21, 112}

-- canadianSyllabicsTyi BMPString ::= {0, 0, 21, 113}

-- canadianSyllabicsTyo BMPString ::= {0, 0, 21, 114}

-- canadianSyllabicsTya BMPString ::= {0, 0, 21, 115}

-- canadianSyllabicsNunavikHe BMPString ::= {0, 0, 21, 116}

-- canadianSyllabicsNunavikHi BMPString ::= {0, 0, 21, 117}

-- canadianSyllabicsNunavikHii BMPString ::= {0, 0, 21, 118}

-- canadianSyllabicsNunavikHo BMPString ::= {0, 0, 21, 119}

-- canadianSyllabicsNunavikHoo BMPString ::= {0, 0, 21, 120}

-- canadianSyllabicsNunavikHa BMPString ::= {0, 0, 21, 121}

-- canadianSyllabicsNunavikHaa BMPString ::= {0, 0, 21, 122}

-- canadianSyllabicsNunavikH BMPString ::= {0, 0, 21, 123}

-- canadianSyllabicsNunavutH BMPString ::= {0, 0, 21, 124}

-- canadianSyllabicsHk BMPString ::= {0, 0, 21, 125}

-- canadianSyllabicsQaai BMPString ::= {0, 0, 21, 126}

-- canadianSyllabicsQi BMPString ::= {0, 0, 21, 127}

-- canadianSyllabicsQii BMPString ::= {0, 0, 21, 128}

-- canadianSyllabicsQo BMPString ::= {0, 0, 21, 129}

-- canadianSyllabicsQoo BMPString ::= {0, 0, 21, 130}

-- canadianSyllabicsQa BMPString ::= {0, 0, 21, 131}

-- canadianSyllabicsQaa BMPString ::= {0, 0, 21, 132}

-- canadianSyllabicsQ BMPString ::= {0, 0, 21, 133}

-- canadianSyllabicsTlhe BMPString ::= {0, 0, 21, 134}

-- canadianSyllabicsTlhi BMPString ::= {0, 0, 21, 135}

-- canadianSyllabicsTlho BMPString ::= {0, 0, 21, 136}

-- canadianSyllabicsTlha BMPString ::= {0, 0, 21, 137}

-- canadianSyllabicsWest-creeRe BMPString ::= {0, 0, 21, 138}

-- canadianSyllabicsWest-creeRi BMPString ::= {0, 0, 21, 139}

-- canadianSyllabicsWest-creeRo BMPString ::= {0, 0, 21, 140}

-- canadianSyllabicsWest-creeRa BMPString ::= {0, 0, 21, 141}

-- canadianSyllabicsNgaai BMPString ::= {0, 0, 21, 142}

-- canadianSyllabicsNgi BMPString ::= {0, 0, 21, 143}

-- canadianSyllabicsNgii BMPString ::= {0, 0, 21, 144}

-- canadianSyllabicsNgo BMPString ::= {0, 0, 21, 145}

-- canadianSyllabicsNgoo BMPString ::= {0, 0, 21, 146}

-- canadianSyllabicsNga BMPString ::= {0, 0, 21, 147}

-- canadianSyllabicsNgaa BMPString ::= {0, 0, 21, 148}

-- canadianSyllabicsNg BMPString ::= {0, 0, 21, 149}

-- canadianSyllabicsNng BMPString ::= {0, 0, 21, 150}

-- canadianSyllabicsSayisiShe BMPString ::= {0, 0, 21, 151}

-- canadianSyllabicsSayisiShi BMPString ::= {0, 0, 21, 152}

-- canadianSyllabicsSayisiSho BMPString ::= {0, 0, 21, 153}

-- canadianSyllabicsSayisiSha BMPString ::= {0, 0, 21, 154}

-- canadianSyllabicsWoods-creeThe BMPString ::= {0, 0, 21, 155}

-- canadianSyllabicsWoods-creeThi BMPString ::= {0, 0, 21, 156}

-- canadianSyllabicsWoods-creeTho BMPString ::= {0, 0, 21, 157}

-- canadianSyllabicsWoods-creeTha BMPString ::= {0, 0, 21, 158}

-- canadianSyllabicsWoods-creeTh BMPString ::= {0, 0, 21, 159}

-- canadianSyllabicsLhi BMPString ::= {0, 0, 21, 160}

-- canadianSyllabicsLhii BMPString ::= {0, 0, 21, 161}

-- canadianSyllabicsLho BMPString ::= {0, 0, 21, 162}

-- canadianSyllabicsLhoo BMPString ::= {0, 0, 21, 163}

-- canadianSyllabicsLha BMPString ::= {0, 0, 21, 164}

-- canadianSyllabicsLhaa BMPString ::= {0, 0, 21, 165}

-- canadianSyllabicsLh BMPString ::= {0, 0, 21, 166}

-- canadianSyllabicsTh-creeThe BMPString ::= {0, 0, 21, 167}

-- canadianSyllabicsTh-creeThi BMPString ::= {0, 0, 21, 168}

-- canadianSyllabicsTh-creeThii BMPString ::= {0, 0, 21, 169}

-- canadianSyllabicsTh-creeTho BMPString ::= {0, 0, 21, 170}

-- canadianSyllabicsTh-creeThoo BMPString ::= {0, 0, 21, 171}

-- canadianSyllabicsTh-creeTha BMPString ::= {0, 0, 21, 172}

-- canadianSyllabicsTh-creeThaa BMPString ::= {0, 0, 21, 173}

-- canadianSyllabicsTh-creeTh BMPString ::= {0, 0, 21, 174}

-- canadianSyllabicsAivilikB BMPString ::= {0, 0, 21, 175}

-- canadianSyllabicsBlackfootE BMPString ::= {0, 0, 21, 176}

-- canadianSyllabicsBlackfootI BMPString ::= {0, 0, 21, 177}

-- canadianSyllabicsBlackfootO BMPString ::= {0, 0, 21, 178}

-- canadianSyllabicsBlackfootA BMPString ::= {0, 0, 21, 179}

-- canadianSyllabicsBlackfootWe BMPString ::= {0, 0, 21, 180}

-- canadianSyllabicsBlackfootWi BMPString ::= {0, 0, 21, 181}

-- canadianSyllabicsBlackfootWo BMPString ::= {0, 0, 21, 182}

-- canadianSyllabicsBlackfootWa BMPString ::= {0, 0, 21, 183}

-- canadianSyllabicsBlackfootNe BMPString ::= {0, 0, 21, 184}

-- canadianSyllabicsBlackfootNi BMPString ::= {0, 0, 21, 185}

-- canadianSyllabicsBlackfootNo BMPString ::= {0, 0, 21, 186}

-- canadianSyllabicsBlackfootNa BMPString ::= {0, 0, 21, 187}

-- canadianSyllabicsBlackfootKe BMPString ::= {0, 0, 21, 188}

-- canadianSyllabicsBlackfootKi BMPString ::= {0, 0, 21, 189}

-- canadianSyllabicsBlackfootKo BMPString ::= {0, 0, 21, 190}

-- canadianSyllabicsBlackfootKa BMPString ::= {0, 0, 21, 191}

-- canadianSyllabicsSayisiHe BMPString ::= {0, 0, 21, 192}

-- canadianSyllabicsSayisiHi BMPString ::= {0, 0, 21, 193}

-- canadianSyllabicsSayisiHo BMPString ::= {0, 0, 21, 194}

-- canadianSyllabicsSayisiHa BMPString ::= {0, 0, 21, 195}

-- canadianSyllabicsCarrierGhu BMPString ::= {0, 0, 21, 196}

-- canadianSyllabicsCarrierGho BMPString ::= {0, 0, 21, 197}

-- canadianSyllabicsCarrierGhe BMPString ::= {0, 0, 21, 198}

-- canadianSyllabicsCarrierGhee BMPString ::= {0, 0, 21, 199}

-- canadianSyllabicsCarrierGhi BMPString ::= {0, 0, 21, 200}

-- canadianSyllabicsCarrierGha BMPString ::= {0, 0, 21, 201}

-- canadianSyllabicsCarrierRu BMPString ::= {0, 0, 21, 202}

-- canadianSyllabicsCarrierRo BMPString ::= {0, 0, 21, 203}

-- canadianSyllabicsCarrierRe BMPString ::= {0, 0, 21, 204}

-- canadianSyllabicsCarrierRee BMPString ::= {0, 0, 21, 205}

-- canadianSyllabicsCarrierRi BMPString ::= {0, 0, 21, 206}

-- canadianSyllabicsCarrierRa BMPString ::= {0, 0, 21, 207}

-- canadianSyllabicsCarrierWu BMPString ::= {0, 0, 21, 208}

-- canadianSyllabicsCarrierWo BMPString ::= {0, 0, 21, 209}

-- canadianSyllabicsCarrierWe BMPString ::= {0, 0, 21, 210}

-- canadianSyllabicsCarrierWee BMPString ::= {0, 0, 21, 211}

-- canadianSyllabicsCarrierWi BMPString ::= {0, 0, 21, 212}

-- canadianSyllabicsCarrierWa BMPString ::= {0, 0, 21, 213}

-- canadianSyllabicsCarrierHwu BMPString ::= {0, 0, 21, 214}

-- canadianSyllabicsCarrierHwo BMPString ::= {0, 0, 21, 215}

-- canadianSyllabicsCarrierHwe BMPString ::= {0, 0, 21, 216}

-- canadianSyllabicsCarrierHwee BMPString ::= {0, 0, 21, 217}

-- canadianSyllabicsCarrierHwi BMPString ::= {0, 0, 21, 218}

-- canadianSyllabicsCarrierHwa BMPString ::= {0, 0, 21, 219}

-- canadianSyllabicsCarrierThu BMPString ::= {0, 0, 21, 220}

-- canadianSyllabicsCarrierTho BMPString ::= {0, 0, 21, 221}

-- canadianSyllabicsCarrierThe BMPString ::= {0, 0, 21, 222}

-- canadianSyllabicsCarrierThee BMPString ::= {0, 0, 21, 223}

-- canadianSyllabicsCarrierThi BMPString ::= {0, 0, 21, 224}

-- canadianSyllabicsCarrierTha BMPString ::= {0, 0, 21, 225}

-- canadianSyllabicsCarrierTtu BMPString ::= {0, 0, 21, 226}

-- canadianSyllabicsCarrierTto BMPString ::= {0, 0, 21, 227}

-- canadianSyllabicsCarrierTte BMPString ::= {0, 0, 21, 228}

-- canadianSyllabicsCarrierTtee BMPString ::= {0, 0, 21, 229}

-- canadianSyllabicsCarrierTti BMPString ::= {0, 0, 21, 230}

-- canadianSyllabicsCarrierTta BMPString ::= {0, 0, 21, 231}

-- canadianSyllabicsCarrierPu BMPString ::= {0, 0, 21, 232}

-- canadianSyllabicsCarrierPo BMPString ::= {0, 0, 21, 233}

-- canadianSyllabicsCarrierPe BMPString ::= {0, 0, 21, 234}

-- canadianSyllabicsCarrierPee BMPString ::= {0, 0, 21, 235}

-- canadianSyllabicsCarrierPi BMPString ::= {0, 0, 21, 236}

-- canadianSyllabicsCarrierPa BMPString ::= {0, 0, 21, 237}

-- canadianSyllabicsCarrierP BMPString ::= {0, 0, 21, 238}

-- canadianSyllabicsCarrierGu BMPString ::= {0, 0, 21, 239}

-- canadianSyllabicsCarrierGo BMPString ::= {0, 0, 21, 240}

-- canadianSyllabicsCarrierGe BMPString ::= {0, 0, 21, 241}

-- canadianSyllabicsCarrierGee BMPString ::= {0, 0, 21, 242}

-- canadianSyllabicsCarrierGi BMPString ::= {0, 0, 21, 243}

-- canadianSyllabicsCarrierGa BMPString ::= {0, 0, 21, 244}

-- canadianSyllabicsCarrierKhu BMPString ::= {0, 0, 21, 245}

-- canadianSyllabicsCarrierKho BMPString ::= {0, 0, 21, 246}

-- canadianSyllabicsCarrierKhe BMPString ::= {0, 0, 21, 247}

-- canadianSyllabicsCarrierKhee BMPString ::= {0, 0, 21, 248}

-- canadianSyllabicsCarrierKhi BMPString ::= {0, 0, 21, 249}

-- canadianSyllabicsCarrierKha BMPString ::= {0, 0, 21, 250}

-- canadianSyllabicsCarrierKku BMPString ::= {0, 0, 21, 251}

-- canadianSyllabicsCarrierKko BMPString ::= {0, 0, 21, 252}

-- canadianSyllabicsCarrierKke BMPString ::= {0, 0, 21, 253}

-- canadianSyllabicsCarrierKkee BMPString ::= {0, 0, 21, 254}

-- canadianSyllabicsCarrierKki BMPString ::= {0, 0, 21, 255}

-- canadianSyllabicsCarrierKka BMPString ::= {0, 0, 22, 0}

-- canadianSyllabicsCarrierKk BMPString ::= {0, 0, 22, 1}

-- canadianSyllabicsCarrierNu BMPString ::= {0, 0, 22, 2}

-- canadianSyllabicsCarrierNo BMPString ::= {0, 0, 22, 3}

-- canadianSyllabicsCarrierNe BMPString ::= {0, 0, 22, 4}

-- canadianSyllabicsCarrierNee BMPString ::= {0, 0, 22, 5}

-- canadianSyllabicsCarrierNi BMPString ::= {0, 0, 22, 6}

-- canadianSyllabicsCarrierNa BMPString ::= {0, 0, 22, 7}

-- canadianSyllabicsCarrierMu BMPString ::= {0, 0, 22, 8}

-- canadianSyllabicsCarrierMo BMPString ::= {0, 0, 22, 9}

-- canadianSyllabicsCarrierMe BMPString ::= {0, 0, 22, 10}

-- canadianSyllabicsCarrierMee BMPString ::= {0, 0, 22, 11}

-- canadianSyllabicsCarrierMi BMPString ::= {0, 0, 22, 12}

-- canadianSyllabicsCarrierMa BMPString ::= {0, 0, 22, 13}

-- canadianSyllabicsCarrierYu BMPString ::= {0, 0, 22, 14}

-- canadianSyllabicsCarrierYo BMPString ::= {0, 0, 22, 15}

-- canadianSyllabicsCarrierYe BMPString ::= {0, 0, 22, 16}

-- canadianSyllabicsCarrierYee BMPString ::= {0, 0, 22, 17}

-- canadianSyllabicsCarrierYi BMPString ::= {0, 0, 22, 18}

-- canadianSyllabicsCarrierYa BMPString ::= {0, 0, 22, 19}

-- canadianSyllabicsCarrierJu BMPString ::= {0, 0, 22, 20}

-- canadianSyllabicsSayisiJu BMPString ::= {0, 0, 22, 21}

-- canadianSyllabicsCarrierJo BMPString ::= {0, 0, 22, 22}

-- canadianSyllabicsCarrierJe BMPString ::= {0, 0, 22, 23}

-- canadianSyllabicsCarrierJee BMPString ::= {0, 0, 22, 24}

-- canadianSyllabicsCarrierJi BMPString ::= {0, 0, 22, 25}

-- canadianSyllabicsSayisiJi BMPString ::= {0, 0, 22, 26}

-- canadianSyllabicsCarrierJa BMPString ::= {0, 0, 22, 27}

-- canadianSyllabicsCarrierJju BMPString ::= {0, 0, 22, 28}

-- canadianSyllabicsCarrierJjo BMPString ::= {0, 0, 22, 29}

-- canadianSyllabicsCarrierJje BMPString ::= {0, 0, 22, 30}

-- canadianSyllabicsCarrierJjee BMPString ::= {0, 0, 22, 31}

-- canadianSyllabicsCarrierJji BMPString ::= {0, 0, 22, 32}

-- canadianSyllabicsCarrierJja BMPString ::= {0, 0, 22, 33}

-- canadianSyllabicsCarrierLu BMPString ::= {0, 0, 22, 34}

-- canadianSyllabicsCarrierLo BMPString ::= {0, 0, 22, 35}

-- canadianSyllabicsCarrierLe BMPString ::= {0, 0, 22, 36}

-- canadianSyllabicsCarrierLee BMPString ::= {0, 0, 22, 37}

-- canadianSyllabicsCarrierLi BMPString ::= {0, 0, 22, 38}

-- canadianSyllabicsCarrierLa BMPString ::= {0, 0, 22, 39}

-- canadianSyllabicsCarrierDlu BMPString ::= {0, 0, 22, 40}

-- canadianSyllabicsCarrierDlo BMPString ::= {0, 0, 22, 41}

-- canadianSyllabicsCarrierDle BMPString ::= {0, 0, 22, 42}

-- canadianSyllabicsCarrierDlee BMPString ::= {0, 0, 22, 43}

-- canadianSyllabicsCarrierDli BMPString ::= {0, 0, 22, 44}

-- canadianSyllabicsCarrierDla BMPString ::= {0, 0, 22, 45}

-- canadianSyllabicsCarrierLhu BMPString ::= {0, 0, 22, 46}

-- canadianSyllabicsCarrierLho BMPString ::= {0, 0, 22, 47}

-- canadianSyllabicsCarrierLhe BMPString ::= {0, 0, 22, 48}

-- canadianSyllabicsCarrierLhee BMPString ::= {0, 0, 22, 49}

-- canadianSyllabicsCarrierLhi BMPString ::= {0, 0, 22, 50}

-- canadianSyllabicsCarrierLha BMPString ::= {0, 0, 22, 51}

-- canadianSyllabicsCarrierTlhu BMPString ::= {0, 0, 22, 52}

-- canadianSyllabicsCarrierTlho BMPString ::= {0, 0, 22, 53}

-- canadianSyllabicsCarrierTlhe BMPString ::= {0, 0, 22, 54}

-- canadianSyllabicsCarrierTlhee BMPString ::= {0, 0, 22, 55}

-- canadianSyllabicsCarrierTlhi BMPString ::= {0, 0, 22, 56}

-- canadianSyllabicsCarrierTlha BMPString ::= {0, 0, 22, 57}

-- canadianSyllabicsCarrierTlu BMPString ::= {0, 0, 22, 58}

-- canadianSyllabicsCarrierTlo BMPString ::= {0, 0, 22, 59}

-- canadianSyllabicsCarrierTle BMPString ::= {0, 0, 22, 60}

-- canadianSyllabicsCarrierTlee BMPString ::= {0, 0, 22, 61}

-- canadianSyllabicsCarrierTli BMPString ::= {0, 0, 22, 62}

-- canadianSyllabicsCarrierTla BMPString ::= {0, 0, 22, 63}

-- canadianSyllabicsCarrierZu BMPString ::= {0, 0, 22, 64}

-- canadianSyllabicsCarrierZo BMPString ::= {0, 0, 22, 65}

-- canadianSyllabicsCarrierZe BMPString ::= {0, 0, 22, 66}

-- canadianSyllabicsCarrierZee BMPString ::= {0, 0, 22, 67}

-- canadianSyllabicsCarrierZi BMPString ::= {0, 0, 22, 68}

-- canadianSyllabicsCarrierZa BMPString ::= {0, 0, 22, 69}

-- canadianSyllabicsCarrierZ BMPString ::= {0, 0, 22, 70}

-- canadianSyllabicsCarrierInitialZ BMPString ::= {0, 0, 22, 71}

-- canadianSyllabicsCarrierDzu BMPString ::= {0, 0, 22, 72}

-- canadianSyllabicsCarrierDzo BMPString ::= {0, 0, 22, 73}

-- canadianSyllabicsCarrierDze BMPString ::= {0, 0, 22, 74}

-- canadianSyllabicsCarrierDzee BMPString ::= {0, 0, 22, 75}

-- canadianSyllabicsCarrierDzi BMPString ::= {0, 0, 22, 76}

-- canadianSyllabicsCarrierDza BMPString ::= {0, 0, 22, 77}

-- canadianSyllabicsCarrierSu BMPString ::= {0, 0, 22, 78}

-- canadianSyllabicsCarrierSo BMPString ::= {0, 0, 22, 79}

-- canadianSyllabicsCarrierSe BMPString ::= {0, 0, 22, 80}

-- canadianSyllabicsCarrierSee BMPString ::= {0, 0, 22, 81}

-- canadianSyllabicsCarrierSi BMPString ::= {0, 0, 22, 82}

-- canadianSyllabicsCarrierSa BMPString ::= {0, 0, 22, 83}

-- canadianSyllabicsCarrierShu BMPString ::= {0, 0, 22, 84}

-- canadianSyllabicsCarrierSho BMPString ::= {0, 0, 22, 85}

-- canadianSyllabicsCarrierShe BMPString ::= {0, 0, 22, 86}

-- canadianSyllabicsCarrierShee BMPString ::= {0, 0, 22, 87}

-- canadianSyllabicsCarrierShi BMPString ::= {0, 0, 22, 88}

-- canadianSyllabicsCarrierSha BMPString ::= {0, 0, 22, 89}

-- canadianSyllabicsCarrierSh BMPString ::= {0, 0, 22, 90}

-- canadianSyllabicsCarrierTsu BMPString ::= {0, 0, 22, 91}

-- canadianSyllabicsCarrierTso BMPString ::= {0, 0, 22, 92}

-- canadianSyllabicsCarrierTse BMPString ::= {0, 0, 22, 93}

-- canadianSyllabicsCarrierTsee BMPString ::= {0, 0, 22, 94}

-- canadianSyllabicsCarrierTsi BMPString ::= {0, 0, 22, 95}

-- canadianSyllabicsCarrierTsa BMPString ::= {0, 0, 22, 96}

-- canadianSyllabicsCarrierChu BMPString ::= {0, 0, 22, 97}

-- canadianSyllabicsCarrierCho BMPString ::= {0, 0, 22, 98}

-- canadianSyllabicsCarrierChe BMPString ::= {0, 0, 22, 99}

-- canadianSyllabicsCarrierChee BMPString ::= {0, 0, 22, 100}

-- canadianSyllabicsCarrierChi BMPString ::= {0, 0, 22, 101}

-- canadianSyllabicsCarrierCha BMPString ::= {0, 0, 22, 102}

-- canadianSyllabicsCarrierTtsu BMPString ::= {0, 0, 22, 103}

-- canadianSyllabicsCarrierTtso BMPString ::= {0, 0, 22, 104}

-- canadianSyllabicsCarrierTtse BMPString ::= {0, 0, 22, 105}

-- canadianSyllabicsCarrierTtsee BMPString ::= {0, 0, 22, 106}

-- canadianSyllabicsCarrierTtsi BMPString ::= {0, 0, 22, 107}

-- canadianSyllabicsCarrierTtsa BMPString ::= {0, 0, 22, 108}

-- canadianSyllabicsChiSign BMPString ::= {0, 0, 22, 109}

-- canadianSyllabicsFullStop BMPString ::= {0, 0, 22, 110}

-- canadianSyllabicsQai BMPString ::= {0, 0, 22, 111}

-- canadianSyllabicsNgai BMPString ::= {0, 0, 22, 112}

-- canadianSyllabicsNngi BMPString ::= {0, 0, 22, 113}

-- canadianSyllabicsNngii BMPString ::= {0, 0, 22, 114}

-- canadianSyllabicsNngo BMPString ::= {0, 0, 22, 115}

-- canadianSyllabicsNngoo BMPString ::= {0, 0, 22, 116}

-- canadianSyllabicsNnga BMPString ::= {0, 0, 22, 117}

-- canadianSyllabicsNngaa BMPString ::= {0, 0, 22, 118}

-- oghamSpaceMark BMPString ::= {0, 0, 22, 128}

-- oghamLetterBeith BMPString ::= {0, 0, 22, 129}

-- oghamLetterLuis BMPString ::= {0, 0, 22, 130}

-- oghamLetterFearn BMPString ::= {0, 0, 22, 131}

-- oghamLetterSail BMPString ::= {0, 0, 22, 132}

-- oghamLetterNion BMPString ::= {0, 0, 22, 133}

-- oghamLetterUath BMPString ::= {0, 0, 22, 134}

-- oghamLetterDair BMPString ::= {0, 0, 22, 135}

-- oghamLetterTinne BMPString ::= {0, 0, 22, 136}

-- oghamLetterColl BMPString ::= {0, 0, 22, 137}

-- oghamLetterCeirt BMPString ::= {0, 0, 22, 138}

-- oghamLetterMuin BMPString ::= {0, 0, 22, 139}

-- oghamLetterGort BMPString ::= {0, 0, 22, 140}

-- oghamLetterNgeadal BMPString ::= {0, 0, 22, 141}

-- oghamLetterStraif BMPString ::= {0, 0, 22, 142}

-- oghamLetterRuis BMPString ::= {0, 0, 22, 143}

-- oghamLetterAilm BMPString ::= {0, 0, 22, 144}

-- oghamLetterOnn BMPString ::= {0, 0, 22, 145}

-- oghamLetterUr BMPString ::= {0, 0, 22, 146}

-- oghamLetterEadhadh BMPString ::= {0, 0, 22, 147}

-- oghamLetterIodhadh BMPString ::= {0, 0, 22, 148}

-- oghamLetterEabhadh BMPString ::= {0, 0, 22, 149}

-- oghamLetterOr BMPString ::= {0, 0, 22, 150}

-- oghamLetterUilleann BMPString ::= {0, 0, 22, 151}

-- oghamLetterIfin BMPString ::= {0, 0, 22, 152}

-- oghamLetterEamhancholl BMPString ::= {0, 0, 22, 153}

-- oghamLetterPeith BMPString ::= {0, 0, 22, 154}

-- oghamFeatherMark BMPString ::= {0, 0, 22, 155}

-- oghamReversedFeatherMark BMPString ::= {0, 0, 22, 156}

-- runicLetterFehuFeohFeF BMPString ::= {0, 0, 22, 160}

-- runicLetterV BMPString ::= {0, 0, 22, 161}

-- runicLetterUruzUrU BMPString ::= {0, 0, 22, 162}

-- runicLetterYr BMPString ::= {0, 0, 22, 163}

-- runicLetterY BMPString ::= {0, 0, 22, 164}

-- runicLetterW BMPString ::= {0, 0, 22, 165}

-- runicLetterThurisazThursThorn BMPString ::= {0, 0, 22, 166}

-- runicLetterEth BMPString ::= {0, 0, 22, 167}

-- runicLetterAnsuzA BMPString ::= {0, 0, 22, 168}

-- runicLetterOsO BMPString ::= {0, 0, 22, 169}

-- runicLetterAcA BMPString ::= {0, 0, 22, 170}

-- runicLetterAesc BMPString ::= {0, 0, 22, 171}

-- runicLetterLong-branch-ossO BMPString ::= {0, 0, 22, 172}

-- runicLetterShort-twig-ossO BMPString ::= {0, 0, 22, 173}

-- runicLetterO BMPString ::= {0, 0, 22, 174}

-- runicLetterOe BMPString ::= {0, 0, 22, 175}

-- runicLetterOn BMPString ::= {0, 0, 22, 176}

-- runicLetterRaidoRadReidR BMPString ::= {0, 0, 22, 177}

-- runicLetterKauna BMPString ::= {0, 0, 22, 178}

-- runicLetterCen BMPString ::= {0, 0, 22, 179}

-- runicLetterKaunK BMPString ::= {0, 0, 22, 180}

-- runicLetterG BMPString ::= {0, 0, 22, 181}

-- runicLetterEng BMPString ::= {0, 0, 22, 182}

-- runicLetterGeboGyfuG BMPString ::= {0, 0, 22, 183}

-- runicLetterGar BMPString ::= {0, 0, 22, 184}

-- runicLetterWunjoWynnW BMPString ::= {0, 0, 22, 185}

-- runicLetterHaglazH BMPString ::= {0, 0, 22, 186}

-- runicLetterHaeglH BMPString ::= {0, 0, 22, 187}

-- runicLetterLong-branch-hagallH BMPString ::= {0, 0, 22, 188}

-- runicLetterShort-twig-hagallH BMPString ::= {0, 0, 22, 189}

-- runicLetterNaudizNydNaudN BMPString ::= {0, 0, 22, 190}

-- runicLetterShort-twig-naudN BMPString ::= {0, 0, 22, 191}

-- runicLetterDotted-n BMPString ::= {0, 0, 22, 192}

-- runicLetterIsazIsIssI BMPString ::= {0, 0, 22, 193}

-- runicLetterE BMPString ::= {0, 0, 22, 194}

-- runicLetterJeranJ BMPString ::= {0, 0, 22, 195}

-- runicLetterGer BMPString ::= {0, 0, 22, 196}

-- runicLetterLong-branch-arAe BMPString ::= {0, 0, 22, 197}

-- runicLetterShort-twig-arA BMPString ::= {0, 0, 22, 198}

-- runicLetterIwazEoh BMPString ::= {0, 0, 22, 199}

-- runicLetterPerthoPeorthP BMPString ::= {0, 0, 22, 200}

-- runicLetterAlgizEolhx BMPString ::= {0, 0, 22, 201}

-- runicLetterSowiloS BMPString ::= {0, 0, 22, 202}

-- runicLetterSigelLong-branch-solS BMPString ::= {0, 0, 22, 203}

-- runicLetterShort-twig-solS BMPString ::= {0, 0, 22, 204}

-- runicLetterC BMPString ::= {0, 0, 22, 205}

-- runicLetterZ BMPString ::= {0, 0, 22, 206}

-- runicLetterTiwazTirTyrT BMPString ::= {0, 0, 22, 207}

-- runicLetterShort-twig-tyrT BMPString ::= {0, 0, 22, 208}

-- runicLetterD BMPString ::= {0, 0, 22, 209}

-- runicLetterBerkananBeorcBjarkanB BMPString ::= {0, 0, 22, 210}

-- runicLetterShort-twig-bjarkanB BMPString ::= {0, 0, 22, 211}

-- runicLetterDotted-p BMPString ::= {0, 0, 22, 212}

-- runicLetterOpen-p BMPString ::= {0, 0, 22, 213}

-- runicLetterEhwazEhE BMPString ::= {0, 0, 22, 214}

-- runicLetterMannazManM BMPString ::= {0, 0, 22, 215}

-- runicLetterLong-branch-madrM BMPString ::= {0, 0, 22, 216}

-- runicLetterShort-twig-madrM BMPString ::= {0, 0, 22, 217}

-- runicLetterLaukazLaguLogrL BMPString ::= {0, 0, 22, 218}

-- runicLetterDotted-l BMPString ::= {0, 0, 22, 219}

-- runicLetterIngwaz BMPString ::= {0, 0, 22, 220}

-- runicLetterIng BMPString ::= {0, 0, 22, 221}

-- runicLetterDagazDaegD BMPString ::= {0, 0, 22, 222}

-- runicLetterOthalanEthelO BMPString ::= {0, 0, 22, 223}

-- runicLetterEar BMPString ::= {0, 0, 22, 224}

-- runicLetterIor BMPString ::= {0, 0, 22, 225}

-- runicLetterCweorth BMPString ::= {0, 0, 22, 226}

-- runicLetterCalc BMPString ::= {0, 0, 22, 227}

-- runicLetterCealc BMPString ::= {0, 0, 22, 228}

-- runicLetterStan BMPString ::= {0, 0, 22, 229}

-- runicLetterLong-branch-yr BMPString ::= {0, 0, 22, 230}

-- runicLetterShort-twig-yr BMPString ::= {0, 0, 22, 231}

-- runicLetterIcelandic-yr BMPString ::= {0, 0, 22, 232}

-- runicLetterQ BMPString ::= {0, 0, 22, 233}

-- runicLetterX BMPString ::= {0, 0, 22, 234}

-- runicSinglePunctuation BMPString ::= {0, 0, 22, 235}

-- runicMultiplePunctuation BMPString ::= {0, 0, 22, 236}

-- runicCrossPunctuation BMPString ::= {0, 0, 22, 237}

-- runicArlaugSymbol BMPString ::= {0, 0, 22, 238}

-- runicTvimadurSymbol BMPString ::= {0, 0, 22, 239}

-- runicBelgthorSymbol BMPString ::= {0, 0, 22, 240}

-- tagalogLetterA BMPString ::= {0, 0, 23, 0}

-- tagalogLetterI BMPString ::= {0, 0, 23, 1}

-- tagalogLetterU BMPString ::= {0, 0, 23, 2}

-- tagalogLetterKa BMPString ::= {0, 0, 23, 3}

-- tagalogLetterGa BMPString ::= {0, 0, 23, 4}

-- tagalogLetterNga BMPString ::= {0, 0, 23, 5}

-- tagalogLetterTa BMPString ::= {0, 0, 23, 6}

-- tagalogLetterDa BMPString ::= {0, 0, 23, 7}

-- tagalogLetterNa BMPString ::= {0, 0, 23, 8}

-- tagalogLetterPa BMPString ::= {0, 0, 23, 9}

-- tagalogLetterBa BMPString ::= {0, 0, 23, 10}

-- tagalogLetterMa BMPString ::= {0, 0, 23, 11}

-- tagalogLetterYa BMPString ::= {0, 0, 23, 12}

-- tagalogLetterLa BMPString ::= {0, 0, 23, 14}

-- tagalogLetterWa BMPString ::= {0, 0, 23, 15}

-- tagalogLetterSa BMPString ::= {0, 0, 23, 16}

-- tagalogLetterHa BMPString ::= {0, 0, 23, 17}

-- tagalogVowelSignI BMPString ::= {0, 0, 23, 18}

-- tagalogVowelSignU BMPString ::= {0, 0, 23, 19}

-- tagalogSignVirama BMPString ::= {0, 0, 23, 20}

-- hanunooLetterA BMPString ::= {0, 0, 23, 32}

-- hanunooLetterI BMPString ::= {0, 0, 23, 33}

-- hanunooLetterU BMPString ::= {0, 0, 23, 34}

-- hanunooLetterKa BMPString ::= {0, 0, 23, 35}

-- hanunooLetterGa BMPString ::= {0, 0, 23, 36}

-- hanunooLetterNga BMPString ::= {0, 0, 23, 37}

-- hanunooLetterTa BMPString ::= {0, 0, 23, 38}

-- hanunooLetterDa BMPString ::= {0, 0, 23, 39}

-- hanunooLetterNa BMPString ::= {0, 0, 23, 40}

-- hanunooLetterPa BMPString ::= {0, 0, 23, 41}

-- hanunooLetterBa BMPString ::= {0, 0, 23, 42}

-- hanunooLetterMa BMPString ::= {0, 0, 23, 43}

-- hanunooLetterYa BMPString ::= {0, 0, 23, 44}

-- hanunooLetterRa BMPString ::= {0, 0, 23, 45}

-- hanunooLetterLa BMPString ::= {0, 0, 23, 46}

-- hanunooLetterWa BMPString ::= {0, 0, 23, 47}

-- hanunooLetterSa BMPString ::= {0, 0, 23, 48}

-- hanunooLetterHa BMPString ::= {0, 0, 23, 49}

-- hanunooVowelSignI BMPString ::= {0, 0, 23, 50}

-- hanunooVowelSignU BMPString ::= {0, 0, 23, 51}

-- hanunooSignPamudpod BMPString ::= {0, 0, 23, 52}

-- philippineSinglePunctuation BMPString ::= {0, 0, 23, 53}

-- philippineDoublePunctuation BMPString ::= {0, 0, 23, 54}

-- buhidLetterA BMPString ::= {0, 0, 23, 64}

-- buhidLetterI BMPString ::= {0, 0, 23, 65}

-- buhidLetterU BMPString ::= {0, 0, 23, 66}

-- buhidLetterKa BMPString ::= {0, 0, 23, 67}

-- buhidLetterGa BMPString ::= {0, 0, 23, 68}

-- buhidLetterNga BMPString ::= {0, 0, 23, 69}

-- buhidLetterTa BMPString ::= {0, 0, 23, 70}

-- buhidLetterDa BMPString ::= {0, 0, 23, 71}

-- buhidLetterNa BMPString ::= {0, 0, 23, 72}

-- buhidLetterPa BMPString ::= {0, 0, 23, 73}

-- buhidLetterBa BMPString ::= {0, 0, 23, 74}

-- buhidLetterMa BMPString ::= {0, 0, 23, 75}

-- buhidLetterYa BMPString ::= {0, 0, 23, 76}

-- buhidLetterRa BMPString ::= {0, 0, 23, 77}

-- buhidLetterLa BMPString ::= {0, 0, 23, 78}

-- buhidLetterWa BMPString ::= {0, 0, 23, 79}

-- buhidLetterSa BMPString ::= {0, 0, 23, 80}

-- buhidLetterHa BMPString ::= {0, 0, 23, 81}

-- buhidVowelSignI BMPString ::= {0, 0, 23, 82}

-- buhidVowelSignU BMPString ::= {0, 0, 23, 83}

-- tagbanwaLetterA BMPString ::= {0, 0, 23, 96}

-- tagbanwaLetterI BMPString ::= {0, 0, 23, 97}

-- tagbanwaLetterU BMPString ::= {0, 0, 23, 98}

-- tagbanwaLetterKa BMPString ::= {0, 0, 23, 99}

-- tagbanwaLetterGa BMPString ::= {0, 0, 23, 100}

-- tagbanwaLetterNga BMPString ::= {0, 0, 23, 101}

-- tagbanwaLetterTa BMPString ::= {0, 0, 23, 102}

-- tagbanwaLetterDa BMPString ::= {0, 0, 23, 103}

-- tagbanwaLetterNa BMPString ::= {0, 0, 23, 104}

-- tagbanwaLetterPa BMPString ::= {0, 0, 23, 105}

-- tagbanwaLetterBa BMPString ::= {0, 0, 23, 106}

-- tagbanwaLetterMa BMPString ::= {0, 0, 23, 107}

-- tagbanwaLetterYa BMPString ::= {0, 0, 23, 108}

-- tagbanwaLetterLa BMPString ::= {0, 0, 23, 110}

-- tagbanwaLetterWa BMPString ::= {0, 0, 23, 111}

-- tagbanwaLetterSa BMPString ::= {0, 0, 23, 112}

-- tagbanwaVowelSignI BMPString ::= {0, 0, 23, 114}

-- tagbanwaVowelSignU BMPString ::= {0, 0, 23, 115}

-- khmerLetterKa BMPString ::= {0, 0, 23, 128}

-- khmerLetterKha BMPString ::= {0, 0, 23, 129}

-- khmerLetterKo BMPString ::= {0, 0, 23, 130}

-- khmerLetterKho BMPString ::= {0, 0, 23, 131}

-- khmerLetterNgo BMPString ::= {0, 0, 23, 132}

-- khmerLetterCa BMPString ::= {0, 0, 23, 133}

-- khmerLetterCha BMPString ::= {0, 0, 23, 134}

-- khmerLetterCo BMPString ::= {0, 0, 23, 135}

-- khmerLetterCho BMPString ::= {0, 0, 23, 136}

-- khmerLetterNyo BMPString ::= {0, 0, 23, 137}

-- khmerLetterDa BMPString ::= {0, 0, 23, 138}

-- khmerLetterTtha BMPString ::= {0, 0, 23, 139}

-- khmerLetterDo BMPString ::= {0, 0, 23, 140}

-- khmerLetterTtho BMPString ::= {0, 0, 23, 141}

-- khmerLetterNno BMPString ::= {0, 0, 23, 142}

-- khmerLetterTa BMPString ::= {0, 0, 23, 143}

-- khmerLetterTha BMPString ::= {0, 0, 23, 144}

-- khmerLetterTo BMPString ::= {0, 0, 23, 145}

-- khmerLetterTho BMPString ::= {0, 0, 23, 146}

-- khmerLetterNo BMPString ::= {0, 0, 23, 147}

-- khmerLetterBa BMPString ::= {0, 0, 23, 148}

-- khmerLetterPha BMPString ::= {0, 0, 23, 149}

-- khmerLetterPo BMPString ::= {0, 0, 23, 150}

-- khmerLetterPho BMPString ::= {0, 0, 23, 151}

-- khmerLetterMo BMPString ::= {0, 0, 23, 152}

-- khmerLetterYo BMPString ::= {0, 0, 23, 153}

-- khmerLetterRo BMPString ::= {0, 0, 23, 154}

-- khmerLetterLo BMPString ::= {0, 0, 23, 155}

-- khmerLetterVo BMPString ::= {0, 0, 23, 156}

-- khmerLetterSha BMPString ::= {0, 0, 23, 157}

-- khmerLetterSso BMPString ::= {0, 0, 23, 158}

-- khmerLetterSa BMPString ::= {0, 0, 23, 159}

-- khmerLetterHa BMPString ::= {0, 0, 23, 160}

-- khmerLetterLa BMPString ::= {0, 0, 23, 161}

-- khmerLetterQa BMPString ::= {0, 0, 23, 162}

-- khmerIndependentVowelQaq BMPString ::= {0, 0, 23, 163}

-- khmerIndependentVowelQaa BMPString ::= {0, 0, 23, 164}

-- khmerIndependentVowelQi BMPString ::= {0, 0, 23, 165}

-- khmerIndependentVowelQii BMPString ::= {0, 0, 23, 166}

-- khmerIndependentVowelQu BMPString ::= {0, 0, 23, 167}

-- khmerIndependentVowelQuk BMPString ::= {0, 0, 23, 168}

-- khmerIndependentVowelQuu BMPString ::= {0, 0, 23, 169}

-- khmerIndependentVowelQuuv BMPString ::= {0, 0, 23, 170}

-- khmerIndependentVowelRy BMPString ::= {0, 0, 23, 171}

-- khmerIndependentVowelRyy BMPString ::= {0, 0, 23, 172}

-- khmerIndependentVowelLy BMPString ::= {0, 0, 23, 173}

-- khmerIndependentVowelLyy BMPString ::= {0, 0, 23, 174}

-- khmerIndependentVowelQe BMPString ::= {0, 0, 23, 175}

-- khmerIndependentVowelQai BMPString ::= {0, 0, 23, 176}

-- khmerIndependentVowelQooTypeOne BMPString ::= {0, 0, 23, 177}

-- khmerIndependentVowelQooTypeTwo BMPString ::= {0, 0, 23, 178}

-- khmerIndependentVowelQau BMPString ::= {0, 0, 23, 179}

-- khmerVowelInherentAq BMPString ::= {0, 0, 23, 180}

-- khmerVowelInherentAa BMPString ::= {0, 0, 23, 181}

-- khmerVowelSignAa BMPString ::= {0, 0, 23, 182}

-- khmerVowelSignI BMPString ::= {0, 0, 23, 183}

-- khmerVowelSignIi BMPString ::= {0, 0, 23, 184}

-- khmerVowelSignY BMPString ::= {0, 0, 23, 185}

-- khmerVowelSignYy BMPString ::= {0, 0, 23, 186}

-- khmerVowelSignU BMPString ::= {0, 0, 23, 187}

-- khmerVowelSignUu BMPString ::= {0, 0, 23, 188}

-- khmerVowelSignUa BMPString ::= {0, 0, 23, 189}

-- khmerVowelSignOe BMPString ::= {0, 0, 23, 190}

-- khmerVowelSignYa BMPString ::= {0, 0, 23, 191}

-- khmerVowelSignIe BMPString ::= {0, 0, 23, 192}

-- khmerVowelSignE BMPString ::= {0, 0, 23, 193}

-- khmerVowelSignAe BMPString ::= {0, 0, 23, 194}

-- khmerVowelSignAi BMPString ::= {0, 0, 23, 195}

-- khmerVowelSignOo BMPString ::= {0, 0, 23, 196}

-- khmerVowelSignAu BMPString ::= {0, 0, 23, 197}

-- khmerSignNikahit BMPString ::= {0, 0, 23, 198}

-- khmerSignReahmuk BMPString ::= {0, 0, 23, 199}

-- khmerSignYuukaleapintu BMPString ::= {0, 0, 23, 200}

-- khmerSignMuusikatoan BMPString ::= {0, 0, 23, 201}

-- khmerSignTriisap BMPString ::= {0, 0, 23, 202}

-- khmerSignBantoc BMPString ::= {0, 0, 23, 203}

-- khmerSignRobat BMPString ::= {0, 0, 23, 204}

-- khmerSignToandakhiat BMPString ::= {0, 0, 23, 205}

-- khmerSignKakabat BMPString ::= {0, 0, 23, 206}

-- khmerSignAhsda BMPString ::= {0, 0, 23, 207}

-- khmerSignSamyokSannya BMPString ::= {0, 0, 23, 208}

-- khmerSignViriam BMPString ::= {0, 0, 23, 209}

-- khmerSignCoeng BMPString ::= {0, 0, 23, 210}

-- khmerSignBathamasat BMPString ::= {0, 0, 23, 211}

-- khmerSignKhan BMPString ::= {0, 0, 23, 212}

-- khmerSignBariyoosan BMPString ::= {0, 0, 23, 213}

-- khmerSignCamnucPiiKuuh BMPString ::= {0, 0, 23, 214}

-- khmerSignLekToo BMPString ::= {0, 0, 23, 215}

-- khmerSignBeyyal BMPString ::= {0, 0, 23, 216}

-- khmerSignPhnaekMuan BMPString ::= {0, 0, 23, 217}

-- khmerSignKoomuut BMPString ::= {0, 0, 23, 218}

-- khmerCurrencySymbolRiel BMPString ::= {0, 0, 23, 219}

-- khmerSignAvakrahasanya BMPString ::= {0, 0, 23, 220}

-- khmerDigitZero BMPString ::= {0, 0, 23, 224}

-- khmerDigitOne BMPString ::= {0, 0, 23, 225}

-- khmerDigitTwo BMPString ::= {0, 0, 23, 226}

-- khmerDigitThree BMPString ::= {0, 0, 23, 227}

-- khmerDigitFour BMPString ::= {0, 0, 23, 228}

-- khmerDigitFive BMPString ::= {0, 0, 23, 229}

-- khmerDigitSix BMPString ::= {0, 0, 23, 230}

-- khmerDigitSeven BMPString ::= {0, 0, 23, 231}

-- khmerDigitEight BMPString ::= {0, 0, 23, 232}

-- khmerDigitNine BMPString ::= {0, 0, 23, 233}

-- mongolianBirga BMPString ::= {0, 0, 24, 0}

-- mongolianEllipsis BMPString ::= {0, 0, 24, 1}

-- mongolianComma BMPString ::= {0, 0, 24, 2}

-- mongolianFullStop BMPString ::= {0, 0, 24, 3}

-- mongolianColon BMPString ::= {0, 0, 24, 4}

-- mongolianFourDots BMPString ::= {0, 0, 24, 5}

-- mongolianTodoSoftHyphen BMPString ::= {0, 0, 24, 6}

-- mongolianSibeSyllableBoundaryMarker BMPString ::= {0, 0, 24, 7}

-- mongolianManchuComma BMPString ::= {0, 0, 24, 8}

-- mongolianManchuFullStop BMPString ::= {0, 0, 24, 9}

-- mongolianNirugu BMPString ::= {0, 0, 24, 10}

-- mongolianFreeVariationSelectorOne BMPString ::= {0, 0, 24, 11}

-- mongolianFreeVariationSelectorTwo BMPString ::= {0, 0, 24, 12}

-- mongolianFreeVariationSelectorThree BMPString ::= {0, 0, 24, 13}

-- mongolianVowelSeparator BMPString ::= {0, 0, 24, 14}

-- mongolianDigitZero BMPString ::= {0, 0, 24, 16}

-- mongolianDigitOne BMPString ::= {0, 0, 24, 17}

-- mongolianDigitTwo BMPString ::= {0, 0, 24, 18}

-- mongolianDigitThree BMPString ::= {0, 0, 24, 19}

-- mongolianDigitFour BMPString ::= {0, 0, 24, 20}

-- mongolianDigitFive BMPString ::= {0, 0, 24, 21}

-- mongolianDigitSix BMPString ::= {0, 0, 24, 22}

-- mongolianDigitSeven BMPString ::= {0, 0, 24, 23}

-- mongolianDigitEight BMPString ::= {0, 0, 24, 24}

-- mongolianDigitNine BMPString ::= {0, 0, 24, 25}

-- mongolianLetterA BMPString ::= {0, 0, 24, 32}

-- mongolianLetterE BMPString ::= {0, 0, 24, 33}

-- mongolianLetterI BMPString ::= {0, 0, 24, 34}

-- mongolianLetterO BMPString ::= {0, 0, 24, 35}

-- mongolianLetterU BMPString ::= {0, 0, 24, 36}

-- mongolianLetterOe BMPString ::= {0, 0, 24, 37}

-- mongolianLetterUe BMPString ::= {0, 0, 24, 38}

-- mongolianLetterEe BMPString ::= {0, 0, 24, 39}

-- mongolianLetterNa BMPString ::= {0, 0, 24, 40}

-- mongolianLetterAng BMPString ::= {0, 0, 24, 41}

-- mongolianLetterBa BMPString ::= {0, 0, 24, 42}

-- mongolianLetterPa BMPString ::= {0, 0, 24, 43}

-- mongolianLetterQa BMPString ::= {0, 0, 24, 44}

-- mongolianLetterGa BMPString ::= {0, 0, 24, 45}

-- mongolianLetterMa BMPString ::= {0, 0, 24, 46}

-- mongolianLetterLa BMPString ::= {0, 0, 24, 47}

-- mongolianLetterSa BMPString ::= {0, 0, 24, 48}

-- mongolianLetterSha BMPString ::= {0, 0, 24, 49}

-- mongolianLetterTa BMPString ::= {0, 0, 24, 50}

-- mongolianLetterDa BMPString ::= {0, 0, 24, 51}

-- mongolianLetterCha BMPString ::= {0, 0, 24, 52}

-- mongolianLetterJa BMPString ::= {0, 0, 24, 53}

-- mongolianLetterYa BMPString ::= {0, 0, 24, 54}

-- mongolianLetterRa BMPString ::= {0, 0, 24, 55}

-- mongolianLetterWa BMPString ::= {0, 0, 24, 56}

-- mongolianLetterFa BMPString ::= {0, 0, 24, 57}

-- mongolianLetterKa BMPString ::= {0, 0, 24, 58}

-- mongolianLetterKha BMPString ::= {0, 0, 24, 59}

-- mongolianLetterTsa BMPString ::= {0, 0, 24, 60}

-- mongolianLetterZa BMPString ::= {0, 0, 24, 61}

-- mongolianLetterHaa BMPString ::= {0, 0, 24, 62}

-- mongolianLetterZra BMPString ::= {0, 0, 24, 63}

-- mongolianLetterLha BMPString ::= {0, 0, 24, 64}

-- mongolianLetterZhi BMPString ::= {0, 0, 24, 65}

-- mongolianLetterChi BMPString ::= {0, 0, 24, 66}

-- mongolianLetterTodoLongVowelSign BMPString ::= {0, 0, 24, 67}

-- mongolianLetterTodoE BMPString ::= {0, 0, 24, 68}

-- mongolianLetterTodoI BMPString ::= {0, 0, 24, 69}

-- mongolianLetterTodoO BMPString ::= {0, 0, 24, 70}

-- mongolianLetterTodoU BMPString ::= {0, 0, 24, 71}

-- mongolianLetterTodoOe BMPString ::= {0, 0, 24, 72}

-- mongolianLetterTodoUe BMPString ::= {0, 0, 24, 73}

-- mongolianLetterTodoAng BMPString ::= {0, 0, 24, 74}

-- mongolianLetterTodoBa BMPString ::= {0, 0, 24, 75}

-- mongolianLetterTodoPa BMPString ::= {0, 0, 24, 76}

-- mongolianLetterTodoQa BMPString ::= {0, 0, 24, 77}

-- mongolianLetterTodoGa BMPString ::= {0, 0, 24, 78}

-- mongolianLetterTodoMa BMPString ::= {0, 0, 24, 79}

-- mongolianLetterTodoTa BMPString ::= {0, 0, 24, 80}

-- mongolianLetterTodoDa BMPString ::= {0, 0, 24, 81}

-- mongolianLetterTodoCha BMPString ::= {0, 0, 24, 82}

-- mongolianLetterTodoJa BMPString ::= {0, 0, 24, 83}

-- mongolianLetterTodoTsa BMPString ::= {0, 0, 24, 84}

-- mongolianLetterTodoYa BMPString ::= {0, 0, 24, 85}

-- mongolianLetterTodoWa BMPString ::= {0, 0, 24, 86}

-- mongolianLetterTodoKa BMPString ::= {0, 0, 24, 87}

-- mongolianLetterTodoGaa BMPString ::= {0, 0, 24, 88}

-- mongolianLetterTodoHaa BMPString ::= {0, 0, 24, 89}

-- mongolianLetterTodoJia BMPString ::= {0, 0, 24, 90}

-- mongolianLetterTodoNia BMPString ::= {0, 0, 24, 91}

-- mongolianLetterTodoDza BMPString ::= {0, 0, 24, 92}

-- mongolianLetterSibeE BMPString ::= {0, 0, 24, 93}

-- mongolianLetterSibeI BMPString ::= {0, 0, 24, 94}

-- mongolianLetterSibeIy BMPString ::= {0, 0, 24, 95}

-- mongolianLetterSibeUe BMPString ::= {0, 0, 24, 96}

-- mongolianLetterSibeU BMPString ::= {0, 0, 24, 97}

-- mongolianLetterSibeAng BMPString ::= {0, 0, 24, 98}

-- mongolianLetterSibeKa BMPString ::= {0, 0, 24, 99}

-- mongolianLetterSibeGa BMPString ::= {0, 0, 24, 100}

-- mongolianLetterSibeHa BMPString ::= {0, 0, 24, 101}

-- mongolianLetterSibePa BMPString ::= {0, 0, 24, 102}

-- mongolianLetterSibeSha BMPString ::= {0, 0, 24, 103}

-- mongolianLetterSibeTa BMPString ::= {0, 0, 24, 104}

-- mongolianLetterSibeDa BMPString ::= {0, 0, 24, 105}

-- mongolianLetterSibeJa BMPString ::= {0, 0, 24, 106}

-- mongolianLetterSibeFa BMPString ::= {0, 0, 24, 107}

-- mongolianLetterSibeGaa BMPString ::= {0, 0, 24, 108}

-- mongolianLetterSibeHaa BMPString ::= {0, 0, 24, 109}

-- mongolianLetterSibeTsa BMPString ::= {0, 0, 24, 110}

-- mongolianLetterSibeZa BMPString ::= {0, 0, 24, 111}

-- mongolianLetterSibeRaa BMPString ::= {0, 0, 24, 112}

-- mongolianLetterSibeCha BMPString ::= {0, 0, 24, 113}

-- mongolianLetterSibeZha BMPString ::= {0, 0, 24, 114}

-- mongolianLetterManchuI BMPString ::= {0, 0, 24, 115}

-- mongolianLetterManchuKa BMPString ::= {0, 0, 24, 116}

-- mongolianLetterManchuRa BMPString ::= {0, 0, 24, 117}

-- mongolianLetterManchuFa BMPString ::= {0, 0, 24, 118}

-- mongolianLetterManchuZha BMPString ::= {0, 0, 24, 119}

-- mongolianLetterAliGaliAnusvaraOne BMPString ::= {0, 0, 24, 128}

-- mongolianLetterAliGaliVisargaOne BMPString ::= {0, 0, 24, 129}

-- mongolianLetterAliGaliDamaru BMPString ::= {0, 0, 24, 130}

-- mongolianLetterAliGaliUbadama BMPString ::= {0, 0, 24, 131}

-- mongolianLetterAliGaliInvertedUbadama BMPString ::= {0, 0, 24, 132}

-- mongolianLetterAliGaliBaluda BMPString ::= {0, 0, 24, 133}

-- mongolianLetterAliGaliThreeBaluda BMPString ::= {0, 0, 24, 134}

-- mongolianLetterAliGaliA BMPString ::= {0, 0, 24, 135}

-- mongolianLetterAliGaliI BMPString ::= {0, 0, 24, 136}

-- mongolianLetterAliGaliKa BMPString ::= {0, 0, 24, 137}

-- mongolianLetterAliGaliNga BMPString ::= {0, 0, 24, 138}

-- mongolianLetterAliGaliCa BMPString ::= {0, 0, 24, 139}

-- mongolianLetterAliGaliTta BMPString ::= {0, 0, 24, 140}

-- mongolianLetterAliGaliTtha BMPString ::= {0, 0, 24, 141}

-- mongolianLetterAliGaliDda BMPString ::= {0, 0, 24, 142}

-- mongolianLetterAliGaliNna BMPString ::= {0, 0, 24, 143}

-- mongolianLetterAliGaliTa BMPString ::= {0, 0, 24, 144}

-- mongolianLetterAliGaliDa BMPString ::= {0, 0, 24, 145}

-- mongolianLetterAliGaliPa BMPString ::= {0, 0, 24, 146}

-- mongolianLetterAliGaliPha BMPString ::= {0, 0, 24, 147}

-- mongolianLetterAliGaliSsa BMPString ::= {0, 0, 24, 148}

-- mongolianLetterAliGaliZha BMPString ::= {0, 0, 24, 149}

-- mongolianLetterAliGaliZa BMPString ::= {0, 0, 24, 150}

-- mongolianLetterAliGaliAh BMPString ::= {0, 0, 24, 151}

-- mongolianLetterTodoAliGaliTa BMPString ::= {0, 0, 24, 152}

-- mongolianLetterTodoAliGaliZha BMPString ::= {0, 0, 24, 153}

-- mongolianLetterManchuAliGaliGha BMPString ::= {0, 0, 24, 154}

-- mongolianLetterManchuAliGaliNga BMPString ::= {0, 0, 24, 155}

-- mongolianLetterManchuAliGaliCa BMPString ::= {0, 0, 24, 156}

-- mongolianLetterManchuAliGaliJha BMPString ::= {0, 0, 24, 157}

-- mongolianLetterManchuAliGaliTta BMPString ::= {0, 0, 24, 158}

-- mongolianLetterManchuAliGaliDdha BMPString ::= {0, 0, 24, 159}

-- mongolianLetterManchuAliGaliTa BMPString ::= {0, 0, 24, 160}

-- mongolianLetterManchuAliGaliDha BMPString ::= {0, 0, 24, 161}

-- mongolianLetterManchuAliGaliSsa BMPString ::= {0, 0, 24, 162}

-- mongolianLetterManchuAliGaliCya BMPString ::= {0, 0, 24, 163}

-- mongolianLetterManchuAliGaliZha BMPString ::= {0, 0, 24, 164}

-- mongolianLetterManchuAliGaliZa BMPString ::= {0, 0, 24, 165}

-- mongolianLetterAliGaliHalfU BMPString ::= {0, 0, 24, 166}

-- mongolianLetterAliGaliHalfYa BMPString ::= {0, 0, 24, 167}

-- mongolianLetterManchuAliGaliBha BMPString ::= {0, 0, 24, 168}

-- mongolianLetterAliGaliDagalga BMPString ::= {0, 0, 24, 169}

-- latinCapitalLetterAWithRingBelow BMPString ::= {0, 0, 30, 0}

-- latinSmallLetterAWithRingBelow BMPString ::= {0, 0, 30, 1}

-- latinCapitalLetterBWithDotAbove BMPString ::= {0, 0, 30, 2}

-- latinSmallLetterBWithDotAbove BMPString ::= {0, 0, 30, 3}

-- latinCapitalLetterBWithDotBelow BMPString ::= {0, 0, 30, 4}

-- latinSmallLetterBWithDotBelow BMPString ::= {0, 0, 30, 5}

-- latinCapitalLetterBWithLineBelow BMPString ::= {0, 0, 30, 6}

-- latinSmallLetterBWithLineBelow BMPString ::= {0, 0, 30, 7}

-- latinCapitalLetterCWithCedillaAndAcute BMPString ::= {0, 0, 30, 8}

-- latinSmallLetterCWithCedillaAndAcute BMPString ::= {0, 0, 30, 9}

-- latinCapitalLetterDWithDotAbove BMPString ::= {0, 0, 30, 10}

-- latinSmallLetterDWithDotAbove BMPString ::= {0, 0, 30, 11}

-- latinCapitalLetterDWithDotBelow BMPString ::= {0, 0, 30, 12}

-- latinSmallLetterDWithDotBelow BMPString ::= {0, 0, 30, 13}

-- latinCapitalLetterDWithLineBelow BMPString ::= {0, 0, 30, 14}

-- latinSmallLetterDWithLineBelow BMPString ::= {0, 0, 30, 15}

-- latinCapitalLetterDWithCedilla BMPString ::= {0, 0, 30, 16}

-- latinSmallLetterDWithCedilla BMPString ::= {0, 0, 30, 17}

-- latinCapitalLetterDWithCircumflexBelow BMPString ::= {0, 0, 30, 18}

-- latinSmallLetterDWithCircumflexBelow BMPString ::= {0, 0, 30, 19}

-- latinCapitalLetterEWithMacronAndGrave BMPString ::= {0, 0, 30, 20}

-- latinSmallLetterEWithMacronAndGrave BMPString ::= {0, 0, 30, 21}

-- latinCapitalLetterEWithMacronAndAcute BMPString ::= {0, 0, 30, 22}

-- latinSmallLetterEWithMacronAndAcute BMPString ::= {0, 0, 30, 23}

-- latinCapitalLetterEWithCircumflexBelow BMPString ::= {0, 0, 30, 24}

-- latinSmallLetterEWithCircumflexBelow BMPString ::= {0, 0, 30, 25}

-- latinCapitalLetterEWithTildeBelow BMPString ::= {0, 0, 30, 26}

-- latinSmallLetterEWithTildeBelow BMPString ::= {0, 0, 30, 27}

-- latinCapitalLetterEWithCedillaAndBreve BMPString ::= {0, 0, 30, 28}

-- latinSmallLetterEWithCedillaAndBreve BMPString ::= {0, 0, 30, 29}

-- latinCapitalLetterFWithDotAbove BMPString ::= {0, 0, 30, 30}

-- latinSmallLetterFWithDotAbove BMPString ::= {0, 0, 30, 31}

-- latinCapitalLetterGWithMacron BMPString ::= {0, 0, 30, 32}

-- latinSmallLetterGWithMacron BMPString ::= {0, 0, 30, 33}

-- latinCapitalLetterHWithDotAbove BMPString ::= {0, 0, 30, 34}

-- latinSmallLetterHWithDotAbove BMPString ::= {0, 0, 30, 35}

-- latinCapitalLetterHWithDotBelow BMPString ::= {0, 0, 30, 36}

-- latinSmallLetterHWithDotBelow BMPString ::= {0, 0, 30, 37}

-- latinCapitalLetterHWithDiaeresis BMPString ::= {0, 0, 30, 38}

-- latinSmallLetterHWithDiaeresis BMPString ::= {0, 0, 30, 39}

-- latinCapitalLetterHWithCedilla BMPString ::= {0, 0, 30, 40}

-- latinSmallLetterHWithCedilla BMPString ::= {0, 0, 30, 41}

-- latinCapitalLetterHWithBreveBelow BMPString ::= {0, 0, 30, 42}

-- latinSmallLetterHWithBreveBelow BMPString ::= {0, 0, 30, 43}

-- latinCapitalLetterIWithTildeBelow BMPString ::= {0, 0, 30, 44}

-- latinSmallLetterIWithTildeBelow BMPString ::= {0, 0, 30, 45}

-- latinCapitalLetterIWithDiaeresisAndAcute BMPString ::= {0, 0, 30, 46}

-- latinSmallLetterIWithDiaeresisAndAcute BMPString ::= {0, 0, 30, 47}

-- latinCapitalLetterKWithAcute BMPString ::= {0, 0, 30, 48}

-- latinSmallLetterKWithAcute BMPString ::= {0, 0, 30, 49}

-- latinCapitalLetterKWithDotBelow BMPString ::= {0, 0, 30, 50}

-- latinSmallLetterKWithDotBelow BMPString ::= {0, 0, 30, 51}

-- latinCapitalLetterKWithLineBelow BMPString ::= {0, 0, 30, 52}

-- latinSmallLetterKWithLineBelow BMPString ::= {0, 0, 30, 53}

-- latinCapitalLetterLWithDotBelow BMPString ::= {0, 0, 30, 54}

-- latinSmallLetterLWithDotBelow BMPString ::= {0, 0, 30, 55}

-- latinCapitalLetterLWithDotBelowAndMacron BMPString ::= {0, 0, 30, 56}

-- latinSmallLetterLWithDotBelowAndMacron BMPString ::= {0, 0, 30, 57}

-- latinCapitalLetterLWithLineBelow BMPString ::= {0, 0, 30, 58}

-- latinSmallLetterLWithLineBelow BMPString ::= {0, 0, 30, 59}

-- latinCapitalLetterLWithCircumflexBelow BMPString ::= {0, 0, 30, 60}

-- latinSmallLetterLWithCircumflexBelow BMPString ::= {0, 0, 30, 61}

-- latinCapitalLetterMWithAcute BMPString ::= {0, 0, 30, 62}

-- latinSmallLetterMWithAcute BMPString ::= {0, 0, 30, 63}

-- latinCapitalLetterMWithDotAbove BMPString ::= {0, 0, 30, 64}

-- latinSmallLetterMWithDotAbove BMPString ::= {0, 0, 30, 65}

-- latinCapitalLetterMWithDotBelow BMPString ::= {0, 0, 30, 66}

-- latinSmallLetterMWithDotBelow BMPString ::= {0, 0, 30, 67}

-- latinCapitalLetterNWithDotAbove BMPString ::= {0, 0, 30, 68}

-- latinSmallLetterNWithDotAbove BMPString ::= {0, 0, 30, 69}

-- latinCapitalLetterNWithDotBelow BMPString ::= {0, 0, 30, 70}

-- latinSmallLetterNWithDotBelow BMPString ::= {0, 0, 30, 71}

-- latinCapitalLetterNWithLineBelow BMPString ::= {0, 0, 30, 72}

-- latinSmallLetterNWithLineBelow BMPString ::= {0, 0, 30, 73}

-- latinCapitalLetterNWithCircumflexBelow BMPString ::= {0, 0, 30, 74}

-- latinSmallLetterNWithCircumflexBelow BMPString ::= {0, 0, 30, 75}

-- latinCapitalLetterOWithTildeAndAcute BMPString ::= {0, 0, 30, 76}

-- latinSmallLetterOWithTildeAndAcute BMPString ::= {0, 0, 30, 77}

-- latinCapitalLetterOWithTildeAndDiaeresis BMPString ::= {0, 0, 30, 78}

-- latinSmallLetterOWithTildeAndDiaeresis BMPString ::= {0, 0, 30, 79}

-- latinCapitalLetterOWithMacronAndGrave BMPString ::= {0, 0, 30, 80}

-- latinSmallLetterOWithMacronAndGrave BMPString ::= {0, 0, 30, 81}

-- latinCapitalLetterOWithMacronAndAcute BMPString ::= {0, 0, 30, 82}

-- latinSmallLetterOWithMacronAndAcute BMPString ::= {0, 0, 30, 83}

-- latinCapitalLetterPWithAcute BMPString ::= {0, 0, 30, 84}

-- latinSmallLetterPWithAcute BMPString ::= {0, 0, 30, 85}

-- latinCapitalLetterPWithDotAbove BMPString ::= {0, 0, 30, 86}

-- latinSmallLetterPWithDotAbove BMPString ::= {0, 0, 30, 87}

-- latinCapitalLetterRWithDotAbove BMPString ::= {0, 0, 30, 88}

-- latinSmallLetterRWithDotAbove BMPString ::= {0, 0, 30, 89}

-- latinCapitalLetterRWithDotBelow BMPString ::= {0, 0, 30, 90}

-- latinSmallLetterRWithDotBelow BMPString ::= {0, 0, 30, 91}

-- latinCapitalLetterRWithDotBelowAndMacron BMPString ::= {0, 0, 30, 92}

-- latinSmallLetterRWithDotBelowAndMacron BMPString ::= {0, 0, 30, 93}

-- latinCapitalLetterRWithLineBelow BMPString ::= {0, 0, 30, 94}

-- latinSmallLetterRWithLineBelow BMPString ::= {0, 0, 30, 95}

-- latinCapitalLetterSWithDotAbove BMPString ::= {0, 0, 30, 96}

-- latinSmallLetterSWithDotAbove BMPString ::= {0, 0, 30, 97}

-- latinCapitalLetterSWithDotBelow BMPString ::= {0, 0, 30, 98}

-- latinSmallLetterSWithDotBelow BMPString ::= {0, 0, 30, 99}

-- latinCapitalLetterSWithAcuteAndDotAbove BMPString ::= {0, 0, 30, 100}

-- latinSmallLetterSWithAcuteAndDotAbove BMPString ::= {0, 0, 30, 101}

-- latinCapitalLetterSWithCaronAndDotAbove BMPString ::= {0, 0, 30, 102}

-- latinSmallLetterSWithCaronAndDotAbove BMPString ::= {0, 0, 30, 103}

-- latinCapitalLetterSWithDotBelowAndDotAbove BMPString ::= {0, 0, 30, 104}

-- latinSmallLetterSWithDotBelowAndDotAbove BMPString ::= {0, 0, 30, 105}

-- latinCapitalLetterTWithDotAbove BMPString ::= {0, 0, 30, 106}

-- latinSmallLetterTWithDotAbove BMPString ::= {0, 0, 30, 107}

-- latinCapitalLetterTWithDotBelow BMPString ::= {0, 0, 30, 108}

-- latinSmallLetterTWithDotBelow BMPString ::= {0, 0, 30, 109}

-- latinCapitalLetterTWithLineBelow BMPString ::= {0, 0, 30, 110}

-- latinSmallLetterTWithLineBelow BMPString ::= {0, 0, 30, 111}

-- latinCapitalLetterTWithCircumflexBelow BMPString ::= {0, 0, 30, 112}

-- latinSmallLetterTWithCircumflexBelow BMPString ::= {0, 0, 30, 113}

-- latinCapitalLetterUWithDiaeresisBelow BMPString ::= {0, 0, 30, 114}

-- latinSmallLetterUWithDiaeresisBelow BMPString ::= {0, 0, 30, 115}

-- latinCapitalLetterUWithTildeBelow BMPString ::= {0, 0, 30, 116}

-- latinSmallLetterUWithTildeBelow BMPString ::= {0, 0, 30, 117}

-- latinCapitalLetterUWithCircumflexBelow BMPString ::= {0, 0, 30, 118}

-- latinSmallLetterUWithCircumflexBelow BMPString ::= {0, 0, 30, 119}

-- latinCapitalLetterUWithTildeAndAcute BMPString ::= {0, 0, 30, 120}

-- latinSmallLetterUWithTildeAndAcute BMPString ::= {0, 0, 30, 121}

-- latinCapitalLetterUWithMacronAndDiaeresis BMPString ::= {0, 0, 30, 122}

-- latinSmallLetterUWithMacronAndDiaeresis BMPString ::= {0, 0, 30, 123}

-- latinCapitalLetterVWithTilde BMPString ::= {0, 0, 30, 124}

-- latinSmallLetterVWithTilde BMPString ::= {0, 0, 30, 125}

-- latinCapitalLetterVWithDotBelow BMPString ::= {0, 0, 30, 126}

-- latinSmallLetterVWithDotBelow BMPString ::= {0, 0, 30, 127}

-- latinCapitalLetterWWithGrave BMPString ::= {0, 0, 30, 128}

-- latinSmallLetterWWithGrave BMPString ::= {0, 0, 30, 129}

-- latinCapitalLetterWWithAcute BMPString ::= {0, 0, 30, 130}

-- latinSmallLetterWWithAcute BMPString ::= {0, 0, 30, 131}

-- latinCapitalLetterWWithDiaeresis BMPString ::= {0, 0, 30, 132}

-- latinSmallLetterWWithDiaeresis BMPString ::= {0, 0, 30, 133}

-- latinCapitalLetterWWithDotAbove BMPString ::= {0, 0, 30, 134}

-- latinSmallLetterWWithDotAbove BMPString ::= {0, 0, 30, 135}

-- latinCapitalLetterWWithDotBelow BMPString ::= {0, 0, 30, 136}

-- latinSmallLetterWWithDotBelow BMPString ::= {0, 0, 30, 137}

-- latinCapitalLetterXWithDotAbove BMPString ::= {0, 0, 30, 138}

-- latinSmallLetterXWithDotAbove BMPString ::= {0, 0, 30, 139}

-- latinCapitalLetterXWithDiaeresis BMPString ::= {0, 0, 30, 140}

-- latinSmallLetterXWithDiaeresis BMPString ::= {0, 0, 30, 141}

-- latinCapitalLetterYWithDotAbove BMPString ::= {0, 0, 30, 142}

-- latinSmallLetterYWithDotAbove BMPString ::= {0, 0, 30, 143}

-- latinCapitalLetterZWithCircumflex BMPString ::= {0, 0, 30, 144}

-- latinSmallLetterZWithCircumflex BMPString ::= {0, 0, 30, 145}

-- latinCapitalLetterZWithDotBelow BMPString ::= {0, 0, 30, 146}

-- latinSmallLetterZWithDotBelow BMPString ::= {0, 0, 30, 147}

-- latinCapitalLetterZWithLineBelow BMPString ::= {0, 0, 30, 148}

-- latinSmallLetterZWithLineBelow BMPString ::= {0, 0, 30, 149}

-- latinSmallLetterHWithLineBelow BMPString ::= {0, 0, 30, 150}

-- latinSmallLetterTWithDiaeresis BMPString ::= {0, 0, 30, 151}

-- latinSmallLetterWWithRingAbove BMPString ::= {0, 0, 30, 152}

-- latinSmallLetterYWithRingAbove BMPString ::= {0, 0, 30, 153}

-- latinSmallLetterAWithRightHalfRing BMPString ::= {0, 0, 30, 154}

-- latinSmallLetterLongSWithDotAbove BMPString ::= {0, 0, 30, 155}

-- latinCapitalLetterAWithDotBelow BMPString ::= {0, 0, 30, 160}

-- latinSmallLetterAWithDotBelow BMPString ::= {0, 0, 30, 161}

-- latinCapitalLetterAWithHookAbove BMPString ::= {0, 0, 30, 162}

-- latinSmallLetterAWithHookAbove BMPString ::= {0, 0, 30, 163}

-- latinCapitalLetterAWithCircumflexAndAcute BMPString ::= {0, 0, 30, 164}

-- latinSmallLetterAWithCircumflexAndAcute BMPString ::= {0, 0, 30, 165}

-- latinCapitalLetterAWithCircumflexAndGrave BMPString ::= {0, 0, 30, 166}

-- latinSmallLetterAWithCircumflexAndGrave BMPString ::= {0, 0, 30, 167}

-- latinCapitalLetterAWithCircumflexAndHookAbove BMPString ::= {0, 0, 30, 168}

-- latinSmallLetterAWithCircumflexAndHookAbove BMPString ::= {0, 0, 30, 169}

-- latinCapitalLetterAWithCircumflexAndTilde BMPString ::= {0, 0, 30, 170}

-- latinSmallLetterAWithCircumflexAndTilde BMPString ::= {0, 0, 30, 171}

-- latinCapitalLetterAWithCircumflexAndDotBelow BMPString ::= {0, 0, 30, 172}

-- latinSmallLetterAWithCircumflexAndDotBelow BMPString ::= {0, 0, 30, 173}

-- latinCapitalLetterAWithBreveAndAcute BMPString ::= {0, 0, 30, 174}

-- latinSmallLetterAWithBreveAndAcute BMPString ::= {0, 0, 30, 175}

-- latinCapitalLetterAWithBreveAndGrave BMPString ::= {0, 0, 30, 176}

-- latinSmallLetterAWithBreveAndGrave BMPString ::= {0, 0, 30, 177}

-- latinCapitalLetterAWithBreveAndHookAbove BMPString ::= {0, 0, 30, 178}

-- latinSmallLetterAWithBreveAndHookAbove BMPString ::= {0, 0, 30, 179}

-- latinCapitalLetterAWithBreveAndTilde BMPString ::= {0, 0, 30, 180}

-- latinSmallLetterAWithBreveAndTilde BMPString ::= {0, 0, 30, 181}

-- latinCapitalLetterAWithBreveAndDotBelow BMPString ::= {0, 0, 30, 182}

-- latinSmallLetterAWithBreveAndDotBelow BMPString ::= {0, 0, 30, 183}

-- latinCapitalLetterEWithDotBelow BMPString ::= {0, 0, 30, 184}

-- latinSmallLetterEWithDotBelow BMPString ::= {0, 0, 30, 185}

-- latinCapitalLetterEWithHookAbove BMPString ::= {0, 0, 30, 186}

-- latinSmallLetterEWithHookAbove BMPString ::= {0, 0, 30, 187}

-- latinCapitalLetterEWithTilde BMPString ::= {0, 0, 30, 188}

-- latinSmallLetterEWithTilde BMPString ::= {0, 0, 30, 189}

-- latinCapitalLetterEWithCircumflexAndAcute BMPString ::= {0, 0, 30, 190}

-- latinSmallLetterEWithCircumflexAndAcute BMPString ::= {0, 0, 30, 191}

-- latinCapitalLetterEWithCircumflexAndGrave BMPString ::= {0, 0, 30, 192}

-- latinSmallLetterEWithCircumflexAndGrave BMPString ::= {0, 0, 30, 193}

-- latinCapitalLetterEWithCircumflexAndHookAbove BMPString ::= {0, 0, 30, 194}

-- latinSmallLetterEWithCircumflexAndHookAbove BMPString ::= {0, 0, 30, 195}

-- latinCapitalLetterEWithCircumflexAndTilde BMPString ::= {0, 0, 30, 196}

-- latinSmallLetterEWithCircumflexAndTilde BMPString ::= {0, 0, 30, 197}

-- latinCapitalLetterEWithCircumflexAndDotBelow BMPString ::= {0, 0, 30, 198}

-- latinSmallLetterEWithCircumflexAndDotBelow BMPString ::= {0, 0, 30, 199}

-- latinCapitalLetterIWithHookAbove BMPString ::= {0, 0, 30, 200}

-- latinSmallLetterIWithHookAbove BMPString ::= {0, 0, 30, 201}

-- latinCapitalLetterIWithDotBelow BMPString ::= {0, 0, 30, 202}

-- latinSmallLetterIWithDotBelow BMPString ::= {0, 0, 30, 203}

-- latinCapitalLetterOWithDotBelow BMPString ::= {0, 0, 30, 204}

-- latinSmallLetterOWithDotBelow BMPString ::= {0, 0, 30, 205}

-- latinCapitalLetterOWithHookAbove BMPString ::= {0, 0, 30, 206}

-- latinSmallLetterOWithHookAbove BMPString ::= {0, 0, 30, 207}

-- latinCapitalLetterOWithCircumflexAndAcute BMPString ::= {0, 0, 30, 208}

-- latinSmallLetterOWithCircumflexAndAcute BMPString ::= {0, 0, 30, 209}

-- latinCapitalLetterOWithCircumflexAndGrave BMPString ::= {0, 0, 30, 210}

-- latinSmallLetterOWithCircumflexAndGrave BMPString ::= {0, 0, 30, 211}

-- latinCapitalLetterOWithCircumflexAndHookAbove BMPString ::= {0, 0, 30, 212}

-- latinSmallLetterOWithCircumflexAndHookAbove BMPString ::= {0, 0, 30, 213}

-- latinCapitalLetterOWithCircumflexAndTilde BMPString ::= {0, 0, 30, 214}

-- latinSmallLetterOWithCircumflexAndTilde BMPString ::= {0, 0, 30, 215}

-- latinCapitalLetterOWithCircumflexAndDotBelow BMPString ::= {0, 0, 30, 216}

-- latinSmallLetterOWithCircumflexAndDotBelow BMPString ::= {0, 0, 30, 217}

-- latinCapitalLetterOWithHornAndAcute BMPString ::= {0, 0, 30, 218}

-- latinSmallLetterOWithHornAndAcute BMPString ::= {0, 0, 30, 219}

-- latinCapitalLetterOWithHornAndGrave BMPString ::= {0, 0, 30, 220}

-- latinSmallLetterOWithHornAndGrave BMPString ::= {0, 0, 30, 221}

-- latinCapitalLetterOWithHornAndHookAbove BMPString ::= {0, 0, 30, 222}

-- latinSmallLetterOWithHornAndHookAbove BMPString ::= {0, 0, 30, 223}

-- latinCapitalLetterOWithHornAndTilde BMPString ::= {0, 0, 30, 224}

-- latinSmallLetterOWithHornAndTilde BMPString ::= {0, 0, 30, 225}

-- latinCapitalLetterOWithHornAndDotBelow BMPString ::= {0, 0, 30, 226}

-- latinSmallLetterOWithHornAndDotBelow BMPString ::= {0, 0, 30, 227}

-- latinCapitalLetterUWithDotBelow BMPString ::= {0, 0, 30, 228}

-- latinSmallLetterUWithDotBelow BMPString ::= {0, 0, 30, 229}

-- latinCapitalLetterUWithHookAbove BMPString ::= {0, 0, 30, 230}

-- latinSmallLetterUWithHookAbove BMPString ::= {0, 0, 30, 231}

-- latinCapitalLetterUWithHornAndAcute BMPString ::= {0, 0, 30, 232}

-- latinSmallLetterUWithHornAndAcute BMPString ::= {0, 0, 30, 233}

-- latinCapitalLetterUWithHornAndGrave BMPString ::= {0, 0, 30, 234}

-- latinSmallLetterUWithHornAndGrave BMPString ::= {0, 0, 30, 235}

-- latinCapitalLetterUWithHornAndHookAbove BMPString ::= {0, 0, 30, 236}

-- latinSmallLetterUWithHornAndHookAbove BMPString ::= {0, 0, 30, 237}

-- latinCapitalLetterUWithHornAndTilde BMPString ::= {0, 0, 30, 238}

-- latinSmallLetterUWithHornAndTilde BMPString ::= {0, 0, 30, 239}

-- latinCapitalLetterUWithHornAndDotBelow BMPString ::= {0, 0, 30, 240}

-- latinSmallLetterUWithHornAndDotBelow BMPString ::= {0, 0, 30, 241}

-- latinCapitalLetterYWithGrave BMPString ::= {0, 0, 30, 242}

-- latinSmallLetterYWithGrave BMPString ::= {0, 0, 30, 243}

-- latinCapitalLetterYWithDotBelow BMPString ::= {0, 0, 30, 244}

-- latinSmallLetterYWithDotBelow BMPString ::= {0, 0, 30, 245}

-- latinCapitalLetterYWithHookAbove BMPString ::= {0, 0, 30, 246}

-- latinSmallLetterYWithHookAbove BMPString ::= {0, 0, 30, 247}

-- latinCapitalLetterYWithTilde BMPString ::= {0, 0, 30, 248}

-- latinSmallLetterYWithTilde BMPString ::= {0, 0, 30, 249}

-- greekSmallLetterAlphaWithPsili BMPString ::= {0, 0, 31, 0}

-- greekSmallLetterAlphaWithDasia BMPString ::= {0, 0, 31, 1}

-- greekSmallLetterAlphaWithPsiliAndVaria BMPString ::= {0, 0, 31, 2}

-- greekSmallLetterAlphaWithDasiaAndVaria BMPString ::= {0, 0, 31, 3}

-- greekSmallLetterAlphaWithPsiliAndOxia BMPString ::= {0, 0, 31, 4}

-- greekSmallLetterAlphaWithDasiaAndOxia BMPString ::= {0, 0, 31, 5}

-- greekSmallLetterAlphaWithPsiliAndPerispomeni BMPString ::= {0, 0, 31, 6}

-- greekSmallLetterAlphaWithDasiaAndPerispomeni BMPString ::= {0, 0, 31, 7}

-- greekCapitalLetterAlphaWithPsili BMPString ::= {0, 0, 31, 8}

-- greekCapitalLetterAlphaWithDasia BMPString ::= {0, 0, 31, 9}

-- greekCapitalLetterAlphaWithPsiliAndVaria BMPString ::= {0, 0, 31, 10}

-- greekCapitalLetterAlphaWithDasiaAndVaria BMPString ::= {0, 0, 31, 11}

-- greekCapitalLetterAlphaWithPsiliAndOxia BMPString ::= {0, 0, 31, 12}

-- greekCapitalLetterAlphaWithDasiaAndOxia BMPString ::= {0, 0, 31, 13}

-- greekCapitalLetterAlphaWithPsiliAndPerispomeni BMPString ::= {0, 0, 31, 14}

-- greekCapitalLetterAlphaWithDasiaAndPerispomeni BMPString ::= {0, 0, 31, 15}

-- greekSmallLetterEpsilonWithPsili BMPString ::= {0, 0, 31, 16}

-- greekSmallLetterEpsilonWithDasia BMPString ::= {0, 0, 31, 17}

-- greekSmallLetterEpsilonWithPsiliAndVaria BMPString ::= {0, 0, 31, 18}

-- greekSmallLetterEpsilonWithDasiaAndVaria BMPString ::= {0, 0, 31, 19}

-- greekSmallLetterEpsilonWithPsiliAndOxia BMPString ::= {0, 0, 31, 20}

-- greekSmallLetterEpsilonWithDasiaAndOxia BMPString ::= {0, 0, 31, 21}

-- greekCapitalLetterEpsilonWithPsili BMPString ::= {0, 0, 31, 24}

-- greekCapitalLetterEpsilonWithDasia BMPString ::= {0, 0, 31, 25}

-- greekCapitalLetterEpsilonWithPsiliAndVaria BMPString ::= {0, 0, 31, 26}

-- greekCapitalLetterEpsilonWithDasiaAndVaria BMPString ::= {0, 0, 31, 27}

-- greekCapitalLetterEpsilonWithPsiliAndOxia BMPString ::= {0, 0, 31, 28}

-- greekCapitalLetterEpsilonWithDasiaAndOxia BMPString ::= {0, 0, 31, 29}

-- greekSmallLetterEtaWithPsili BMPString ::= {0, 0, 31, 32}

-- greekSmallLetterEtaWithDasia BMPString ::= {0, 0, 31, 33}

-- greekSmallLetterEtaWithPsiliAndVaria BMPString ::= {0, 0, 31, 34}

-- greekSmallLetterEtaWithDasiaAndVaria BMPString ::= {0, 0, 31, 35}

-- greekSmallLetterEtaWithPsiliAndOxia BMPString ::= {0, 0, 31, 36}

-- greekSmallLetterEtaWithDasiaAndOxia BMPString ::= {0, 0, 31, 37}

-- greekSmallLetterEtaWithPsiliAndPerispomeni BMPString ::= {0, 0, 31, 38}

-- greekSmallLetterEtaWithDasiaAndPerispomeni BMPString ::= {0, 0, 31, 39}

-- greekCapitalLetterEtaWithPsili BMPString ::= {0, 0, 31, 40}

-- greekCapitalLetterEtaWithDasia BMPString ::= {0, 0, 31, 41}

-- greekCapitalLetterEtaWithPsiliAndVaria BMPString ::= {0, 0, 31, 42}

-- greekCapitalLetterEtaWithDasiaAndVaria BMPString ::= {0, 0, 31, 43}

-- greekCapitalLetterEtaWithPsiliAndOxia BMPString ::= {0, 0, 31, 44}

-- greekCapitalLetterEtaWithDasiaAndOxia BMPString ::= {0, 0, 31, 45}

-- greekCapitalLetterEtaWithPsiliAndPerispomeni BMPString ::= {0, 0, 31, 46}

-- greekCapitalLetterEtaWithDasiaAndPerispomeni BMPString ::= {0, 0, 31, 47}

-- greekSmallLetterIotaWithPsili BMPString ::= {0, 0, 31, 48}

-- greekSmallLetterIotaWithDasia BMPString ::= {0, 0, 31, 49}

-- greekSmallLetterIotaWithPsiliAndVaria BMPString ::= {0, 0, 31, 50}

-- greekSmallLetterIotaWithDasiaAndVaria BMPString ::= {0, 0, 31, 51}

-- greekSmallLetterIotaWithPsiliAndOxia BMPString ::= {0, 0, 31, 52}

-- greekSmallLetterIotaWithDasiaAndOxia BMPString ::= {0, 0, 31, 53}

-- greekSmallLetterIotaWithPsiliAndPerispomeni BMPString ::= {0, 0, 31, 54}

-- greekSmallLetterIotaWithDasiaAndPerispomeni BMPString ::= {0, 0, 31, 55}

-- greekCapitalLetterIotaWithPsili BMPString ::= {0, 0, 31, 56}

-- greekCapitalLetterIotaWithDasia BMPString ::= {0, 0, 31, 57}

-- greekCapitalLetterIotaWithPsiliAndVaria BMPString ::= {0, 0, 31, 58}

-- greekCapitalLetterIotaWithDasiaAndVaria BMPString ::= {0, 0, 31, 59}

-- greekCapitalLetterIotaWithPsiliAndOxia BMPString ::= {0, 0, 31, 60}

-- greekCapitalLetterIotaWithDasiaAndOxia BMPString ::= {0, 0, 31, 61}

-- greekCapitalLetterIotaWithPsiliAndPerispomeni BMPString ::= {0, 0, 31, 62}

-- greekCapitalLetterIotaWithDasiaAndPerispomeni BMPString ::= {0, 0, 31, 63}

-- greekSmallLetterOmicronWithPsili BMPString ::= {0, 0, 31, 64}

-- greekSmallLetterOmicronWithDasia BMPString ::= {0, 0, 31, 65}

-- greekSmallLetterOmicronWithPsiliAndVaria BMPString ::= {0, 0, 31, 66}

-- greekSmallLetterOmicronWithDasiaAndVaria BMPString ::= {0, 0, 31, 67}

-- greekSmallLetterOmicronWithPsiliAndOxia BMPString ::= {0, 0, 31, 68}

-- greekSmallLetterOmicronWithDasiaAndOxia BMPString ::= {0, 0, 31, 69}

-- greekCapitalLetterOmicronWithPsili BMPString ::= {0, 0, 31, 72}

-- greekCapitalLetterOmicronWithDasia BMPString ::= {0, 0, 31, 73}

-- greekCapitalLetterOmicronWithPsiliAndVaria BMPString ::= {0, 0, 31, 74}

-- greekCapitalLetterOmicronWithDasiaAndVaria BMPString ::= {0, 0, 31, 75}

-- greekCapitalLetterOmicronWithPsiliAndOxia BMPString ::= {0, 0, 31, 76}

-- greekCapitalLetterOmicronWithDasiaAndOxia BMPString ::= {0, 0, 31, 77}

-- greekSmallLetterUpsilonWithPsili BMPString ::= {0, 0, 31, 80}

-- greekSmallLetterUpsilonWithDasia BMPString ::= {0, 0, 31, 81}

-- greekSmallLetterUpsilonWithPsiliAndVaria BMPString ::= {0, 0, 31, 82}

-- greekSmallLetterUpsilonWithDasiaAndVaria BMPString ::= {0, 0, 31, 83}

-- greekSmallLetterUpsilonWithPsiliAndOxia BMPString ::= {0, 0, 31, 84}

-- greekSmallLetterUpsilonWithDasiaAndOxia BMPString ::= {0, 0, 31, 85}

-- greekSmallLetterUpsilonWithPsiliAndPerispomeni BMPString ::= {0, 0, 31, 86}

-- greekSmallLetterUpsilonWithDasiaAndPerispomeni BMPString ::= {0, 0, 31, 87}

-- greekCapitalLetterUpsilonWithDasia BMPString ::= {0, 0, 31, 89}

-- greekCapitalLetterUpsilonWithDasiaAndVaria BMPString ::= {0, 0, 31, 91}

-- greekCapitalLetterUpsilonWithDasiaAndOxia BMPString ::= {0, 0, 31, 93}

-- greekCapitalLetterUpsilonWithDasiaAndPerispomeni BMPString ::= {0, 0, 31, 95}

-- greekSmallLetterOmegaWithPsili BMPString ::= {0, 0, 31, 96}

-- greekSmallLetterOmegaWithDasia BMPString ::= {0, 0, 31, 97}

-- greekSmallLetterOmegaWithPsiliAndVaria BMPString ::= {0, 0, 31, 98}

-- greekSmallLetterOmegaWithDasiaAndVaria BMPString ::= {0, 0, 31, 99}

-- greekSmallLetterOmegaWithPsiliAndOxia BMPString ::= {0, 0, 31, 100}

-- greekSmallLetterOmegaWithDasiaAndOxia BMPString ::= {0, 0, 31, 101}

-- greekSmallLetterOmegaWithPsiliAndPerispomeni BMPString ::= {0, 0, 31, 102}

-- greekSmallLetterOmegaWithDasiaAndPerispomeni BMPString ::= {0, 0, 31, 103}

-- greekCapitalLetterOmegaWithPsili BMPString ::= {0, 0, 31, 104}

-- greekCapitalLetterOmegaWithDasia BMPString ::= {0, 0, 31, 105}

-- greekCapitalLetterOmegaWithPsiliAndVaria BMPString ::= {0, 0, 31, 106}

-- greekCapitalLetterOmegaWithDasiaAndVaria BMPString ::= {0, 0, 31, 107}

-- greekCapitalLetterOmegaWithPsiliAndOxia BMPString ::= {0, 0, 31, 108}

-- greekCapitalLetterOmegaWithDasiaAndOxia BMPString ::= {0, 0, 31, 109}

-- greekCapitalLetterOmegaWithPsiliAndPerispomeni BMPString ::= {0, 0, 31, 110}

-- greekCapitalLetterOmegaWithDasiaAndPerispomeni BMPString ::= {0, 0, 31, 111}

-- greekSmallLetterAlphaWithVaria BMPString ::= {0, 0, 31, 112}

-- greekSmallLetterAlphaWithOxia BMPString ::= {0, 0, 31, 113}

-- greekSmallLetterEpsilonWithVaria BMPString ::= {0, 0, 31, 114}

-- greekSmallLetterEpsilonWithOxia BMPString ::= {0, 0, 31, 115}

-- greekSmallLetterEtaWithVaria BMPString ::= {0, 0, 31, 116}

-- greekSmallLetterEtaWithOxia BMPString ::= {0, 0, 31, 117}

-- greekSmallLetterIotaWithVaria BMPString ::= {0, 0, 31, 118}

-- greekSmallLetterIotaWithOxia BMPString ::= {0, 0, 31, 119}

-- greekSmallLetterOmicronWithVaria BMPString ::= {0, 0, 31, 120}

-- greekSmallLetterOmicronWithOxia BMPString ::= {0, 0, 31, 121}

-- greekSmallLetterUpsilonWithVaria BMPString ::= {0, 0, 31, 122}

-- greekSmallLetterUpsilonWithOxia BMPString ::= {0, 0, 31, 123}

-- greekSmallLetterOmegaWithVaria BMPString ::= {0, 0, 31, 124}

-- greekSmallLetterOmegaWithOxia BMPString ::= {0, 0, 31, 125}

-- greekSmallLetterAlphaWithPsiliAndYpogegrammeni BMPString ::= {0, 0, 31, 128}

-- greekSmallLetterAlphaWithDasiaAndYpogegrammeni BMPString ::= {0, 0, 31, 129}

-- greekSmallLetterAlphaWithPsiliAndVariaAndYpogegrammeni BMPString ::=
--   {0, 0, 31, 130}

-- greekSmallLetterAlphaWithDasiaAndVariaAndYpogegrammeni BMPString ::=
--   {0, 0, 31, 131}

-- greekSmallLetterAlphaWithPsiliAndOxiaAndYpogegrammeni BMPString ::=
--   {0, 0, 31, 132}

-- greekSmallLetterAlphaWithDasiaAndOxiaAndYpogegrammeni BMPString ::=
--   {0, 0, 31, 133}

-- greekSmallLetterAlphaWithPsiliAndPerispomeniAndYpogegrammeni BMPString ::=
--   {0, 0, 31, 134}

-- greekSmallLetterAlphaWithDasiaAndPerispomeniAndYpogegrammeni BMPString ::=
--   {0, 0, 31, 135}

-- greekCapitalLetterAlphaWithPsiliAndProsgegrammeni BMPString ::= {0, 0, 31, 136}

-- greekCapitalLetterAlphaWithDasiaAndProsgegrammeni BMPString ::= {0, 0, 31, 137}

-- greekCapitalLetterAlphaWithPsiliAndVariaAndProsgegrammeni BMPString ::=
--   {0, 0, 31, 138}

-- greekCapitalLetterAlphaWithDasiaAndVariaAndProsgegrammeni BMPString ::=
--   {0, 0, 31, 139}

-- greekCapitalLetterAlphaWithPsiliAndOxiaAndProsgegrammeni BMPString ::=
--   {0, 0, 31, 140}

-- greekCapitalLetterAlphaWithDasiaAndOxiaAndProsgegrammeni BMPString ::=
--   {0, 0, 31, 141}

-- greekCapitalLetterAlphaWithPsiliAndPerispomeniAndProsgegrammeni BMPString ::=
--   {0, 0, 31, 142}

-- greekCapitalLetterAlphaWithDasiaAndPerispomeniAndProsgegrammeni BMPString ::=
--   {0, 0, 31, 143}

-- greekSmallLetterEtaWithPsiliAndYpogegrammeni BMPString ::= {0, 0, 31, 144}

-- greekSmallLetterEtaWithDasiaAndYpogegrammeni BMPString ::= {0, 0, 31, 145}

-- greekSmallLetterEtaWithPsiliAndVariaAndYpogegrammeni BMPString ::=
--   {0, 0, 31, 146}

-- greekSmallLetterEtaWithDasiaAndVariaAndYpogegrammeni BMPString ::=
--   {0, 0, 31, 147}

-- greekSmallLetterEtaWithPsiliAndOxiaAndYpogegrammeni BMPString ::=
--   {0, 0, 31, 148}

-- greekSmallLetterEtaWithDasiaAndOxiaAndYpogegrammeni BMPString ::=
--   {0, 0, 31, 149}

-- greekSmallLetterEtaWithPsiliAndPerispomeniAndYpogegrammeni BMPString ::=
--   {0, 0, 31, 150}

-- greekSmallLetterEtaWithDasiaAndPerispomeniAndYpogegrammeni BMPString ::=
--   {0, 0, 31, 151}

-- greekCapitalLetterEtaWithPsiliAndProsgegrammeni BMPString ::= {0, 0, 31, 152}

-- greekCapitalLetterEtaWithDasiaAndProsgegrammeni BMPString ::= {0, 0, 31, 153}

-- greekCapitalLetterEtaWithPsiliAndVariaAndProsgegrammeni BMPString ::=
--   {0, 0, 31, 154}

-- greekCapitalLetterEtaWithDasiaAndVariaAndProsgegrammeni BMPString ::=
--   {0, 0, 31, 155}

-- greekCapitalLetterEtaWithPsiliAndOxiaAndProsgegrammeni BMPString ::=
--   {0, 0, 31, 156}

-- greekCapitalLetterEtaWithDasiaAndOxiaAndProsgegrammeni BMPString ::=
--   {0, 0, 31, 157}

-- greekCapitalLetterEtaWithPsiliAndPerispomeniAndProsgegrammeni BMPString ::=
--   {0, 0, 31, 158}

-- greekCapitalLetterEtaWithDasiaAndPerispomeniAndProsgegrammeni BMPString ::=
--   {0, 0, 31, 159}

-- greekSmallLetterOmegaWithPsiliAndYpogegrammeni BMPString ::= {0, 0, 31, 160}

-- greekSmallLetterOmegaWithDasiaAndYpogegrammeni BMPString ::= {0, 0, 31, 161}

-- greekSmallLetterOmegaWithPsiliAndVariaAndYpogegrammeni BMPString ::=
--   {0, 0, 31, 162}

-- greekSmallLetterOmegaWithDasiaAndVariaAndYpogegrammeni BMPString ::=
--   {0, 0, 31, 163}

-- greekSmallLetterOmegaWithPsiliAndOxiaAndYpogegrammeni BMPString ::=
--   {0, 0, 31, 164}

-- greekSmallLetterOmegaWithDasiaAndOxiaAndYpogegrammeni BMPString ::=
--   {0, 0, 31, 165}

-- greekSmallLetterOmegaWithPsiliAndPerispomeniAndYpogegrammeni BMPString ::=
--   {0, 0, 31, 166}

-- greekSmallLetterOmegaWithDasiaAndPerispomeniAndYpogegrammeni BMPString ::=
--   {0, 0, 31, 167}

-- greekCapitalLetterOmegaWithPsiliAndProsgegrammeni BMPString ::= {0, 0, 31, 168}

-- greekCapitalLetterOmegaWithDasiaAndProsgegrammeni BMPString ::= {0, 0, 31, 169}

-- greekCapitalLetterOmegaWithPsiliAndVariaAndProsgegrammeni BMPString ::=
--   {0, 0, 31, 170}

-- greekCapitalLetterOmegaWithDasiaAndVariaAndProsgegrammeni BMPString ::=
--   {0, 0, 31, 171}

-- greekCapitalLetterOmegaWithPsiliAndOxiaAndProsgegrammeni BMPString ::=
--   {0, 0, 31, 172}

-- greekCapitalLetterOmegaWithDasiaAndOxiaAndProsgegrammeni BMPString ::=
--   {0, 0, 31, 173}

-- greekCapitalLetterOmegaWithPsiliAndPerispomeniAndProsgegrammeni BMPString ::=
--   {0, 0, 31, 174}

-- greekCapitalLetterOmegaWithDasiaAndPerispomeniAndProsgegrammeni BMPString ::=
--   {0, 0, 31, 175}

-- greekSmallLetterAlphaWithVrachy BMPString ::= {0, 0, 31, 176}

-- greekSmallLetterAlphaWithMacron BMPString ::= {0, 0, 31, 177}

-- greekSmallLetterAlphaWithVariaAndYpogegrammeni BMPString ::= {0, 0, 31, 178}

-- greekSmallLetterAlphaWithYpogegrammeni BMPString ::= {0, 0, 31, 179}

-- greekSmallLetterAlphaWithOxiaAndYpogegrammeni BMPString ::= {0, 0, 31, 180}

-- greekSmallLetterAlphaWithPerispomeni BMPString ::= {0, 0, 31, 182}

-- greekSmallLetterAlphaWithPerispomeniAndYpogegrammeni BMPString ::=
--   {0, 0, 31, 183}

-- greekCapitalLetterAlphaWithVrachy BMPString ::= {0, 0, 31, 184}

-- greekCapitalLetterAlphaWithMacron BMPString ::= {0, 0, 31, 185}

-- greekCapitalLetterAlphaWithVaria BMPString ::= {0, 0, 31, 186}

-- greekCapitalLetterAlphaWithOxia BMPString ::= {0, 0, 31, 187}

-- greekCapitalLetterAlphaWithProsgegrammeni BMPString ::= {0, 0, 31, 188}

-- greekKoronis BMPString ::= {0, 0, 31, 189}

-- greekProsgegrammeni BMPString ::= {0, 0, 31, 190}

-- greekPsili BMPString ::= {0, 0, 31, 191}

-- greekPerispomeni BMPString ::= {0, 0, 31, 192}

-- greekDialytikaAndPerispomeni BMPString ::= {0, 0, 31, 193}

-- greekSmallLetterEtaWithVariaAndYpogegrammeni BMPString ::= {0, 0, 31, 194}

-- greekSmallLetterEtaWithYpogegrammeni BMPString ::= {0, 0, 31, 195}

-- greekSmallLetterEtaWithOxiaAndYpogegrammeni BMPString ::= {0, 0, 31, 196}

-- greekSmallLetterEtaWithPerispomeni BMPString ::= {0, 0, 31, 198}

-- greekSmallLetterEtaWithPerispomeniAndYpogegrammeni BMPString ::=
--   {0, 0, 31, 199}

-- greekCapitalLetterEpsilonWithVaria BMPString ::= {0, 0, 31, 200}

-- greekCapitalLetterEpsilonWithOxia BMPString ::= {0, 0, 31, 201}

-- greekCapitalLetterEtaWithVaria BMPString ::= {0, 0, 31, 202}

-- greekCapitalLetterEtaWithOxia BMPString ::= {0, 0, 31, 203}

-- greekCapitalLetterEtaWithProsgegrammeni BMPString ::= {0, 0, 31, 204}

-- greekPsiliAndVaria BMPString ::= {0, 0, 31, 205}

-- greekPsiliAndOxia BMPString ::= {0, 0, 31, 206}

-- greekPsiliAndPerispomeni BMPString ::= {0, 0, 31, 207}

-- greekSmallLetterIotaWithVrachy BMPString ::= {0, 0, 31, 208}

-- greekSmallLetterIotaWithMacron BMPString ::= {0, 0, 31, 209}

-- greekSmallLetterIotaWithDialytikaAndVaria BMPString ::= {0, 0, 31, 210}

-- greekSmallLetterIotaWithDialytikaAndOxia BMPString ::= {0, 0, 31, 211}

-- greekSmallLetterIotaWithPerispomeni BMPString ::= {0, 0, 31, 214}

-- greekSmallLetterIotaWithDialytikaAndPerispomeni BMPString ::= {0, 0, 31, 215}

-- greekCapitalLetterIotaWithVrachy BMPString ::= {0, 0, 31, 216}

-- greekCapitalLetterIotaWithMacron BMPString ::= {0, 0, 31, 217}

-- greekCapitalLetterIotaWithVaria BMPString ::= {0, 0, 31, 218}

-- greekCapitalLetterIotaWithOxia BMPString ::= {0, 0, 31, 219}

-- greekDasiaAndVaria BMPString ::= {0, 0, 31, 221}

-- greekDasiaAndOxia BMPString ::= {0, 0, 31, 222}

-- greekDasiaAndPerispomeni BMPString ::= {0, 0, 31, 223}

-- greekSmallLetterUpsilonWithVrachy BMPString ::= {0, 0, 31, 224}

-- greekSmallLetterUpsilonWithMacron BMPString ::= {0, 0, 31, 225}

-- greekSmallLetterUpsilonWithDialytikaAndVaria BMPString ::= {0, 0, 31, 226}

-- greekSmallLetterUpsilonWithDialytikaAndOxia BMPString ::= {0, 0, 31, 227}

-- greekSmallLetterRhoWithPsili BMPString ::= {0, 0, 31, 228}

-- greekSmallLetterRhoWithDasia BMPString ::= {0, 0, 31, 229}

-- greekSmallLetterUpsilonWithPerispomeni BMPString ::= {0, 0, 31, 230}

-- greekSmallLetterUpsilonWithDialytikaAndPerispomeni BMPString ::=
--   {0, 0, 31, 231}

-- greekCapitalLetterUpsilonWithVrachy BMPString ::= {0, 0, 31, 232}

-- greekCapitalLetterUpsilonWithMacron BMPString ::= {0, 0, 31, 233}

-- greekCapitalLetterUpsilonWithVaria BMPString ::= {0, 0, 31, 234}

-- greekCapitalLetterUpsilonWithOxia BMPString ::= {0, 0, 31, 235}

-- greekCapitalLetterRhoWithDasia BMPString ::= {0, 0, 31, 236}

-- greekDialytikaAndVaria BMPString ::= {0, 0, 31, 237}

-- greekDialytikaAndOxia BMPString ::= {0, 0, 31, 238}

-- greekVaria BMPString ::= {0, 0, 31, 239}

-- greekSmallLetterOmegaWithVariaAndYpogegrammeni BMPString ::= {0, 0, 31, 242}

-- greekSmallLetterOmegaWithYpogegrammeni BMPString ::= {0, 0, 31, 243}

-- greekSmallLetterOmegaWithOxiaAndYpogegrammeni BMPString ::= {0, 0, 31, 244}

-- greekSmallLetterOmegaWithPerispomeni BMPString ::= {0, 0, 31, 246}

-- greekSmallLetterOmegaWithPerispomeniAndYpogegrammeni BMPString ::=
--   {0, 0, 31, 247}

-- greekCapitalLetterOmicronWithVaria BMPString ::= {0, 0, 31, 248}

-- greekCapitalLetterOmicronWithOxia BMPString ::= {0, 0, 31, 249}

-- greekCapitalLetterOmegaWithVaria BMPString ::= {0, 0, 31, 250}

-- greekCapitalLetterOmegaWithOxia BMPString ::= {0, 0, 31, 251}

-- greekCapitalLetterOmegaWithProsgegrammeni BMPString ::= {0, 0, 31, 252}

-- greekOxia BMPString ::= {0, 0, 31, 253}

-- greekDasia BMPString ::= {0, 0, 31, 254}

-- enQuad BMPString ::= {0, 0, 32, 0}

-- emQuad BMPString ::= {0, 0, 32, 1}

-- enSpace BMPString ::= {0, 0, 32, 2}

-- emSpace BMPString ::= {0, 0, 32, 3}

-- three-per-emSpace BMPString ::= {0, 0, 32, 4}

-- four-per-emSpace BMPString ::= {0, 0, 32, 5}

-- six-per-emSpace BMPString ::= {0, 0, 32, 6}

-- figureSpace BMPString ::= {0, 0, 32, 7}

-- punctuationSpace BMPString ::= {0, 0, 32, 8}

-- thinSpace BMPString ::= {0, 0, 32, 9}

-- hairSpace BMPString ::= {0, 0, 32, 10}

-- zeroWidthSpace BMPString ::= {0, 0, 32, 11}

-- zeroWidthNon-joiner BMPString ::= {0, 0, 32, 12}

-- zeroWidthJoiner BMPString ::= {0, 0, 32, 13}

-- left-to-rightMark BMPString ::= {0, 0, 32, 14}

-- right-to-leftMark BMPString ::= {0, 0, 32, 15}

-- hyphen BMPString ::= {0, 0, 32, 16}

-- non-breakingHyphen BMPString ::= {0, 0, 32, 17}

-- figureDash BMPString ::= {0, 0, 32, 18}

-- enDash BMPString ::= {0, 0, 32, 19}

-- emDash BMPString ::= {0, 0, 32, 20}

-- horizontalBar BMPString ::= {0, 0, 32, 21}

-- doubleVerticalLine BMPString ::= {0, 0, 32, 22}

-- doubleLowLine BMPString ::= {0, 0, 32, 23}

-- leftSingleQuotationMark BMPString ::= {0, 0, 32, 24}

-- rightSingleQuotationMark BMPString ::= {0, 0, 32, 25}

-- singleLow-9QuotationMark BMPString ::= {0, 0, 32, 26}

-- singleHigh-reversed-9QuotationMark BMPString ::= {0, 0, 32, 27}

-- leftDoubleQuotationMark BMPString ::= {0, 0, 32, 28}

-- rightDoubleQuotationMark BMPString ::= {0, 0, 32, 29}

-- doubleLow-9QuotationMark BMPString ::= {0, 0, 32, 30}

-- doubleHigh-reversed-9QuotationMark BMPString ::= {0, 0, 32, 31}

-- dagger BMPString ::= {0, 0, 32, 32}

-- doubleDagger BMPString ::= {0, 0, 32, 33}

-- bullet BMPString ::= {0, 0, 32, 34}

-- triangularBullet BMPString ::= {0, 0, 32, 35}

-- oneDotLeader BMPString ::= {0, 0, 32, 36}

-- twoDotLeader BMPString ::= {0, 0, 32, 37}

-- horizontalEllipsis BMPString ::= {0, 0, 32, 38}

-- hyphenationPoint BMPString ::= {0, 0, 32, 39}

-- lineSeparator BMPString ::= {0, 0, 32, 40}

-- paragraphSeparator BMPString ::= {0, 0, 32, 41}

-- left-to-rightEmbedding BMPString ::= {0, 0, 32, 42}

-- right-to-leftEmbedding BMPString ::= {0, 0, 32, 43}

-- popDirectionalFormatting BMPString ::= {0, 0, 32, 44}

-- left-to-rightOverride BMPString ::= {0, 0, 32, 45}

-- right-to-leftOverride BMPString ::= {0, 0, 32, 46}

-- narrowNo-breakSpace BMPString ::= {0, 0, 32, 47}

-- perMilleSign BMPString ::= {0, 0, 32, 48}

-- perTenThousandSign BMPString ::= {0, 0, 32, 49}

-- prime BMPString ::= {0, 0, 32, 50}

-- doublePrime BMPString ::= {0, 0, 32, 51}

-- triplePrime BMPString ::= {0, 0, 32, 52}

-- reversedPrime BMPString ::= {0, 0, 32, 53}

-- reversedDoublePrime BMPString ::= {0, 0, 32, 54}

-- reversedTriplePrime BMPString ::= {0, 0, 32, 55}

-- caret BMPString ::= {0, 0, 32, 56}

-- singleLeft-pointingAngleQuotationMark BMPString ::= {0, 0, 32, 57}

-- singleRight-pointingAngleQuotationMark BMPString ::= {0, 0, 32, 58}

-- referenceMark BMPString ::= {0, 0, 32, 59}

-- doubleExclamationMark BMPString ::= {0, 0, 32, 60}

-- interrobang BMPString ::= {0, 0, 32, 61}

-- overline BMPString ::= {0, 0, 32, 62}

-- undertie BMPString ::= {0, 0, 32, 63}

-- characterTie BMPString ::= {0, 0, 32, 64}

-- caretInsertionPoint BMPString ::= {0, 0, 32, 65}

-- asterism BMPString ::= {0, 0, 32, 66}

-- hyphenBullet BMPString ::= {0, 0, 32, 67}

-- fractionSlash BMPString ::= {0, 0, 32, 68}

-- leftSquareBracketWithQuill BMPString ::= {0, 0, 32, 69}

-- rightSquareBracketWithQuill BMPString ::= {0, 0, 32, 70}

-- doubleQuestionMark BMPString ::= {0, 0, 32, 71}

-- questionExclamationMark BMPString ::= {0, 0, 32, 72}

-- exclamationQuestionMark BMPString ::= {0, 0, 32, 73}

-- tironianSignEt BMPString ::= {0, 0, 32, 74}

-- reversedPilcrowSign BMPString ::= {0, 0, 32, 75}

-- blackLeftwardsBullet BMPString ::= {0, 0, 32, 76}

-- blackRightwardsBullet BMPString ::= {0, 0, 32, 77}

-- lowAsterisk BMPString ::= {0, 0, 32, 78}

-- reversedSemicolon BMPString ::= {0, 0, 32, 79}

-- closeUp BMPString ::= {0, 0, 32, 80}

-- twoAsterisksAlignedVertically BMPString ::= {0, 0, 32, 81}

-- commercialMinusSign BMPString ::= {0, 0, 32, 82}

-- quadruplePrime BMPString ::= {0, 0, 32, 87}

-- mediumMathematicalSpace BMPString ::= {0, 0, 32, 95}

-- wordJoiner BMPString ::= {0, 0, 32, 96}

-- functionApplication BMPString ::= {0, 0, 32, 97}

-- invisibleTimes BMPString ::= {0, 0, 32, 98}

-- invisibleSeparator BMPString ::= {0, 0, 32, 99}

-- inhibitSymmetricSwapping BMPString ::= {0, 0, 32, 106}

-- activateSymmetricSwapping BMPString ::= {0, 0, 32, 107}

-- inhibitArabicFormShaping BMPString ::= {0, 0, 32, 108}

-- activateArabicFormShaping BMPString ::= {0, 0, 32, 109}

-- nationalDigitShapes BMPString ::= {0, 0, 32, 110}

-- nominalDigitShapes BMPString ::= {0, 0, 32, 111}

-- superscriptZero BMPString ::= {0, 0, 32, 112}

-- superscriptLatinSmallLetterI BMPString ::= {0, 0, 32, 113}

-- superscriptFour BMPString ::= {0, 0, 32, 116}

-- superscriptFive BMPString ::= {0, 0, 32, 117}

-- superscriptSix BMPString ::= {0, 0, 32, 118}

-- superscriptSeven BMPString ::= {0, 0, 32, 119}

-- superscriptEight BMPString ::= {0, 0, 32, 120}

-- superscriptNine BMPString ::= {0, 0, 32, 121}

-- superscriptPlusSign BMPString ::= {0, 0, 32, 122}

-- superscriptMinus BMPString ::= {0, 0, 32, 123}

-- superscriptEqualsSign BMPString ::= {0, 0, 32, 124}

-- superscriptLeftParenthesis BMPString ::= {0, 0, 32, 125}

-- superscriptRightParenthesis BMPString ::= {0, 0, 32, 126}

-- superscriptLatinSmallLetterN BMPString ::= {0, 0, 32, 127}

-- subscriptZero BMPString ::= {0, 0, 32, 128}

-- subscriptOne BMPString ::= {0, 0, 32, 129}

-- subscriptTwo BMPString ::= {0, 0, 32, 130}

-- subscriptThree BMPString ::= {0, 0, 32, 131}

-- subscriptFour BMPString ::= {0, 0, 32, 132}

-- subscriptFive BMPString ::= {0, 0, 32, 133}

-- subscriptSix BMPString ::= {0, 0, 32, 134}

-- subscriptSeven BMPString ::= {0, 0, 32, 135}

-- subscriptEight BMPString ::= {0, 0, 32, 136}

-- subscriptNine BMPString ::= {0, 0, 32, 137}

-- subscriptPlusSign BMPString ::= {0, 0, 32, 138}

-- subscriptMinus BMPString ::= {0, 0, 32, 139}

-- subscriptEqualsSign BMPString ::= {0, 0, 32, 140}

-- subscriptLeftParenthesis BMPString ::= {0, 0, 32, 141}

-- subscriptRightParenthesis BMPString ::= {0, 0, 32, 142}

-- euro-currencySign BMPString ::= {0, 0, 32, 160}

-- colonSign BMPString ::= {0, 0, 32, 161}

-- cruzeiroSign BMPString ::= {0, 0, 32, 162}

-- frenchFrancSign BMPString ::= {0, 0, 32, 163}

-- liraSign BMPString ::= {0, 0, 32, 164}

-- millSign BMPString ::= {0, 0, 32, 165}

-- nairaSign BMPString ::= {0, 0, 32, 166}

-- pesetaSign BMPString ::= {0, 0, 32, 167}

-- rupeeSign BMPString ::= {0, 0, 32, 168}

-- wonSign BMPString ::= {0, 0, 32, 169}

-- newSheqelSign BMPString ::= {0, 0, 32, 170}

-- dongSign BMPString ::= {0, 0, 32, 171}

-- euroSign BMPString ::= {0, 0, 32, 172}

-- kipSign BMPString ::= {0, 0, 32, 173}

-- tugrikSign BMPString ::= {0, 0, 32, 174}

-- drachmaSign BMPString ::= {0, 0, 32, 175}

-- germanPennySign BMPString ::= {0, 0, 32, 176}

-- pesoSign BMPString ::= {0, 0, 32, 177}

-- combiningLeftHarpoonAbove BMPString ::= {0, 0, 32, 208}

-- combiningRightHarpoonAbove BMPString ::= {0, 0, 32, 209}

-- combiningLongVerticalLineOverlay BMPString ::= {0, 0, 32, 210}

-- combiningShortVerticalLineOverlay BMPString ::= {0, 0, 32, 211}

-- combiningAnticlockwiseArrowAbove BMPString ::= {0, 0, 32, 212}

-- combiningClockwiseArrowAbove BMPString ::= {0, 0, 32, 213}

-- combiningLeftArrowAbove BMPString ::= {0, 0, 32, 214}

-- combiningRightArrowAbove BMPString ::= {0, 0, 32, 215}

-- combiningRingOverlay BMPString ::= {0, 0, 32, 216}

-- combiningClockwiseRingOverlay BMPString ::= {0, 0, 32, 217}

-- combiningAnticlockwiseRingOverlay BMPString ::= {0, 0, 32, 218}

-- combiningThreeDotsAbove BMPString ::= {0, 0, 32, 219}

-- combiningFourDotsAbove BMPString ::= {0, 0, 32, 220}

-- combiningEnclosingCircle BMPString ::= {0, 0, 32, 221}

-- combiningEnclosingSquare BMPString ::= {0, 0, 32, 222}

-- combiningEnclosingDiamond BMPString ::= {0, 0, 32, 223}

-- combiningEnclosingCircleBackslash BMPString ::= {0, 0, 32, 224}

-- combiningLeftRightArrowAbove BMPString ::= {0, 0, 32, 225}

-- combiningEnclosingScreen BMPString ::= {0, 0, 32, 226}

-- combiningEnclosingKeycap BMPString ::= {0, 0, 32, 227}

-- combiningEnclosingUpwardPointingTriangle BMPString ::= {0, 0, 32, 228}

-- combiningReverseSolidusOverlay BMPString ::= {0, 0, 32, 229}

-- combiningDoubleVerticalStrokeOverlay BMPString ::= {0, 0, 32, 230}

-- combiningAnnuitySymbol BMPString ::= {0, 0, 32, 231}

-- combiningTripleUnderdot BMPString ::= {0, 0, 32, 232}

-- combiningWideBridgeAbove BMPString ::= {0, 0, 32, 233}

-- combiningLeftwardsArrowOverlay BMPString ::= {0, 0, 32, 234}

-- accountOf BMPString ::= {0, 0, 33, 0}

-- addressedToTheSubject BMPString ::= {0, 0, 33, 1}

-- double-struckCapitalC BMPString ::= {0, 0, 33, 2}

-- degreeCelsius BMPString ::= {0, 0, 33, 3}

-- centreLineSymbol BMPString ::= {0, 0, 33, 4}

-- careOf BMPString ::= {0, 0, 33, 5}

-- cadaUna BMPString ::= {0, 0, 33, 6}

-- eulerConstant BMPString ::= {0, 0, 33, 7}

-- scruple BMPString ::= {0, 0, 33, 8}

-- degreeFahrenheit BMPString ::= {0, 0, 33, 9}

-- scriptSmallG BMPString ::= {0, 0, 33, 10}

-- scriptCapitalH BMPString ::= {0, 0, 33, 11}

-- black-letterCapitalH BMPString ::= {0, 0, 33, 12}

-- double-struckCapitalH BMPString ::= {0, 0, 33, 13}

-- planckConstant BMPString ::= {0, 0, 33, 14}

-- planckConstantOverTwoPi BMPString ::= {0, 0, 33, 15}

-- scriptCapitalI BMPString ::= {0, 0, 33, 16}

-- black-letterCapitalI BMPString ::= {0, 0, 33, 17}

-- scriptCapitalL BMPString ::= {0, 0, 33, 18}

-- scriptSmallL BMPString ::= {0, 0, 33, 19}

-- lBBarSymbol BMPString ::= {0, 0, 33, 20}

-- double-struckCapitalN BMPString ::= {0, 0, 33, 21}

-- numeroSign BMPString ::= {0, 0, 33, 22}

-- soundRecordingCopyright BMPString ::= {0, 0, 33, 23}

-- scriptCapitalP BMPString ::= {0, 0, 33, 24}

-- double-struckCapitalP BMPString ::= {0, 0, 33, 25}

-- double-struckCapitalQ BMPString ::= {0, 0, 33, 26}

-- scriptCapitalR BMPString ::= {0, 0, 33, 27}

-- black-letterCapitalR BMPString ::= {0, 0, 33, 28}

-- double-struckCapitalR BMPString ::= {0, 0, 33, 29}

-- prescriptionTake BMPString ::= {0, 0, 33, 30}

-- response BMPString ::= {0, 0, 33, 31}

-- serviceMark BMPString ::= {0, 0, 33, 32}

-- telephoneSign BMPString ::= {0, 0, 33, 33}

-- tradeMarkSign BMPString ::= {0, 0, 33, 34}

-- versicle BMPString ::= {0, 0, 33, 35}

-- double-struckCapitalZ BMPString ::= {0, 0, 33, 36}

-- ounceSign BMPString ::= {0, 0, 33, 37}

-- ohmSign BMPString ::= {0, 0, 33, 38}

-- invertedOhmSign BMPString ::= {0, 0, 33, 39}

-- black-letterCapitalZ BMPString ::= {0, 0, 33, 40}

-- turnedGreekSmallLetterIota BMPString ::= {0, 0, 33, 41}

-- kelvinSign BMPString ::= {0, 0, 33, 42}

-- angstromSign BMPString ::= {0, 0, 33, 43}

-- scriptCapitalB BMPString ::= {0, 0, 33, 44}

-- black-letterCapitalC BMPString ::= {0, 0, 33, 45}

-- estimatedSymbol BMPString ::= {0, 0, 33, 46}

-- scriptSmallE BMPString ::= {0, 0, 33, 47}

-- scriptCapitalE BMPString ::= {0, 0, 33, 48}

-- scriptCapitalF BMPString ::= {0, 0, 33, 49}

-- turnedCapitalF BMPString ::= {0, 0, 33, 50}

-- scriptCapitalM BMPString ::= {0, 0, 33, 51}

-- scriptSmallO BMPString ::= {0, 0, 33, 52}

-- alefSymbol BMPString ::= {0, 0, 33, 53}

-- betSymbol BMPString ::= {0, 0, 33, 54}

-- gimelSymbol BMPString ::= {0, 0, 33, 55}

-- daletSymbol BMPString ::= {0, 0, 33, 56}

-- informationSource BMPString ::= {0, 0, 33, 57}

-- rotatedCapitalQ BMPString ::= {0, 0, 33, 58}

-- double-struckSmallGamma BMPString ::= {0, 0, 33, 61}

-- double-struckCapitalGamma BMPString ::= {0, 0, 33, 62}

-- double-struckCapitalPi BMPString ::= {0, 0, 33, 63}

-- double-struckN-arySummation BMPString ::= {0, 0, 33, 64}

-- turnedSans-serifCapitalG BMPString ::= {0, 0, 33, 65}

-- turnedSans-serifCapitalL BMPString ::= {0, 0, 33, 66}

-- reversedSans-serifCapitalL BMPString ::= {0, 0, 33, 67}

-- turnedSans-serifCapitalY BMPString ::= {0, 0, 33, 68}

-- double-struckItalicCapitalD BMPString ::= {0, 0, 33, 69}

-- double-struckItalicSmallD BMPString ::= {0, 0, 33, 70}

-- double-struckItalicSmallE BMPString ::= {0, 0, 33, 71}

-- double-struckItalicSmallI BMPString ::= {0, 0, 33, 72}

-- double-struckItalicSmallJ BMPString ::= {0, 0, 33, 73}

-- propertyLine BMPString ::= {0, 0, 33, 74}

-- turnedAmpersand BMPString ::= {0, 0, 33, 75}

-- vulgarFractionOneThird BMPString ::= {0, 0, 33, 83}

-- vulgarFractionTwoThirds BMPString ::= {0, 0, 33, 84}

-- vulgarFractionOneFifth BMPString ::= {0, 0, 33, 85}

-- vulgarFractionTwoFifths BMPString ::= {0, 0, 33, 86}

-- vulgarFractionThreeFifths BMPString ::= {0, 0, 33, 87}

-- vulgarFractionFourFifths BMPString ::= {0, 0, 33, 88}

-- vulgarFractionOneSixth BMPString ::= {0, 0, 33, 89}

-- vulgarFractionFiveSixths BMPString ::= {0, 0, 33, 90}

-- vulgarFractionOneEighth BMPString ::= {0, 0, 33, 91}

-- vulgarFractionThreeEighths BMPString ::= {0, 0, 33, 92}

-- vulgarFractionFiveEighths BMPString ::= {0, 0, 33, 93}

-- vulgarFractionSevenEighths BMPString ::= {0, 0, 33, 94}

-- fractionNumeratorOne BMPString ::= {0, 0, 33, 95}

-- romanNumeralOne BMPString ::= {0, 0, 33, 96}

-- romanNumeralTwo BMPString ::= {0, 0, 33, 97}

-- romanNumeralThree BMPString ::= {0, 0, 33, 98}

-- romanNumeralFour BMPString ::= {0, 0, 33, 99}

-- romanNumeralFive BMPString ::= {0, 0, 33, 100}

-- romanNumeralSix BMPString ::= {0, 0, 33, 101}

-- romanNumeralSeven BMPString ::= {0, 0, 33, 102}

-- romanNumeralEight BMPString ::= {0, 0, 33, 103}

-- romanNumeralNine BMPString ::= {0, 0, 33, 104}

-- romanNumeralTen BMPString ::= {0, 0, 33, 105}

-- romanNumeralEleven BMPString ::= {0, 0, 33, 106}

-- romanNumeralTwelve BMPString ::= {0, 0, 33, 107}

-- romanNumeralFifty BMPString ::= {0, 0, 33, 108}

-- romanNumeralOneHundred BMPString ::= {0, 0, 33, 109}

-- romanNumeralFiveHundred BMPString ::= {0, 0, 33, 110}

-- romanNumeralOneThousand BMPString ::= {0, 0, 33, 111}

-- smallRomanNumeralOne BMPString ::= {0, 0, 33, 112}

-- smallRomanNumeralTwo BMPString ::= {0, 0, 33, 113}

-- smallRomanNumeralThree BMPString ::= {0, 0, 33, 114}

-- smallRomanNumeralFour BMPString ::= {0, 0, 33, 115}

-- smallRomanNumeralFive BMPString ::= {0, 0, 33, 116}

-- smallRomanNumeralSix BMPString ::= {0, 0, 33, 117}

-- smallRomanNumeralSeven BMPString ::= {0, 0, 33, 118}

-- smallRomanNumeralEight BMPString ::= {0, 0, 33, 119}

-- smallRomanNumeralNine BMPString ::= {0, 0, 33, 120}

-- smallRomanNumeralTen BMPString ::= {0, 0, 33, 121}

-- smallRomanNumeralEleven BMPString ::= {0, 0, 33, 122}

-- smallRomanNumeralTwelve BMPString ::= {0, 0, 33, 123}

-- smallRomanNumeralFifty BMPString ::= {0, 0, 33, 124}

-- smallRomanNumeralOneHundred BMPString ::= {0, 0, 33, 125}

-- smallRomanNumeralFiveHundred BMPString ::= {0, 0, 33, 126}

-- smallRomanNumeralOneThousand BMPString ::= {0, 0, 33, 127}

-- romanNumeralOneThousandCD BMPString ::= {0, 0, 33, 128}

-- romanNumeralFiveThousand BMPString ::= {0, 0, 33, 129}

-- romanNumeralTenThousand BMPString ::= {0, 0, 33, 130}

-- romanNumeralReversedOneHundred BMPString ::= {0, 0, 33, 131}

-- leftwardsArrow BMPString ::= {0, 0, 33, 144}

-- upwardsArrow BMPString ::= {0, 0, 33, 145}

-- rightwardsArrow BMPString ::= {0, 0, 33, 146}

-- downwardsArrow BMPString ::= {0, 0, 33, 147}

-- leftRightArrow BMPString ::= {0, 0, 33, 148}

-- upDownArrow BMPString ::= {0, 0, 33, 149}

-- northWestArrow BMPString ::= {0, 0, 33, 150}

-- northEastArrow BMPString ::= {0, 0, 33, 151}

-- southEastArrow BMPString ::= {0, 0, 33, 152}

-- southWestArrow BMPString ::= {0, 0, 33, 153}

-- leftwardsArrowWithStroke BMPString ::= {0, 0, 33, 154}

-- rightwardsArrowWithStroke BMPString ::= {0, 0, 33, 155}

-- leftwardsWaveArrow BMPString ::= {0, 0, 33, 156}

-- rightwardsWaveArrow BMPString ::= {0, 0, 33, 157}

-- leftwardsTwoHeadedArrow BMPString ::= {0, 0, 33, 158}

-- upwardsTwoHeadedArrow BMPString ::= {0, 0, 33, 159}

-- rightwardsTwoHeadedArrow BMPString ::= {0, 0, 33, 160}

-- downwardsTwoHeadedArrow BMPString ::= {0, 0, 33, 161}

-- leftwardsArrowWithTail BMPString ::= {0, 0, 33, 162}

-- rightwardsArrowWithTail BMPString ::= {0, 0, 33, 163}

-- leftwardsArrowFromBar BMPString ::= {0, 0, 33, 164}

-- upwardsArrowFromBar BMPString ::= {0, 0, 33, 165}

-- rightwardsArrowFromBar BMPString ::= {0, 0, 33, 166}

-- downwardsArrowFromBar BMPString ::= {0, 0, 33, 167}

-- upDownArrowWithBase BMPString ::= {0, 0, 33, 168}

-- leftwardsArrowWithHook BMPString ::= {0, 0, 33, 169}

-- rightwardsArrowWithHook BMPString ::= {0, 0, 33, 170}

-- leftwardsArrowWithLoop BMPString ::= {0, 0, 33, 171}

-- rightwardsArrowWithLoop BMPString ::= {0, 0, 33, 172}

-- leftRightWaveArrow BMPString ::= {0, 0, 33, 173}

-- leftRightArrowWithStroke BMPString ::= {0, 0, 33, 174}

-- downwardsZigzagArrow BMPString ::= {0, 0, 33, 175}

-- upwardsArrowWithTipLeftwards BMPString ::= {0, 0, 33, 176}

-- upwardsArrowWithTipRightwards BMPString ::= {0, 0, 33, 177}

-- downwardsArrowWithTipLeftwards BMPString ::= {0, 0, 33, 178}

-- downwardsArrowWithTipRightwards BMPString ::= {0, 0, 33, 179}

-- rightwardsArrowWithCornerDownwards BMPString ::= {0, 0, 33, 180}

-- downwardsArrowWithCornerLeftwards BMPString ::= {0, 0, 33, 181}

-- anticlockwiseTopSemicircleArrow BMPString ::= {0, 0, 33, 182}

-- clockwiseTopSemicircleArrow BMPString ::= {0, 0, 33, 183}

-- northWestArrowToLongBar BMPString ::= {0, 0, 33, 184}

-- leftwardsArrowToBarOverRightwardsArrowToBar BMPString ::= {0, 0, 33, 185}

-- anticlockwiseOpenCircleArrow BMPString ::= {0, 0, 33, 186}

-- clockwiseOpenCircleArrow BMPString ::= {0, 0, 33, 187}

-- leftwardsHarpoonWithBarbUpwards BMPString ::= {0, 0, 33, 188}

-- leftwardsHarpoonWithBarbDownwards BMPString ::= {0, 0, 33, 189}

-- upwardsHarpoonWithBarbRightwards BMPString ::= {0, 0, 33, 190}

-- upwardsHarpoonWithBarbLeftwards BMPString ::= {0, 0, 33, 191}

-- rightwardsHarpoonWithBarbUpwards BMPString ::= {0, 0, 33, 192}

-- rightwardsHarpoonWithBarbDownwards BMPString ::= {0, 0, 33, 193}

-- downwardsHarpoonWithBarbRightwards BMPString ::= {0, 0, 33, 194}

-- downwardsHarpoonWithBarbLeftwards BMPString ::= {0, 0, 33, 195}

-- rightwardsArrowOverLeftwardsArrow BMPString ::= {0, 0, 33, 196}

-- upwardsArrowLeftwardsOfDownwardsArrow BMPString ::= {0, 0, 33, 197}

-- leftwardsArrowOverRightwardsArrow BMPString ::= {0, 0, 33, 198}

-- leftwardsPairedArrows BMPString ::= {0, 0, 33, 199}

-- upwardsPairedArrows BMPString ::= {0, 0, 33, 200}

-- rightwardsPairedArrows BMPString ::= {0, 0, 33, 201}

-- downwardsPairedArrows BMPString ::= {0, 0, 33, 202}

-- leftwardsHarpoonOverRightwardsHarpoon BMPString ::= {0, 0, 33, 203}

-- rightwardsHarpoonOverLeftwardsHarpoon BMPString ::= {0, 0, 33, 204}

-- leftwardsDoubleArrowWithStroke BMPString ::= {0, 0, 33, 205}

-- leftRightDoubleArrowWithStroke BMPString ::= {0, 0, 33, 206}

-- rightwardsDoubleArrowWithStroke BMPString ::= {0, 0, 33, 207}

-- leftwardsDoubleArrow BMPString ::= {0, 0, 33, 208}

-- upwardsDoubleArrow BMPString ::= {0, 0, 33, 209}

-- rightwardsDoubleArrow BMPString ::= {0, 0, 33, 210}

-- downwardsDoubleArrow BMPString ::= {0, 0, 33, 211}

-- leftRightDoubleArrow BMPString ::= {0, 0, 33, 212}

-- upDownDoubleArrow BMPString ::= {0, 0, 33, 213}

-- northWestDoubleArrow BMPString ::= {0, 0, 33, 214}

-- northEastDoubleArrow BMPString ::= {0, 0, 33, 215}

-- southEastDoubleArrow BMPString ::= {0, 0, 33, 216}

-- southWestDoubleArrow BMPString ::= {0, 0, 33, 217}

-- leftwardsTripleArrow BMPString ::= {0, 0, 33, 218}

-- rightwardsTripleArrow BMPString ::= {0, 0, 33, 219}

-- leftwardsSquiggleArrow BMPString ::= {0, 0, 33, 220}

-- rightwardsSquiggleArrow BMPString ::= {0, 0, 33, 221}

-- upwardsArrowWithDoubleStroke BMPString ::= {0, 0, 33, 222}

-- downwardsArrowWithDoubleStroke BMPString ::= {0, 0, 33, 223}

-- leftwardsDashedArrow BMPString ::= {0, 0, 33, 224}

-- upwardsDashedArrow BMPString ::= {0, 0, 33, 225}

-- rightwardsDashedArrow BMPString ::= {0, 0, 33, 226}

-- downwardsDashedArrow BMPString ::= {0, 0, 33, 227}

-- leftwardsArrowToBar BMPString ::= {0, 0, 33, 228}

-- rightwardsArrowToBar BMPString ::= {0, 0, 33, 229}

-- leftwardsWhiteArrow BMPString ::= {0, 0, 33, 230}

-- upwardsWhiteArrow BMPString ::= {0, 0, 33, 231}

-- rightwardsWhiteArrow BMPString ::= {0, 0, 33, 232}

-- downwardsWhiteArrow BMPString ::= {0, 0, 33, 233}

-- upwardsWhiteArrowFromBar BMPString ::= {0, 0, 33, 234}

-- upwardsWhiteArrowOnPedestal BMPString ::= {0, 0, 33, 235}

-- upwardsWhiteArrowOnPedestalWithHorizontalBar BMPString ::= {0, 0, 33, 236}

-- upwardsWhiteArrowOnPedestalWithVerticalBar BMPString ::= {0, 0, 33, 237}

-- upwardsWhiteDoubleArrow BMPString ::= {0, 0, 33, 238}

-- upwardsWhiteDoubleArrowOnPedestal BMPString ::= {0, 0, 33, 239}

-- rightwardsWhiteArrowFromWall BMPString ::= {0, 0, 33, 240}

-- northWestArrowToCorner BMPString ::= {0, 0, 33, 241}

-- southEastArrowToCorner BMPString ::= {0, 0, 33, 242}

-- upDownWhiteArrow BMPString ::= {0, 0, 33, 243}

-- rightArrowWithSmallCircle BMPString ::= {0, 0, 33, 244}

-- downwardsArrowLeftwardsOfUpwardsArrow BMPString ::= {0, 0, 33, 245}

-- threeRightwardsArrows BMPString ::= {0, 0, 33, 246}

-- leftwardsArrowWithVerticalStroke BMPString ::= {0, 0, 33, 247}

-- rightwardsArrowWithVerticalStroke BMPString ::= {0, 0, 33, 248}

-- leftRightArrowWithVerticalStroke BMPString ::= {0, 0, 33, 249}

-- leftwardsArrowWithDoubleVerticalStroke BMPString ::= {0, 0, 33, 250}

-- rightwardsArrowWithDoubleVerticalStroke BMPString ::= {0, 0, 33, 251}

-- leftRightArrowWithDoubleVerticalStroke BMPString ::= {0, 0, 33, 252}

-- leftwardsOpen-headedArrow BMPString ::= {0, 0, 33, 253}

-- rightwardsOpen-headedArrow BMPString ::= {0, 0, 33, 254}

-- leftRightOpen-headedArrow BMPString ::= {0, 0, 33, 255}

-- forAll BMPString ::= {0, 0, 34, 0}

-- complement BMPString ::= {0, 0, 34, 1}

-- partialDifferential BMPString ::= {0, 0, 34, 2}

-- thereExists BMPString ::= {0, 0, 34, 3}

-- thereDoesNotExist BMPString ::= {0, 0, 34, 4}

-- emptySet BMPString ::= {0, 0, 34, 5}

-- increment BMPString ::= {0, 0, 34, 6}

-- nabla BMPString ::= {0, 0, 34, 7}

-- elementOf BMPString ::= {0, 0, 34, 8}

-- notAnElementOf BMPString ::= {0, 0, 34, 9}

-- smallElementOf BMPString ::= {0, 0, 34, 10}

-- containsAsMember BMPString ::= {0, 0, 34, 11}

-- doesNotContainAsMember BMPString ::= {0, 0, 34, 12}

-- smallContainsAsMember BMPString ::= {0, 0, 34, 13}

-- endOfProof BMPString ::= {0, 0, 34, 14}

-- n-aryProduct BMPString ::= {0, 0, 34, 15}

-- n-aryCoproduct BMPString ::= {0, 0, 34, 16}

-- n-arySummation BMPString ::= {0, 0, 34, 17}

-- minusSign BMPString ::= {0, 0, 34, 18}

-- minus-or-plusSign BMPString ::= {0, 0, 34, 19}

-- dotPlus BMPString ::= {0, 0, 34, 20}

-- divisionSlash BMPString ::= {0, 0, 34, 21}

-- setMinus BMPString ::= {0, 0, 34, 22}

-- asteriskOperator BMPString ::= {0, 0, 34, 23}

-- ringOperator BMPString ::= {0, 0, 34, 24}

-- bulletOperator BMPString ::= {0, 0, 34, 25}

-- squareRoot BMPString ::= {0, 0, 34, 26}

-- cubeRoot BMPString ::= {0, 0, 34, 27}

-- fourthRoot BMPString ::= {0, 0, 34, 28}

-- proportionalTo BMPString ::= {0, 0, 34, 29}

-- infinity BMPString ::= {0, 0, 34, 30}

-- rightAngle BMPString ::= {0, 0, 34, 31}

-- angle BMPString ::= {0, 0, 34, 32}

-- measuredAngle BMPString ::= {0, 0, 34, 33}

-- sphericalAngle BMPString ::= {0, 0, 34, 34}

-- divides BMPString ::= {0, 0, 34, 35}

-- doesNotDivide BMPString ::= {0, 0, 34, 36}

-- parallelTo BMPString ::= {0, 0, 34, 37}

-- notParallelTo BMPString ::= {0, 0, 34, 38}

-- logicalAnd BMPString ::= {0, 0, 34, 39}

-- logicalOr BMPString ::= {0, 0, 34, 40}

-- intersection BMPString ::= {0, 0, 34, 41}

-- union BMPString ::= {0, 0, 34, 42}

-- integral BMPString ::= {0, 0, 34, 43}

-- doubleIntegral BMPString ::= {0, 0, 34, 44}

-- tripleIntegral BMPString ::= {0, 0, 34, 45}

-- contourIntegral BMPString ::= {0, 0, 34, 46}

-- surfaceIntegral BMPString ::= {0, 0, 34, 47}

-- volumeIntegral BMPString ::= {0, 0, 34, 48}

-- clockwiseIntegral BMPString ::= {0, 0, 34, 49}

-- clockwiseContourIntegral BMPString ::= {0, 0, 34, 50}

-- anticlockwiseContourIntegral BMPString ::= {0, 0, 34, 51}

-- therefore BMPString ::= {0, 0, 34, 52}

-- because BMPString ::= {0, 0, 34, 53}

-- ratio BMPString ::= {0, 0, 34, 54}

-- proportion BMPString ::= {0, 0, 34, 55}

-- dotMinus BMPString ::= {0, 0, 34, 56}

-- excess BMPString ::= {0, 0, 34, 57}

-- geometricProportion BMPString ::= {0, 0, 34, 58}

-- homothetic BMPString ::= {0, 0, 34, 59}

-- tildeOperator BMPString ::= {0, 0, 34, 60}

-- reversedTilde BMPString ::= {0, 0, 34, 61}

-- invertedLazyS BMPString ::= {0, 0, 34, 62}

-- sineWave BMPString ::= {0, 0, 34, 63}

-- wreathProduct BMPString ::= {0, 0, 34, 64}

-- notTilde BMPString ::= {0, 0, 34, 65}

-- minusTilde BMPString ::= {0, 0, 34, 66}

-- asymptoticallyEqualTo BMPString ::= {0, 0, 34, 67}

-- notAsymptoticallyEqualTo BMPString ::= {0, 0, 34, 68}

-- approximatelyEqualTo BMPString ::= {0, 0, 34, 69}

-- approximatelyButNotActuallyEqualTo BMPString ::= {0, 0, 34, 70}

-- neitherApproximatelyNorActuallyEqualTo BMPString ::= {0, 0, 34, 71}

-- almostEqualTo BMPString ::= {0, 0, 34, 72}

-- notAlmostEqualTo BMPString ::= {0, 0, 34, 73}

-- almostEqualOrEqualTo BMPString ::= {0, 0, 34, 74}

-- tripleTilde BMPString ::= {0, 0, 34, 75}

-- allEqualTo BMPString ::= {0, 0, 34, 76}

-- equivalentTo BMPString ::= {0, 0, 34, 77}

-- geometricallyEquivalentTo BMPString ::= {0, 0, 34, 78}

-- differenceBetween BMPString ::= {0, 0, 34, 79}

-- approachesTheLimit BMPString ::= {0, 0, 34, 80}

-- geometricallyEqualTo BMPString ::= {0, 0, 34, 81}

-- approximatelyEqualToOrTheImageOf BMPString ::= {0, 0, 34, 82}

-- imageOfOrApproximatelyEqualTo BMPString ::= {0, 0, 34, 83}

-- colonEquals BMPString ::= {0, 0, 34, 84}

-- equalsColon BMPString ::= {0, 0, 34, 85}

-- ringInEqualTo BMPString ::= {0, 0, 34, 86}

-- ringEqualTo BMPString ::= {0, 0, 34, 87}

-- correspondsTo BMPString ::= {0, 0, 34, 88}

-- estimates BMPString ::= {0, 0, 34, 89}

-- equiangularTo BMPString ::= {0, 0, 34, 90}

-- starEquals BMPString ::= {0, 0, 34, 91}

-- deltaEqualTo BMPString ::= {0, 0, 34, 92}

-- equalToByDefinition BMPString ::= {0, 0, 34, 93}

-- measuredBy BMPString ::= {0, 0, 34, 94}

-- questionedEqualTo BMPString ::= {0, 0, 34, 95}

-- notEqualTo BMPString ::= {0, 0, 34, 96}

-- identicalTo BMPString ::= {0, 0, 34, 97}

-- notIdenticalTo BMPString ::= {0, 0, 34, 98}

-- strictlyEquivalentTo BMPString ::= {0, 0, 34, 99}

-- less-thanOrEqualTo BMPString ::= {0, 0, 34, 100}

-- greater-thanOrEqualTo BMPString ::= {0, 0, 34, 101}

-- less-thanOverEqualTo BMPString ::= {0, 0, 34, 102}

-- greater-thanOverEqualTo BMPString ::= {0, 0, 34, 103}

-- less-thanButNotEqualTo BMPString ::= {0, 0, 34, 104}

-- greater-thanButNotEqualTo BMPString ::= {0, 0, 34, 105}

-- muchLess-than BMPString ::= {0, 0, 34, 106}

-- muchGreater-than BMPString ::= {0, 0, 34, 107}

-- between BMPString ::= {0, 0, 34, 108}

-- notEquivalentTo BMPString ::= {0, 0, 34, 109}

-- notLess-than BMPString ::= {0, 0, 34, 110}

-- notGreater-than BMPString ::= {0, 0, 34, 111}

-- neitherLess-thanNorEqualTo BMPString ::= {0, 0, 34, 112}

-- neitherGreater-thanNorEqualTo BMPString ::= {0, 0, 34, 113}

-- less-thanOrEquivalentTo BMPString ::= {0, 0, 34, 114}

-- greater-thanOrEquivalentTo BMPString ::= {0, 0, 34, 115}

-- neitherLess-thanNorEquivalentTo BMPString ::= {0, 0, 34, 116}

-- neitherGreater-thanNorEquivalentTo BMPString ::= {0, 0, 34, 117}

-- less-thanOrGreater-than BMPString ::= {0, 0, 34, 118}

-- greater-thanOrLess-than BMPString ::= {0, 0, 34, 119}

-- neitherLess-thanNorGreater-than BMPString ::= {0, 0, 34, 120}

-- neitherGreater-thanNorLess-than BMPString ::= {0, 0, 34, 121}

-- precedes BMPString ::= {0, 0, 34, 122}

-- succeeds BMPString ::= {0, 0, 34, 123}

-- precedesOrEqualTo BMPString ::= {0, 0, 34, 124}

-- succeedsOrEqualTo BMPString ::= {0, 0, 34, 125}

-- precedesOrEquivalentTo BMPString ::= {0, 0, 34, 126}

-- succeedsOrEquivalentTo BMPString ::= {0, 0, 34, 127}

-- doesNotPrecede BMPString ::= {0, 0, 34, 128}

-- doesNotSucceed BMPString ::= {0, 0, 34, 129}

-- subsetOf BMPString ::= {0, 0, 34, 130}

-- supersetOf BMPString ::= {0, 0, 34, 131}

-- notASubsetOf BMPString ::= {0, 0, 34, 132}

-- notASupersetOf BMPString ::= {0, 0, 34, 133}

-- subsetOfOrEqualTo BMPString ::= {0, 0, 34, 134}

-- supersetOfOrEqualTo BMPString ::= {0, 0, 34, 135}

-- neitherASubsetOfNorEqualTo BMPString ::= {0, 0, 34, 136}

-- neitherASupersetOfNorEqualTo BMPString ::= {0, 0, 34, 137}

-- subsetOfWithNotEqualTo BMPString ::= {0, 0, 34, 138}

-- supersetOfWithNotEqualTo BMPString ::= {0, 0, 34, 139}

-- multiset BMPString ::= {0, 0, 34, 140}

-- multisetMultiplication BMPString ::= {0, 0, 34, 141}

-- multisetUnion BMPString ::= {0, 0, 34, 142}

-- squareImageOf BMPString ::= {0, 0, 34, 143}

-- squareOriginalOf BMPString ::= {0, 0, 34, 144}

-- squareImageOfOrEqualTo BMPString ::= {0, 0, 34, 145}

-- squareOriginalOfOrEqualTo BMPString ::= {0, 0, 34, 146}

-- squareCap BMPString ::= {0, 0, 34, 147}

-- squareCup BMPString ::= {0, 0, 34, 148}

-- circledPlus BMPString ::= {0, 0, 34, 149}

-- circledMinus BMPString ::= {0, 0, 34, 150}

-- circledTimes BMPString ::= {0, 0, 34, 151}

-- circledDivisionSlash BMPString ::= {0, 0, 34, 152}

-- circledDotOperator BMPString ::= {0, 0, 34, 153}

-- circledRingOperator BMPString ::= {0, 0, 34, 154}

-- circledAsteriskOperator BMPString ::= {0, 0, 34, 155}

-- circledEquals BMPString ::= {0, 0, 34, 156}

-- circledDash BMPString ::= {0, 0, 34, 157}

-- squaredPlus BMPString ::= {0, 0, 34, 158}

-- squaredMinus BMPString ::= {0, 0, 34, 159}

-- squaredTimes BMPString ::= {0, 0, 34, 160}

-- squaredDotOperator BMPString ::= {0, 0, 34, 161}

-- rightTack BMPString ::= {0, 0, 34, 162}

-- leftTack BMPString ::= {0, 0, 34, 163}

-- downTack BMPString ::= {0, 0, 34, 164}

-- upTack BMPString ::= {0, 0, 34, 165}

-- assertion BMPString ::= {0, 0, 34, 166}

-- models BMPString ::= {0, 0, 34, 167}

-- true BMPString ::= {0, 0, 34, 168}

-- forces BMPString ::= {0, 0, 34, 169}

-- tripleVerticalBarRightTurnstile BMPString ::= {0, 0, 34, 170}

-- doubleVerticalBarDoubleRightTurnstile BMPString ::= {0, 0, 34, 171}

-- doesNotProve BMPString ::= {0, 0, 34, 172}

-- notTrue BMPString ::= {0, 0, 34, 173}

-- doesNotForce BMPString ::= {0, 0, 34, 174}

-- negatedDoubleVerticalBarDoubleRightTurnstile BMPString ::= {0, 0, 34, 175}

-- precedesUnderRelation BMPString ::= {0, 0, 34, 176}

-- succeedsUnderRelation BMPString ::= {0, 0, 34, 177}

-- normalSubgroupOf BMPString ::= {0, 0, 34, 178}

-- containsAsNormalSubgroup BMPString ::= {0, 0, 34, 179}

-- normalSubgroupOfOrEqualTo BMPString ::= {0, 0, 34, 180}

-- containsAsNormalSubgroupOrEqualTo BMPString ::= {0, 0, 34, 181}

-- originalOf BMPString ::= {0, 0, 34, 182}

-- imageOf BMPString ::= {0, 0, 34, 183}

-- multimap BMPString ::= {0, 0, 34, 184}

-- hermitianConjugateMatrix BMPString ::= {0, 0, 34, 185}

-- intercalate BMPString ::= {0, 0, 34, 186}

-- xor BMPString ::= {0, 0, 34, 187}

-- nand BMPString ::= {0, 0, 34, 188}

-- nor BMPString ::= {0, 0, 34, 189}

-- rightAngleWithArc BMPString ::= {0, 0, 34, 190}

-- rightTriangle BMPString ::= {0, 0, 34, 191}

-- n-aryLogicalAnd BMPString ::= {0, 0, 34, 192}

-- n-aryLogicalOr BMPString ::= {0, 0, 34, 193}

-- n-aryIntersection BMPString ::= {0, 0, 34, 194}

-- n-aryUnion BMPString ::= {0, 0, 34, 195}

-- diamondOperator BMPString ::= {0, 0, 34, 196}

-- dotOperator BMPString ::= {0, 0, 34, 197}

-- starOperator BMPString ::= {0, 0, 34, 198}

-- divisionTimes BMPString ::= {0, 0, 34, 199}

-- bowtie BMPString ::= {0, 0, 34, 200}

-- leftNormalFactorSemidirectProduct BMPString ::= {0, 0, 34, 201}

-- rightNormalFactorSemidirectProduct BMPString ::= {0, 0, 34, 202}

-- leftSemidirectProduct BMPString ::= {0, 0, 34, 203}

-- rightSemidirectProduct BMPString ::= {0, 0, 34, 204}

-- reversedTildeEquals BMPString ::= {0, 0, 34, 205}

-- curlyLogicalOr BMPString ::= {0, 0, 34, 206}

-- curlyLogicalAnd BMPString ::= {0, 0, 34, 207}

-- doubleSubset BMPString ::= {0, 0, 34, 208}

-- doubleSuperset BMPString ::= {0, 0, 34, 209}

-- doubleIntersection BMPString ::= {0, 0, 34, 210}

-- doubleUnion BMPString ::= {0, 0, 34, 211}

-- pitchfork BMPString ::= {0, 0, 34, 212}

-- equalAndParallelTo BMPString ::= {0, 0, 34, 213}

-- less-thanWithDot BMPString ::= {0, 0, 34, 214}

-- greater-thanWithDot BMPString ::= {0, 0, 34, 215}

-- veryMuchLess-than BMPString ::= {0, 0, 34, 216}

-- veryMuchGreater-than BMPString ::= {0, 0, 34, 217}

-- less-thanEqualToOrGreater-than BMPString ::= {0, 0, 34, 218}

-- greater-thanEqualToOrLess-than BMPString ::= {0, 0, 34, 219}

-- equalToOrLess-than BMPString ::= {0, 0, 34, 220}

-- equalToOrGreater-than BMPString ::= {0, 0, 34, 221}

-- equalToOrPrecedes BMPString ::= {0, 0, 34, 222}

-- equalToOrSucceeds BMPString ::= {0, 0, 34, 223}

-- doesNotPrecedeOrEqual BMPString ::= {0, 0, 34, 224}

-- doesNotSucceedOrEqual BMPString ::= {0, 0, 34, 225}

-- notSquareImageOfOrEqualTo BMPString ::= {0, 0, 34, 226}

-- notSquareOriginalOfOrEqualTo BMPString ::= {0, 0, 34, 227}

-- squareImageOfOrNotEqualTo BMPString ::= {0, 0, 34, 228}

-- squareOriginalOfOrNotEqualTo BMPString ::= {0, 0, 34, 229}

-- less-thanButNotEquivalentTo BMPString ::= {0, 0, 34, 230}

-- greater-thanButNotEquivalentTo BMPString ::= {0, 0, 34, 231}

-- precedesButNotEquivalentTo BMPString ::= {0, 0, 34, 232}

-- succeedsButNotEquivalentTo BMPString ::= {0, 0, 34, 233}

-- notNormalSubgroupOf BMPString ::= {0, 0, 34, 234}

-- doesNotContainAsNormalSubgroup BMPString ::= {0, 0, 34, 235}

-- notNormalSubgroupOfOrEqualTo BMPString ::= {0, 0, 34, 236}

-- doesNotContainAsNormalSubgroupOrEqual BMPString ::= {0, 0, 34, 237}

-- verticalEllipsis BMPString ::= {0, 0, 34, 238}

-- midlineHorizontalEllipsis BMPString ::= {0, 0, 34, 239}

-- upRightDiagonalEllipsis BMPString ::= {0, 0, 34, 240}

-- downRightDiagonalEllipsis BMPString ::= {0, 0, 34, 241}

-- elementOfWithLongHorizontalStroke BMPString ::= {0, 0, 34, 242}

-- elementOfWithVerticalBarAtEndOfHorizontalStroke BMPString ::= {0, 0, 34, 243}

-- smallElementOfWithVerticalBarAtEndOfHorizontalStroke BMPString ::=
--   {0, 0, 34, 244}

-- elementOfWithDotAbove BMPString ::= {0, 0, 34, 245}

-- elementOfWithOverbar BMPString ::= {0, 0, 34, 246}

-- smallElementOfWithOverbar BMPString ::= {0, 0, 34, 247}

-- elementOfWithUnderbar BMPString ::= {0, 0, 34, 248}

-- elementOfWithTwoHorizontalStrokes BMPString ::= {0, 0, 34, 249}

-- containsWithLongHorizontalStroke BMPString ::= {0, 0, 34, 250}

-- containsWithVerticalBarAtEndOfHorizontalStroke BMPString ::= {0, 0, 34, 251}

-- smallContainsWithVerticalBarAtEndOfHorizontalStroke BMPString ::=
--   {0, 0, 34, 252}

-- containsWithOverbar BMPString ::= {0, 0, 34, 253}

-- smallContainsWithOverbar BMPString ::= {0, 0, 34, 254}

-- zNotationBagMembership BMPString ::= {0, 0, 34, 255}

-- diameterSign BMPString ::= {0, 0, 35, 0}

-- electricArrow BMPString ::= {0, 0, 35, 1}

-- house BMPString ::= {0, 0, 35, 2}

-- upArrowhead BMPString ::= {0, 0, 35, 3}

-- downArrowhead BMPString ::= {0, 0, 35, 4}

-- projective BMPString ::= {0, 0, 35, 5}

-- perspective BMPString ::= {0, 0, 35, 6}

-- wavyLine BMPString ::= {0, 0, 35, 7}

-- leftCeiling BMPString ::= {0, 0, 35, 8}

-- rightCeiling BMPString ::= {0, 0, 35, 9}

-- leftFloor BMPString ::= {0, 0, 35, 10}

-- rightFloor BMPString ::= {0, 0, 35, 11}

-- bottomRightCrop BMPString ::= {0, 0, 35, 12}

-- bottomLeftCrop BMPString ::= {0, 0, 35, 13}

-- topRightCrop BMPString ::= {0, 0, 35, 14}

-- topLeftCrop BMPString ::= {0, 0, 35, 15}

-- reversedNotSign BMPString ::= {0, 0, 35, 16}

-- squareLozenge BMPString ::= {0, 0, 35, 17}

-- arc BMPString ::= {0, 0, 35, 18}

-- segment BMPString ::= {0, 0, 35, 19}

-- sector BMPString ::= {0, 0, 35, 20}

-- telephoneRecorder BMPString ::= {0, 0, 35, 21}

-- positionIndicator BMPString ::= {0, 0, 35, 22}

-- viewdataSquare BMPString ::= {0, 0, 35, 23}

-- placeOfInterestSign BMPString ::= {0, 0, 35, 24}

-- turnedNotSign BMPString ::= {0, 0, 35, 25}

-- watch BMPString ::= {0, 0, 35, 26}

-- hourglass BMPString ::= {0, 0, 35, 27}

-- topLeftCorner BMPString ::= {0, 0, 35, 28}

-- topRightCorner BMPString ::= {0, 0, 35, 29}

-- bottomLeftCorner BMPString ::= {0, 0, 35, 30}

-- bottomRightCorner BMPString ::= {0, 0, 35, 31}

-- topHalfIntegral BMPString ::= {0, 0, 35, 32}

-- bottomHalfIntegral BMPString ::= {0, 0, 35, 33}

-- frown BMPString ::= {0, 0, 35, 34}

-- smile BMPString ::= {0, 0, 35, 35}

-- upArrowheadBetweenTwoHorizontalBars BMPString ::= {0, 0, 35, 36}

-- optionKey BMPString ::= {0, 0, 35, 37}

-- eraseToTheRight BMPString ::= {0, 0, 35, 38}

-- xInARectangleBox BMPString ::= {0, 0, 35, 39}

-- keyboard BMPString ::= {0, 0, 35, 40}

-- left-pointingAngleBracket BMPString ::= {0, 0, 35, 41}

-- right-pointingAngleBracket BMPString ::= {0, 0, 35, 42}

-- eraseToTheLeft BMPString ::= {0, 0, 35, 43}

-- benzeneRing BMPString ::= {0, 0, 35, 44}

-- cylindricity BMPString ::= {0, 0, 35, 45}

-- allAround-profile BMPString ::= {0, 0, 35, 46}

-- symmetry BMPString ::= {0, 0, 35, 47}

-- totalRunout BMPString ::= {0, 0, 35, 48}

-- dimensionOrigin BMPString ::= {0, 0, 35, 49}

-- conicalTaper BMPString ::= {0, 0, 35, 50}

-- slope BMPString ::= {0, 0, 35, 51}

-- counterbore BMPString ::= {0, 0, 35, 52}

-- countersink BMPString ::= {0, 0, 35, 53}

-- aplFunctionalSymbolI-beam BMPString ::= {0, 0, 35, 54}

-- aplFunctionalSymbolSquishQuad BMPString ::= {0, 0, 35, 55}

-- aplFunctionalSymbolQuadEqual BMPString ::= {0, 0, 35, 56}

-- aplFunctionalSymbolQuadDivide BMPString ::= {0, 0, 35, 57}

-- aplFunctionalSymbolQuadDiamond BMPString ::= {0, 0, 35, 58}

-- aplFunctionalSymbolQuadJot BMPString ::= {0, 0, 35, 59}

-- aplFunctionalSymbolQuadCircle BMPString ::= {0, 0, 35, 60}

-- aplFunctionalSymbolCircleStile BMPString ::= {0, 0, 35, 61}

-- aplFunctionalSymbolCircleJot BMPString ::= {0, 0, 35, 62}

-- aplFunctionalSymbolSlashBar BMPString ::= {0, 0, 35, 63}

-- aplFunctionalSymbolBackslashBar BMPString ::= {0, 0, 35, 64}

-- aplFunctionalSymbolQuadSlash BMPString ::= {0, 0, 35, 65}

-- aplFunctionalSymbolQuadBackslash BMPString ::= {0, 0, 35, 66}

-- aplFunctionalSymbolQuadLess-than BMPString ::= {0, 0, 35, 67}

-- aplFunctionalSymbolQuadGreater-than BMPString ::= {0, 0, 35, 68}

-- aplFunctionalSymbolLeftwardsVane BMPString ::= {0, 0, 35, 69}

-- aplFunctionalSymbolRightwardsVane BMPString ::= {0, 0, 35, 70}

-- aplFunctionalSymbolQuadLeftwardsArrow BMPString ::= {0, 0, 35, 71}

-- aplFunctionalSymbolQuadRightwardsArrow BMPString ::= {0, 0, 35, 72}

-- aplFunctionalSymbolCircleBackslash BMPString ::= {0, 0, 35, 73}

-- aplFunctionalSymbolDownTackUnderbar BMPString ::= {0, 0, 35, 74}

-- aplFunctionalSymbolDeltaStile BMPString ::= {0, 0, 35, 75}

-- aplFunctionalSymbolQuadDownCaret BMPString ::= {0, 0, 35, 76}

-- aplFunctionalSymbolQuadDelta BMPString ::= {0, 0, 35, 77}

-- aplFunctionalSymbolDownTackJot BMPString ::= {0, 0, 35, 78}

-- aplFunctionalSymbolUpwardsVane BMPString ::= {0, 0, 35, 79}

-- aplFunctionalSymbolQuadUpwardsArrow BMPString ::= {0, 0, 35, 80}

-- aplFunctionalSymbolUpTackOverbar BMPString ::= {0, 0, 35, 81}

-- aplFunctionalSymbolDelStile BMPString ::= {0, 0, 35, 82}

-- aplFunctionalSymbolQuadUpCaret BMPString ::= {0, 0, 35, 83}

-- aplFunctionalSymbolQuadDel BMPString ::= {0, 0, 35, 84}

-- aplFunctionalSymbolUpTackJot BMPString ::= {0, 0, 35, 85}

-- aplFunctionalSymbolDownwardsVane BMPString ::= {0, 0, 35, 86}

-- aplFunctionalSymbolQuadDownwardsArrow BMPString ::= {0, 0, 35, 87}

-- aplFunctionalSymbolQuoteUnderbar BMPString ::= {0, 0, 35, 88}

-- aplFunctionalSymbolDeltaUnderbar BMPString ::= {0, 0, 35, 89}

-- aplFunctionalSymbolDiamondUnderbar BMPString ::= {0, 0, 35, 90}

-- aplFunctionalSymbolJotUnderbar BMPString ::= {0, 0, 35, 91}

-- aplFunctionalSymbolCircleUnderbar BMPString ::= {0, 0, 35, 92}

-- aplFunctionalSymbolUpShoeJot BMPString ::= {0, 0, 35, 93}

-- aplFunctionalSymbolQuoteQuad BMPString ::= {0, 0, 35, 94}

-- aplFunctionalSymbolCircleStar BMPString ::= {0, 0, 35, 95}

-- aplFunctionalSymbolQuadColon BMPString ::= {0, 0, 35, 96}

-- aplFunctionalSymbolUpTackDiaeresis BMPString ::= {0, 0, 35, 97}

-- aplFunctionalSymbolDelDiaeresis BMPString ::= {0, 0, 35, 98}

-- aplFunctionalSymbolStarDiaeresis BMPString ::= {0, 0, 35, 99}

-- aplFunctionalSymbolJotDiaeresis BMPString ::= {0, 0, 35, 100}

-- aplFunctionalSymbolCircleDiaeresis BMPString ::= {0, 0, 35, 101}

-- aplFunctionalSymbolDownShoeStile BMPString ::= {0, 0, 35, 102}

-- aplFunctionalSymbolLeftShoeStile BMPString ::= {0, 0, 35, 103}

-- aplFunctionalSymbolTildeDiaeresis BMPString ::= {0, 0, 35, 104}

-- aplFunctionalSymbolGreater-thanDiaeresis BMPString ::= {0, 0, 35, 105}

-- aplFunctionalSymbolCommaBar BMPString ::= {0, 0, 35, 106}

-- aplFunctionalSymbolDelTilde BMPString ::= {0, 0, 35, 107}

-- aplFunctionalSymbolZilde BMPString ::= {0, 0, 35, 108}

-- aplFunctionalSymbolStileTilde BMPString ::= {0, 0, 35, 109}

-- aplFunctionalSymbolSemicolonUnderbar BMPString ::= {0, 0, 35, 110}

-- aplFunctionalSymbolQuadNotEqual BMPString ::= {0, 0, 35, 111}

-- aplFunctionalSymbolQuadQuestion BMPString ::= {0, 0, 35, 112}

-- aplFunctionalSymbolDownCaretTilde BMPString ::= {0, 0, 35, 113}

-- aplFunctionalSymbolUpCaretTilde BMPString ::= {0, 0, 35, 114}

-- aplFunctionalSymbolIota BMPString ::= {0, 0, 35, 115}

-- aplFunctionalSymbolRho BMPString ::= {0, 0, 35, 116}

-- aplFunctionalSymbolOmega BMPString ::= {0, 0, 35, 117}

-- aplFunctionalSymbolAlphaUnderbar BMPString ::= {0, 0, 35, 118}

-- aplFunctionalSymbolEpsilonUnderbar BMPString ::= {0, 0, 35, 119}

-- aplFunctionalSymbolIotaUnderbar BMPString ::= {0, 0, 35, 120}

-- aplFunctionalSymbolOmegaUnderbar BMPString ::= {0, 0, 35, 121}

-- aplFunctionalSymbolAlpha BMPString ::= {0, 0, 35, 122}

-- notCheckMark BMPString ::= {0, 0, 35, 123}

-- rightAngleWithDownwardsZigzagArrow BMPString ::= {0, 0, 35, 124}

-- shoulderedOpenBox BMPString ::= {0, 0, 35, 125}

-- bellSymbol BMPString ::= {0, 0, 35, 126}

-- verticalLineWithMiddleDot BMPString ::= {0, 0, 35, 127}

-- insertionSymbol BMPString ::= {0, 0, 35, 128}

-- continuousUnderlineSymbol BMPString ::= {0, 0, 35, 129}

-- discontinuousUnderlineSymbol BMPString ::= {0, 0, 35, 130}

-- emphasisSymbol BMPString ::= {0, 0, 35, 131}

-- compositionSymbol BMPString ::= {0, 0, 35, 132}

-- whiteSquareWithCentreVerticalLine BMPString ::= {0, 0, 35, 133}

-- enterSymbol BMPString ::= {0, 0, 35, 134}

-- alternativeKeySymbol BMPString ::= {0, 0, 35, 135}

-- helmSymbol BMPString ::= {0, 0, 35, 136}

-- circledHorizontalBarWithNotch BMPString ::= {0, 0, 35, 137}

-- circledTriangleDown BMPString ::= {0, 0, 35, 138}

-- brokenCircleWithNorthwestArrow BMPString ::= {0, 0, 35, 139}

-- undoSymbol BMPString ::= {0, 0, 35, 140}

-- monostableSymbol BMPString ::= {0, 0, 35, 141}

-- hysteresisSymbol BMPString ::= {0, 0, 35, 142}

-- open-circuit-outputH-typeSymbol BMPString ::= {0, 0, 35, 143}

-- open-circuit-outputL-typeSymbol BMPString ::= {0, 0, 35, 144}

-- passive-pull-down-outputSymbol BMPString ::= {0, 0, 35, 145}

-- passive-pull-up-outputSymbol BMPString ::= {0, 0, 35, 146}

-- directCurrentSymbolFormTwo BMPString ::= {0, 0, 35, 147}

-- software-functionSymbol BMPString ::= {0, 0, 35, 148}

-- aplFunctionalSymbolQuad BMPString ::= {0, 0, 35, 149}

-- decimalSeparatorKeySymbol BMPString ::= {0, 0, 35, 150}

-- previousPage BMPString ::= {0, 0, 35, 151}

-- nextPage BMPString ::= {0, 0, 35, 152}

-- printScreenSymbol BMPString ::= {0, 0, 35, 153}

-- clearScreenSymbol BMPString ::= {0, 0, 35, 154}

-- leftParenthesisUpperHook BMPString ::= {0, 0, 35, 155}

-- leftParenthesisExtension BMPString ::= {0, 0, 35, 156}

-- leftParenthesisLowerHook BMPString ::= {0, 0, 35, 157}

-- rightParenthesisUpperHook BMPString ::= {0, 0, 35, 158}

-- rightParenthesisExtension BMPString ::= {0, 0, 35, 159}

-- rightParenthesisLowerHook BMPString ::= {0, 0, 35, 160}

-- leftSquareBracketUpperCorner BMPString ::= {0, 0, 35, 161}

-- leftSquareBracketExtension BMPString ::= {0, 0, 35, 162}

-- leftSquareBracketLowerCorner BMPString ::= {0, 0, 35, 163}

-- rightSquareBracketUpperCorner BMPString ::= {0, 0, 35, 164}

-- rightSquareBracketExtension BMPString ::= {0, 0, 35, 165}

-- rightSquareBracketLowerCorner BMPString ::= {0, 0, 35, 166}

-- leftCurlyBracketUpperHook BMPString ::= {0, 0, 35, 167}

-- leftCurlyBracketMiddlePiece BMPString ::= {0, 0, 35, 168}

-- leftCurlyBracketLowerHook BMPString ::= {0, 0, 35, 169}

-- curlyBracketExtension BMPString ::= {0, 0, 35, 170}

-- rightCurlyBracketUpperHook BMPString ::= {0, 0, 35, 171}

-- rightCurlyBracketMiddlePiece BMPString ::= {0, 0, 35, 172}

-- rightCurlyBracketLowerHook BMPString ::= {0, 0, 35, 173}

-- integralExtension BMPString ::= {0, 0, 35, 174}

-- horizontalLineExtension BMPString ::= {0, 0, 35, 175}

-- upperLeftOrLowerRightCurlyBracketSection BMPString ::= {0, 0, 35, 176}

-- upperRightOrLowerLeftCurlyBracketSection BMPString ::= {0, 0, 35, 177}

-- summationTop BMPString ::= {0, 0, 35, 178}

-- summationBottom BMPString ::= {0, 0, 35, 179}

-- topSquareBracket BMPString ::= {0, 0, 35, 180}

-- bottomSquareBracket BMPString ::= {0, 0, 35, 181}

-- bottomSquareBracketOverTopSquareBracket BMPString ::= {0, 0, 35, 182}

-- radicalSymbolBottom BMPString ::= {0, 0, 35, 183}

-- leftVerticalBoxLine BMPString ::= {0, 0, 35, 184}

-- rightVerticalBoxLine BMPString ::= {0, 0, 35, 185}

-- horizontalScanLine-1 BMPString ::= {0, 0, 35, 186}

-- horizontalScanLine-3 BMPString ::= {0, 0, 35, 187}

-- horizontalScanLine-7 BMPString ::= {0, 0, 35, 188}

-- horizontalScanLine-9 BMPString ::= {0, 0, 35, 189}

-- dentistrySymbolLightVerticalAndTopRight BMPString ::= {0, 0, 35, 190}

-- dentistrySymbolLightVerticalAndBottomRight BMPString ::= {0, 0, 35, 191}

-- dentistrySymbolLightVerticalWithCircle BMPString ::= {0, 0, 35, 192}

-- dentistrySymbolLightDownAndHorizontalWithCircle BMPString ::= {0, 0, 35, 193}

-- dentistrySymbolLightUpAndHorizontalWithCircle BMPString ::= {0, 0, 35, 194}

-- dentistrySymbolLightVerticalWithTriangle BMPString ::= {0, 0, 35, 195}

-- dentistrySymbolLightDownAndHorizontalWithTriangle BMPString ::= {0, 0, 35, 196}

-- dentistrySymbolLightUpAndHorizontalWithTriangle BMPString ::= {0, 0, 35, 197}

-- dentistrySymbolLightVerticalAndWave BMPString ::= {0, 0, 35, 198}

-- dentistrySymbolLightDownAndHorizontalWithWave BMPString ::= {0, 0, 35, 199}

-- dentistrySymbolLightUpAndHorizontalWithWave BMPString ::= {0, 0, 35, 200}

-- dentistrySymbolLightDownAndHorizontal BMPString ::= {0, 0, 35, 201}

-- dentistrySymbolLightUpAndHorizontal BMPString ::= {0, 0, 35, 202}

-- dentistrySymbolLightVerticalAndTopLeft BMPString ::= {0, 0, 35, 203}

-- dentistrySymbolLightVerticalAndBottomLeft BMPString ::= {0, 0, 35, 204}

-- squareFoot BMPString ::= {0, 0, 35, 205}

-- returnSymbol BMPString ::= {0, 0, 35, 206}

-- symbolForNull BMPString ::= {0, 0, 36, 0}

-- symbolForStartOfHeading BMPString ::= {0, 0, 36, 1}

-- symbolForStartOfText BMPString ::= {0, 0, 36, 2}

-- symbolForEndOfText BMPString ::= {0, 0, 36, 3}

-- symbolForEndOfTransmission BMPString ::= {0, 0, 36, 4}

-- symbolForEnquiry BMPString ::= {0, 0, 36, 5}

-- symbolForAcknowledge BMPString ::= {0, 0, 36, 6}

-- symbolForBell BMPString ::= {0, 0, 36, 7}

-- symbolForBackspace BMPString ::= {0, 0, 36, 8}

-- symbolForHorizontalTabulation BMPString ::= {0, 0, 36, 9}

-- symbolForLineFeed BMPString ::= {0, 0, 36, 10}

-- symbolForVerticalTabulation BMPString ::= {0, 0, 36, 11}

-- symbolForFormFeed BMPString ::= {0, 0, 36, 12}

-- symbolForCarriageReturn BMPString ::= {0, 0, 36, 13}

-- symbolForShiftOut BMPString ::= {0, 0, 36, 14}

-- symbolForShiftIn BMPString ::= {0, 0, 36, 15}

-- symbolForDataLinkEscape BMPString ::= {0, 0, 36, 16}

-- symbolForDeviceControlOne BMPString ::= {0, 0, 36, 17}

-- symbolForDeviceControlTwo BMPString ::= {0, 0, 36, 18}

-- symbolForDeviceControlThree BMPString ::= {0, 0, 36, 19}

-- symbolForDeviceControlFour BMPString ::= {0, 0, 36, 20}

-- symbolForNegativeAcknowledge BMPString ::= {0, 0, 36, 21}

-- symbolForSynchronousIdle BMPString ::= {0, 0, 36, 22}

-- symbolForEndOfTransmissionBlock BMPString ::= {0, 0, 36, 23}

-- symbolForCancel BMPString ::= {0, 0, 36, 24}

-- symbolForEndOfMedium BMPString ::= {0, 0, 36, 25}

-- symbolForSubstitute BMPString ::= {0, 0, 36, 26}

-- symbolForEscape BMPString ::= {0, 0, 36, 27}

-- symbolForFileSeparator BMPString ::= {0, 0, 36, 28}

-- symbolForGroupSeparator BMPString ::= {0, 0, 36, 29}

-- symbolForRecordSeparator BMPString ::= {0, 0, 36, 30}

-- symbolForUnitSeparator BMPString ::= {0, 0, 36, 31}

-- symbolForSpace BMPString ::= {0, 0, 36, 32}

-- symbolForDelete BMPString ::= {0, 0, 36, 33}

-- blankSymbol BMPString ::= {0, 0, 36, 34}

-- openBox BMPString ::= {0, 0, 36, 35}

-- symbolForNewline BMPString ::= {0, 0, 36, 36}

-- symbolForDeleteFormTwo BMPString ::= {0, 0, 36, 37}

-- symbolForSubstituteFormTwo BMPString ::= {0, 0, 36, 38}

-- ocrHook BMPString ::= {0, 0, 36, 64}

-- ocrChair BMPString ::= {0, 0, 36, 65}

-- ocrFork BMPString ::= {0, 0, 36, 66}

-- ocrInvertedFork BMPString ::= {0, 0, 36, 67}

-- ocrBeltBuckle BMPString ::= {0, 0, 36, 68}

-- ocrBowTie BMPString ::= {0, 0, 36, 69}

-- ocrBranchBankIdentification BMPString ::= {0, 0, 36, 70}

-- ocrAmountOfCheck BMPString ::= {0, 0, 36, 71}

-- ocrDash BMPString ::= {0, 0, 36, 72}

-- ocrCustomerAccountNumber BMPString ::= {0, 0, 36, 73}

-- ocrDoubleBackslash BMPString ::= {0, 0, 36, 74}

-- circledDigitOne BMPString ::= {0, 0, 36, 96}

-- circledDigitTwo BMPString ::= {0, 0, 36, 97}

-- circledDigitThree BMPString ::= {0, 0, 36, 98}

-- circledDigitFour BMPString ::= {0, 0, 36, 99}

-- circledDigitFive BMPString ::= {0, 0, 36, 100}

-- circledDigitSix BMPString ::= {0, 0, 36, 101}

-- circledDigitSeven BMPString ::= {0, 0, 36, 102}

-- circledDigitEight BMPString ::= {0, 0, 36, 103}

-- circledDigitNine BMPString ::= {0, 0, 36, 104}

-- circledNumberTen BMPString ::= {0, 0, 36, 105}

-- circledNumberEleven BMPString ::= {0, 0, 36, 106}

-- circledNumberTwelve BMPString ::= {0, 0, 36, 107}

-- circledNumberThirteen BMPString ::= {0, 0, 36, 108}

-- circledNumberFourteen BMPString ::= {0, 0, 36, 109}

-- circledNumberFifteen BMPString ::= {0, 0, 36, 110}

-- circledNumberSixteen BMPString ::= {0, 0, 36, 111}

-- circledNumberSeventeen BMPString ::= {0, 0, 36, 112}

-- circledNumberEighteen BMPString ::= {0, 0, 36, 113}

-- circledNumberNineteen BMPString ::= {0, 0, 36, 114}

-- circledNumberTwenty BMPString ::= {0, 0, 36, 115}

-- parenthesizedDigitOne BMPString ::= {0, 0, 36, 116}

-- parenthesizedDigitTwo BMPString ::= {0, 0, 36, 117}

-- parenthesizedDigitThree BMPString ::= {0, 0, 36, 118}

-- parenthesizedDigitFour BMPString ::= {0, 0, 36, 119}

-- parenthesizedDigitFive BMPString ::= {0, 0, 36, 120}

-- parenthesizedDigitSix BMPString ::= {0, 0, 36, 121}

-- parenthesizedDigitSeven BMPString ::= {0, 0, 36, 122}

-- parenthesizedDigitEight BMPString ::= {0, 0, 36, 123}

-- parenthesizedDigitNine BMPString ::= {0, 0, 36, 124}

-- parenthesizedNumberTen BMPString ::= {0, 0, 36, 125}

-- parenthesizedNumberEleven BMPString ::= {0, 0, 36, 126}

-- parenthesizedNumberTwelve BMPString ::= {0, 0, 36, 127}

-- parenthesizedNumberThirteen BMPString ::= {0, 0, 36, 128}

-- parenthesizedNumberFourteen BMPString ::= {0, 0, 36, 129}

-- parenthesizedNumberFifteen BMPString ::= {0, 0, 36, 130}

-- parenthesizedNumberSixteen BMPString ::= {0, 0, 36, 131}

-- parenthesizedNumberSeventeen BMPString ::= {0, 0, 36, 132}

-- parenthesizedNumberEighteen BMPString ::= {0, 0, 36, 133}

-- parenthesizedNumberNineteen BMPString ::= {0, 0, 36, 134}

-- parenthesizedNumberTwenty BMPString ::= {0, 0, 36, 135}

-- digitOneFullStop BMPString ::= {0, 0, 36, 136}

-- digitTwoFullStop BMPString ::= {0, 0, 36, 137}

-- digitThreeFullStop BMPString ::= {0, 0, 36, 138}

-- digitFourFullStop BMPString ::= {0, 0, 36, 139}

-- digitFiveFullStop BMPString ::= {0, 0, 36, 140}

-- digitSixFullStop BMPString ::= {0, 0, 36, 141}

-- digitSevenFullStop BMPString ::= {0, 0, 36, 142}

-- digitEightFullStop BMPString ::= {0, 0, 36, 143}

-- digitNineFullStop BMPString ::= {0, 0, 36, 144}

-- numberTenFullStop BMPString ::= {0, 0, 36, 145}

-- numberElevenFullStop BMPString ::= {0, 0, 36, 146}

-- numberTwelveFullStop BMPString ::= {0, 0, 36, 147}

-- numberThirteenFullStop BMPString ::= {0, 0, 36, 148}

-- numberFourteenFullStop BMPString ::= {0, 0, 36, 149}

-- numberFifteenFullStop BMPString ::= {0, 0, 36, 150}

-- numberSixteenFullStop BMPString ::= {0, 0, 36, 151}

-- numberSeventeenFullStop BMPString ::= {0, 0, 36, 152}

-- numberEighteenFullStop BMPString ::= {0, 0, 36, 153}

-- numberNineteenFullStop BMPString ::= {0, 0, 36, 154}

-- numberTwentyFullStop BMPString ::= {0, 0, 36, 155}

-- parenthesizedLatinSmallLetterA BMPString ::= {0, 0, 36, 156}

-- parenthesizedLatinSmallLetterB BMPString ::= {0, 0, 36, 157}

-- parenthesizedLatinSmallLetterC BMPString ::= {0, 0, 36, 158}

-- parenthesizedLatinSmallLetterD BMPString ::= {0, 0, 36, 159}

-- parenthesizedLatinSmallLetterE BMPString ::= {0, 0, 36, 160}

-- parenthesizedLatinSmallLetterF BMPString ::= {0, 0, 36, 161}

-- parenthesizedLatinSmallLetterG BMPString ::= {0, 0, 36, 162}

-- parenthesizedLatinSmallLetterH BMPString ::= {0, 0, 36, 163}

-- parenthesizedLatinSmallLetterI BMPString ::= {0, 0, 36, 164}

-- parenthesizedLatinSmallLetterJ BMPString ::= {0, 0, 36, 165}

-- parenthesizedLatinSmallLetterK BMPString ::= {0, 0, 36, 166}

-- parenthesizedLatinSmallLetterL BMPString ::= {0, 0, 36, 167}

-- parenthesizedLatinSmallLetterM BMPString ::= {0, 0, 36, 168}

-- parenthesizedLatinSmallLetterN BMPString ::= {0, 0, 36, 169}

-- parenthesizedLatinSmallLetterO BMPString ::= {0, 0, 36, 170}

-- parenthesizedLatinSmallLetterP BMPString ::= {0, 0, 36, 171}

-- parenthesizedLatinSmallLetterQ BMPString ::= {0, 0, 36, 172}

-- parenthesizedLatinSmallLetterR BMPString ::= {0, 0, 36, 173}

-- parenthesizedLatinSmallLetterS BMPString ::= {0, 0, 36, 174}

-- parenthesizedLatinSmallLetterT BMPString ::= {0, 0, 36, 175}

-- parenthesizedLatinSmallLetterU BMPString ::= {0, 0, 36, 176}

-- parenthesizedLatinSmallLetterV BMPString ::= {0, 0, 36, 177}

-- parenthesizedLatinSmallLetterW BMPString ::= {0, 0, 36, 178}

-- parenthesizedLatinSmallLetterX BMPString ::= {0, 0, 36, 179}

-- parenthesizedLatinSmallLetterY BMPString ::= {0, 0, 36, 180}

-- parenthesizedLatinSmallLetterZ BMPString ::= {0, 0, 36, 181}

-- circledLatinCapitalLetterA BMPString ::= {0, 0, 36, 182}

-- circledLatinCapitalLetterB BMPString ::= {0, 0, 36, 183}

-- circledLatinCapitalLetterC BMPString ::= {0, 0, 36, 184}

-- circledLatinCapitalLetterD BMPString ::= {0, 0, 36, 185}

-- circledLatinCapitalLetterE BMPString ::= {0, 0, 36, 186}

-- circledLatinCapitalLetterF BMPString ::= {0, 0, 36, 187}

-- circledLatinCapitalLetterG BMPString ::= {0, 0, 36, 188}

-- circledLatinCapitalLetterH BMPString ::= {0, 0, 36, 189}

-- circledLatinCapitalLetterI BMPString ::= {0, 0, 36, 190}

-- circledLatinCapitalLetterJ BMPString ::= {0, 0, 36, 191}

-- circledLatinCapitalLetterK BMPString ::= {0, 0, 36, 192}

-- circledLatinCapitalLetterL BMPString ::= {0, 0, 36, 193}

-- circledLatinCapitalLetterM BMPString ::= {0, 0, 36, 194}

-- circledLatinCapitalLetterN BMPString ::= {0, 0, 36, 195}

-- circledLatinCapitalLetterO BMPString ::= {0, 0, 36, 196}

-- circledLatinCapitalLetterP BMPString ::= {0, 0, 36, 197}

-- circledLatinCapitalLetterQ BMPString ::= {0, 0, 36, 198}

-- circledLatinCapitalLetterR BMPString ::= {0, 0, 36, 199}

-- circledLatinCapitalLetterS BMPString ::= {0, 0, 36, 200}

-- circledLatinCapitalLetterT BMPString ::= {0, 0, 36, 201}

-- circledLatinCapitalLetterU BMPString ::= {0, 0, 36, 202}

-- circledLatinCapitalLetterV BMPString ::= {0, 0, 36, 203}

-- circledLatinCapitalLetterW BMPString ::= {0, 0, 36, 204}

-- circledLatinCapitalLetterX BMPString ::= {0, 0, 36, 205}

-- circledLatinCapitalLetterY BMPString ::= {0, 0, 36, 206}

-- circledLatinCapitalLetterZ BMPString ::= {0, 0, 36, 207}

-- circledLatinSmallLetterA BMPString ::= {0, 0, 36, 208}

-- circledLatinSmallLetterB BMPString ::= {0, 0, 36, 209}

-- circledLatinSmallLetterC BMPString ::= {0, 0, 36, 210}

-- circledLatinSmallLetterD BMPString ::= {0, 0, 36, 211}

-- circledLatinSmallLetterE BMPString ::= {0, 0, 36, 212}

-- circledLatinSmallLetterF BMPString ::= {0, 0, 36, 213}

-- circledLatinSmallLetterG BMPString ::= {0, 0, 36, 214}

-- circledLatinSmallLetterH BMPString ::= {0, 0, 36, 215}

-- circledLatinSmallLetterI BMPString ::= {0, 0, 36, 216}

-- circledLatinSmallLetterJ BMPString ::= {0, 0, 36, 217}

-- circledLatinSmallLetterK BMPString ::= {0, 0, 36, 218}

-- circledLatinSmallLetterL BMPString ::= {0, 0, 36, 219}

-- circledLatinSmallLetterM BMPString ::= {0, 0, 36, 220}

-- circledLatinSmallLetterN BMPString ::= {0, 0, 36, 221}

-- circledLatinSmallLetterO BMPString ::= {0, 0, 36, 222}

-- circledLatinSmallLetterP BMPString ::= {0, 0, 36, 223}

-- circledLatinSmallLetterQ BMPString ::= {0, 0, 36, 224}

-- circledLatinSmallLetterR BMPString ::= {0, 0, 36, 225}

-- circledLatinSmallLetterS BMPString ::= {0, 0, 36, 226}

-- circledLatinSmallLetterT BMPString ::= {0, 0, 36, 227}

-- circledLatinSmallLetterU BMPString ::= {0, 0, 36, 228}

-- circledLatinSmallLetterV BMPString ::= {0, 0, 36, 229}

-- circledLatinSmallLetterW BMPString ::= {0, 0, 36, 230}

-- circledLatinSmallLetterX BMPString ::= {0, 0, 36, 231}

-- circledLatinSmallLetterY BMPString ::= {0, 0, 36, 232}

-- circledLatinSmallLetterZ BMPString ::= {0, 0, 36, 233}

-- circledDigitZero BMPString ::= {0, 0, 36, 234}

-- negativeCircledNumberEleven BMPString ::= {0, 0, 36, 235}

-- negativeCircledNumberTwelve BMPString ::= {0, 0, 36, 236}

-- negativeCircledNumberThirteen BMPString ::= {0, 0, 36, 237}

-- negativeCircledNumberFourteen BMPString ::= {0, 0, 36, 238}

-- negativeCircledNumberFifteen BMPString ::= {0, 0, 36, 239}

-- negativeCircledNumberSixteen BMPString ::= {0, 0, 36, 240}

-- negativeCircledNumberSeventeen BMPString ::= {0, 0, 36, 241}

-- negativeCircledNumberEighteen BMPString ::= {0, 0, 36, 242}

-- negativeCircledNumberNineteen BMPString ::= {0, 0, 36, 243}

-- negativeCircledNumberTwenty BMPString ::= {0, 0, 36, 244}

-- doubleCircledDigitOne BMPString ::= {0, 0, 36, 245}

-- doubleCircledDigitTwo BMPString ::= {0, 0, 36, 246}

-- doubleCircledDigitThree BMPString ::= {0, 0, 36, 247}

-- doubleCircledDigitFour BMPString ::= {0, 0, 36, 248}

-- doubleCircledDigitFive BMPString ::= {0, 0, 36, 249}

-- doubleCircledDigitSix BMPString ::= {0, 0, 36, 250}

-- doubleCircledDigitSeven BMPString ::= {0, 0, 36, 251}

-- doubleCircledDigitEight BMPString ::= {0, 0, 36, 252}

-- doubleCircledDigitNine BMPString ::= {0, 0, 36, 253}

-- doubleCircledNumberTen BMPString ::= {0, 0, 36, 254}

-- boxDrawingsLightHorizontal BMPString ::= {0, 0, 37, 0}

-- boxDrawingsHeavyHorizontal BMPString ::= {0, 0, 37, 1}

-- boxDrawingsLightVertical BMPString ::= {0, 0, 37, 2}

-- boxDrawingsHeavyVertical BMPString ::= {0, 0, 37, 3}

-- boxDrawingsLightTripleDashHorizontal BMPString ::= {0, 0, 37, 4}

-- boxDrawingsHeavyTripleDashHorizontal BMPString ::= {0, 0, 37, 5}

-- boxDrawingsLightTripleDashVertical BMPString ::= {0, 0, 37, 6}

-- boxDrawingsHeavyTripleDashVertical BMPString ::= {0, 0, 37, 7}

-- boxDrawingsLightQuadrupleDashHorizontal BMPString ::= {0, 0, 37, 8}

-- boxDrawingsHeavyQuadrupleDashHorizontal BMPString ::= {0, 0, 37, 9}

-- boxDrawingsLightQuadrupleDashVertical BMPString ::= {0, 0, 37, 10}

-- boxDrawingsHeavyQuadrupleDashVertical BMPString ::= {0, 0, 37, 11}

-- boxDrawingsLightDownAndRight BMPString ::= {0, 0, 37, 12}

-- boxDrawingsDownLightAndRightHeavy BMPString ::= {0, 0, 37, 13}

-- boxDrawingsDownHeavyAndRightLight BMPString ::= {0, 0, 37, 14}

-- boxDrawingsHeavyDownAndRight BMPString ::= {0, 0, 37, 15}

-- boxDrawingsLightDownAndLeft BMPString ::= {0, 0, 37, 16}

-- boxDrawingsDownLightAndLeftHeavy BMPString ::= {0, 0, 37, 17}

-- boxDrawingsDownHeavyAndLeftLight BMPString ::= {0, 0, 37, 18}

-- boxDrawingsHeavyDownAndLeft BMPString ::= {0, 0, 37, 19}

-- boxDrawingsLightUpAndRight BMPString ::= {0, 0, 37, 20}

-- boxDrawingsUpLightAndRightHeavy BMPString ::= {0, 0, 37, 21}

-- boxDrawingsUpHeavyAndRightLight BMPString ::= {0, 0, 37, 22}

-- boxDrawingsHeavyUpAndRight BMPString ::= {0, 0, 37, 23}

-- boxDrawingsLightUpAndLeft BMPString ::= {0, 0, 37, 24}

-- boxDrawingsUpLightAndLeftHeavy BMPString ::= {0, 0, 37, 25}

-- boxDrawingsUpHeavyAndLeftLight BMPString ::= {0, 0, 37, 26}

-- boxDrawingsHeavyUpAndLeft BMPString ::= {0, 0, 37, 27}

-- boxDrawingsLightVerticalAndRight BMPString ::= {0, 0, 37, 28}

-- boxDrawingsVerticalLightAndRightHeavy BMPString ::= {0, 0, 37, 29}

-- boxDrawingsUpHeavyAndRightDownLight BMPString ::= {0, 0, 37, 30}

-- boxDrawingsDownHeavyAndRightUpLight BMPString ::= {0, 0, 37, 31}

-- boxDrawingsVerticalHeavyAndRightLight BMPString ::= {0, 0, 37, 32}

-- boxDrawingsDownLightAndRightUpHeavy BMPString ::= {0, 0, 37, 33}

-- boxDrawingsUpLightAndRightDownHeavy BMPString ::= {0, 0, 37, 34}

-- boxDrawingsHeavyVerticalAndRight BMPString ::= {0, 0, 37, 35}

-- boxDrawingsLightVerticalAndLeft BMPString ::= {0, 0, 37, 36}

-- boxDrawingsVerticalLightAndLeftHeavy BMPString ::= {0, 0, 37, 37}

-- boxDrawingsUpHeavyAndLeftDownLight BMPString ::= {0, 0, 37, 38}

-- boxDrawingsDownHeavyAndLeftUpLight BMPString ::= {0, 0, 37, 39}

-- boxDrawingsVerticalHeavyAndLeftLight BMPString ::= {0, 0, 37, 40}

-- boxDrawingsDownLightAndLeftUpHeavy BMPString ::= {0, 0, 37, 41}

-- boxDrawingsUpLightAndLeftDownHeavy BMPString ::= {0, 0, 37, 42}

-- boxDrawingsHeavyVerticalAndLeft BMPString ::= {0, 0, 37, 43}

-- boxDrawingsLightDownAndHorizontal BMPString ::= {0, 0, 37, 44}

-- boxDrawingsLeftHeavyAndRightDownLight BMPString ::= {0, 0, 37, 45}

-- boxDrawingsRightHeavyAndLeftDownLight BMPString ::= {0, 0, 37, 46}

-- boxDrawingsDownLightAndHorizontalHeavy BMPString ::= {0, 0, 37, 47}

-- boxDrawingsDownHeavyAndHorizontalLight BMPString ::= {0, 0, 37, 48}

-- boxDrawingsRightLightAndLeftDownHeavy BMPString ::= {0, 0, 37, 49}

-- boxDrawingsLeftLightAndRightDownHeavy BMPString ::= {0, 0, 37, 50}

-- boxDrawingsHeavyDownAndHorizontal BMPString ::= {0, 0, 37, 51}

-- boxDrawingsLightUpAndHorizontal BMPString ::= {0, 0, 37, 52}

-- boxDrawingsLeftHeavyAndRightUpLight BMPString ::= {0, 0, 37, 53}

-- boxDrawingsRightHeavyAndLeftUpLight BMPString ::= {0, 0, 37, 54}

-- boxDrawingsUpLightAndHorizontalHeavy BMPString ::= {0, 0, 37, 55}

-- boxDrawingsUpHeavyAndHorizontalLight BMPString ::= {0, 0, 37, 56}

-- boxDrawingsRightLightAndLeftUpHeavy BMPString ::= {0, 0, 37, 57}

-- boxDrawingsLeftLightAndRightUpHeavy BMPString ::= {0, 0, 37, 58}

-- boxDrawingsHeavyUpAndHorizontal BMPString ::= {0, 0, 37, 59}

-- boxDrawingsLightVerticalAndHorizontal BMPString ::= {0, 0, 37, 60}

-- boxDrawingsLeftHeavyAndRightVerticalLight BMPString ::= {0, 0, 37, 61}

-- boxDrawingsRightHeavyAndLeftVerticalLight BMPString ::= {0, 0, 37, 62}

-- boxDrawingsVerticalLightAndHorizontalHeavy BMPString ::= {0, 0, 37, 63}

-- boxDrawingsUpHeavyAndDownHorizontalLight BMPString ::= {0, 0, 37, 64}

-- boxDrawingsDownHeavyAndUpHorizontalLight BMPString ::= {0, 0, 37, 65}

-- boxDrawingsVerticalHeavyAndHorizontalLight BMPString ::= {0, 0, 37, 66}

-- boxDrawingsLeftUpHeavyAndRightDownLight BMPString ::= {0, 0, 37, 67}

-- boxDrawingsRightUpHeavyAndLeftDownLight BMPString ::= {0, 0, 37, 68}

-- boxDrawingsLeftDownHeavyAndRightUpLight BMPString ::= {0, 0, 37, 69}

-- boxDrawingsRightDownHeavyAndLeftUpLight BMPString ::= {0, 0, 37, 70}

-- boxDrawingsDownLightAndUpHorizontalHeavy BMPString ::= {0, 0, 37, 71}

-- boxDrawingsUpLightAndDownHorizontalHeavy BMPString ::= {0, 0, 37, 72}

-- boxDrawingsRightLightAndLeftVerticalHeavy BMPString ::= {0, 0, 37, 73}

-- boxDrawingsLeftLightAndRightVerticalHeavy BMPString ::= {0, 0, 37, 74}

-- boxDrawingsHeavyVerticalAndHorizontal BMPString ::= {0, 0, 37, 75}

-- boxDrawingsLightDoubleDashHorizontal BMPString ::= {0, 0, 37, 76}

-- boxDrawingsHeavyDoubleDashHorizontal BMPString ::= {0, 0, 37, 77}

-- boxDrawingsLightDoubleDashVertical BMPString ::= {0, 0, 37, 78}

-- boxDrawingsHeavyDoubleDashVertical BMPString ::= {0, 0, 37, 79}

-- boxDrawingsDoubleHorizontal BMPString ::= {0, 0, 37, 80}

-- boxDrawingsDoubleVertical BMPString ::= {0, 0, 37, 81}

-- boxDrawingsDownSingleAndRightDouble BMPString ::= {0, 0, 37, 82}

-- boxDrawingsDownDoubleAndRightSingle BMPString ::= {0, 0, 37, 83}

-- boxDrawingsDoubleDownAndRight BMPString ::= {0, 0, 37, 84}

-- boxDrawingsDownSingleAndLeftDouble BMPString ::= {0, 0, 37, 85}

-- boxDrawingsDownDoubleAndLeftSingle BMPString ::= {0, 0, 37, 86}

-- boxDrawingsDoubleDownAndLeft BMPString ::= {0, 0, 37, 87}

-- boxDrawingsUpSingleAndRightDouble BMPString ::= {0, 0, 37, 88}

-- boxDrawingsUpDoubleAndRightSingle BMPString ::= {0, 0, 37, 89}

-- boxDrawingsDoubleUpAndRight BMPString ::= {0, 0, 37, 90}

-- boxDrawingsUpSingleAndLeftDouble BMPString ::= {0, 0, 37, 91}

-- boxDrawingsUpDoubleAndLeftSingle BMPString ::= {0, 0, 37, 92}

-- boxDrawingsDoubleUpAndLeft BMPString ::= {0, 0, 37, 93}

-- boxDrawingsVerticalSingleAndRightDouble BMPString ::= {0, 0, 37, 94}

-- boxDrawingsVerticalDoubleAndRightSingle BMPString ::= {0, 0, 37, 95}

-- boxDrawingsDoubleVerticalAndRight BMPString ::= {0, 0, 37, 96}

-- boxDrawingsVerticalSingleAndLeftDouble BMPString ::= {0, 0, 37, 97}

-- boxDrawingsVerticalDoubleAndLeftSingle BMPString ::= {0, 0, 37, 98}

-- boxDrawingsDoubleVerticalAndLeft BMPString ::= {0, 0, 37, 99}

-- boxDrawingsDownSingleAndHorizontalDouble BMPString ::= {0, 0, 37, 100}

-- boxDrawingsDownDoubleAndHorizontalSingle BMPString ::= {0, 0, 37, 101}

-- boxDrawingsDoubleDownAndHorizontal BMPString ::= {0, 0, 37, 102}

-- boxDrawingsUpSingleAndHorizontalDouble BMPString ::= {0, 0, 37, 103}

-- boxDrawingsUpDoubleAndHorizontalSingle BMPString ::= {0, 0, 37, 104}

-- boxDrawingsDoubleUpAndHorizontal BMPString ::= {0, 0, 37, 105}

-- boxDrawingsVerticalSingleAndHorizontalDouble BMPString ::= {0, 0, 37, 106}

-- boxDrawingsVerticalDoubleAndHorizontalSingle BMPString ::= {0, 0, 37, 107}

-- boxDrawingsDoubleVerticalAndHorizontal BMPString ::= {0, 0, 37, 108}

-- boxDrawingsLightArcDownAndRight BMPString ::= {0, 0, 37, 109}

-- boxDrawingsLightArcDownAndLeft BMPString ::= {0, 0, 37, 110}

-- boxDrawingsLightArcUpAndLeft BMPString ::= {0, 0, 37, 111}

-- boxDrawingsLightArcUpAndRight BMPString ::= {0, 0, 37, 112}

-- boxDrawingsLightDiagonalUpperRightToLowerLeft BMPString ::= {0, 0, 37, 113}

-- boxDrawingsLightDiagonalUpperLeftToLowerRight BMPString ::= {0, 0, 37, 114}

-- boxDrawingsLightDiagonalCross BMPString ::= {0, 0, 37, 115}

-- boxDrawingsLightLeft BMPString ::= {0, 0, 37, 116}

-- boxDrawingsLightUp BMPString ::= {0, 0, 37, 117}

-- boxDrawingsLightRight BMPString ::= {0, 0, 37, 118}

-- boxDrawingsLightDown BMPString ::= {0, 0, 37, 119}

-- boxDrawingsHeavyLeft BMPString ::= {0, 0, 37, 120}

-- boxDrawingsHeavyUp BMPString ::= {0, 0, 37, 121}

-- boxDrawingsHeavyRight BMPString ::= {0, 0, 37, 122}

-- boxDrawingsHeavyDown BMPString ::= {0, 0, 37, 123}

-- boxDrawingsLightLeftAndHeavyRight BMPString ::= {0, 0, 37, 124}

-- boxDrawingsLightUpAndHeavyDown BMPString ::= {0, 0, 37, 125}

-- boxDrawingsHeavyLeftAndLightRight BMPString ::= {0, 0, 37, 126}

-- boxDrawingsHeavyUpAndLightDown BMPString ::= {0, 0, 37, 127}

-- upperHalfBlock BMPString ::= {0, 0, 37, 128}

-- lowerOneEighthBlock BMPString ::= {0, 0, 37, 129}

-- lowerOneQuarterBlock BMPString ::= {0, 0, 37, 130}

-- lowerThreeEighthsBlock BMPString ::= {0, 0, 37, 131}

-- lowerHalfBlock BMPString ::= {0, 0, 37, 132}

-- lowerFiveEighthsBlock BMPString ::= {0, 0, 37, 133}

-- lowerThreeQuartersBlock BMPString ::= {0, 0, 37, 134}

-- lowerSevenEighthsBlock BMPString ::= {0, 0, 37, 135}

-- fullBlock BMPString ::= {0, 0, 37, 136}

-- leftSevenEighthsBlock BMPString ::= {0, 0, 37, 137}

-- leftThreeQuartersBlock BMPString ::= {0, 0, 37, 138}

-- leftFiveEighthsBlock BMPString ::= {0, 0, 37, 139}

-- leftHalfBlock BMPString ::= {0, 0, 37, 140}

-- leftThreeEighthsBlock BMPString ::= {0, 0, 37, 141}

-- leftOneQuarterBlock BMPString ::= {0, 0, 37, 142}

-- leftOneEighthBlock BMPString ::= {0, 0, 37, 143}

-- rightHalfBlock BMPString ::= {0, 0, 37, 144}

-- lightShade BMPString ::= {0, 0, 37, 145}

-- mediumShade BMPString ::= {0, 0, 37, 146}

-- darkShade BMPString ::= {0, 0, 37, 147}

-- upperOneEighthBlock BMPString ::= {0, 0, 37, 148}

-- rightOneEighthBlock BMPString ::= {0, 0, 37, 149}

-- quadrantLowerLeft BMPString ::= {0, 0, 37, 150}

-- quadrantLowerRight BMPString ::= {0, 0, 37, 151}

-- quadrantUpperLeft BMPString ::= {0, 0, 37, 152}

-- quadrantUpperLeftAndLowerLeftAndLowerRight BMPString ::= {0, 0, 37, 153}

-- quadrantUpperLeftAndLowerRight BMPString ::= {0, 0, 37, 154}

-- quadrantUpperLeftAndUpperRightAndLowerLeft BMPString ::= {0, 0, 37, 155}

-- quadrantUpperLeftAndUpperRightAndLowerRight BMPString ::= {0, 0, 37, 156}

-- quadrantUpperRight BMPString ::= {0, 0, 37, 157}

-- quadrantUpperRightAndLowerLeft BMPString ::= {0, 0, 37, 158}

-- quadrantUpperRightAndLowerLeftAndLowerRight BMPString ::= {0, 0, 37, 159}

-- blackSquare BMPString ::= {0, 0, 37, 160}

-- whiteSquare BMPString ::= {0, 0, 37, 161}

-- whiteSquareWithRoundedCorners BMPString ::= {0, 0, 37, 162}

-- whiteSquareContainingBlackSmallSquare BMPString ::= {0, 0, 37, 163}

-- squareWithHorizontalFill BMPString ::= {0, 0, 37, 164}

-- squareWithVerticalFill BMPString ::= {0, 0, 37, 165}

-- squareWithOrthogonalCrosshatchFill BMPString ::= {0, 0, 37, 166}

-- squareWithUpperLeftToLowerRightFill BMPString ::= {0, 0, 37, 167}

-- squareWithUpperRightToLowerLeftFill BMPString ::= {0, 0, 37, 168}

-- squareWithDiagonalCrosshatchFill BMPString ::= {0, 0, 37, 169}

-- blackSmallSquare BMPString ::= {0, 0, 37, 170}

-- whiteSmallSquare BMPString ::= {0, 0, 37, 171}

-- blackRectangle BMPString ::= {0, 0, 37, 172}

-- whiteRectangle BMPString ::= {0, 0, 37, 173}

-- blackVerticalRectangle BMPString ::= {0, 0, 37, 174}

-- whiteVerticalRectangle BMPString ::= {0, 0, 37, 175}

-- blackParallelogram BMPString ::= {0, 0, 37, 176}

-- whiteParallelogram BMPString ::= {0, 0, 37, 177}

-- blackUp-pointingTriangle BMPString ::= {0, 0, 37, 178}

-- whiteUp-pointingTriangle BMPString ::= {0, 0, 37, 179}

-- blackUp-pointingSmallTriangle BMPString ::= {0, 0, 37, 180}

-- whiteUp-pointingSmallTriangle BMPString ::= {0, 0, 37, 181}

-- blackRight-pointingTriangle BMPString ::= {0, 0, 37, 182}

-- whiteRight-pointingTriangle BMPString ::= {0, 0, 37, 183}

-- blackRight-pointingSmallTriangle BMPString ::= {0, 0, 37, 184}

-- whiteRight-pointingSmallTriangle BMPString ::= {0, 0, 37, 185}

-- blackRight-pointingPointer BMPString ::= {0, 0, 37, 186}

-- whiteRight-pointingPointer BMPString ::= {0, 0, 37, 187}

-- blackDown-pointingTriangle BMPString ::= {0, 0, 37, 188}

-- whiteDown-pointingTriangle BMPString ::= {0, 0, 37, 189}

-- blackDown-pointingSmallTriangle BMPString ::= {0, 0, 37, 190}

-- whiteDown-pointingSmallTriangle BMPString ::= {0, 0, 37, 191}

-- blackLeft-pointingTriangle BMPString ::= {0, 0, 37, 192}

-- whiteLeft-pointingTriangle BMPString ::= {0, 0, 37, 193}

-- blackLeft-pointingSmallTriangle BMPString ::= {0, 0, 37, 194}

-- whiteLeft-pointingSmallTriangle BMPString ::= {0, 0, 37, 195}

-- blackLeft-pointingPointer BMPString ::= {0, 0, 37, 196}

-- whiteLeft-pointingPointer BMPString ::= {0, 0, 37, 197}

-- blackDiamond BMPString ::= {0, 0, 37, 198}

-- whiteDiamond BMPString ::= {0, 0, 37, 199}

-- whiteDiamondContainingBlackSmallDiamond BMPString ::= {0, 0, 37, 200}

-- fisheye BMPString ::= {0, 0, 37, 201}

-- lozenge BMPString ::= {0, 0, 37, 202}

-- whiteCircle BMPString ::= {0, 0, 37, 203}

-- dottedCircle BMPString ::= {0, 0, 37, 204}

-- circleWithVerticalFill BMPString ::= {0, 0, 37, 205}

-- bullseye BMPString ::= {0, 0, 37, 206}

-- blackCircle BMPString ::= {0, 0, 37, 207}

-- circleWithLeftHalfBlack BMPString ::= {0, 0, 37, 208}

-- circleWithRightHalfBlack BMPString ::= {0, 0, 37, 209}

-- circleWithLowerHalfBlack BMPString ::= {0, 0, 37, 210}

-- circleWithUpperHalfBlack BMPString ::= {0, 0, 37, 211}

-- circleWithUpperRightQuadrantBlack BMPString ::= {0, 0, 37, 212}

-- circleWithAllButUpperLeftQuadrantBlack BMPString ::= {0, 0, 37, 213}

-- leftHalfBlackCircle BMPString ::= {0, 0, 37, 214}

-- rightHalfBlackCircle BMPString ::= {0, 0, 37, 215}

-- inverseBullet BMPString ::= {0, 0, 37, 216}

-- inverseWhiteCircle BMPString ::= {0, 0, 37, 217}

-- upperHalfInverseWhiteCircle BMPString ::= {0, 0, 37, 218}

-- lowerHalfInverseWhiteCircle BMPString ::= {0, 0, 37, 219}

-- upperLeftQuadrantCircularArc BMPString ::= {0, 0, 37, 220}

-- upperRightQuadrantCircularArc BMPString ::= {0, 0, 37, 221}

-- lowerRightQuadrantCircularArc BMPString ::= {0, 0, 37, 222}

-- lowerLeftQuadrantCircularArc BMPString ::= {0, 0, 37, 223}

-- upperHalfCircle BMPString ::= {0, 0, 37, 224}

-- lowerHalfCircle BMPString ::= {0, 0, 37, 225}

-- blackLowerRightTriangle BMPString ::= {0, 0, 37, 226}

-- blackLowerLeftTriangle BMPString ::= {0, 0, 37, 227}

-- blackUpperLeftTriangle BMPString ::= {0, 0, 37, 228}

-- blackUpperRightTriangle BMPString ::= {0, 0, 37, 229}

-- whiteBullet BMPString ::= {0, 0, 37, 230}

-- squareWithLeftHalfBlack BMPString ::= {0, 0, 37, 231}

-- squareWithRightHalfBlack BMPString ::= {0, 0, 37, 232}

-- squareWithUpperLeftDiagonalHalfBlack BMPString ::= {0, 0, 37, 233}

-- squareWithLowerRightDiagonalHalfBlack BMPString ::= {0, 0, 37, 234}

-- whiteSquareWithVerticalBisectingLine BMPString ::= {0, 0, 37, 235}

-- whiteUp-pointingTriangleWithDot BMPString ::= {0, 0, 37, 236}

-- up-pointingTriangleWithLeftHalfBlack BMPString ::= {0, 0, 37, 237}

-- up-pointingTriangleWithRightHalfBlack BMPString ::= {0, 0, 37, 238}

-- largeCircle BMPString ::= {0, 0, 37, 239}

-- whiteSquareWithUpperLeftQuadrant BMPString ::= {0, 0, 37, 240}

-- whiteSquareWithLowerLeftQuadrant BMPString ::= {0, 0, 37, 241}

-- whiteSquareWithLowerRightQuadrant BMPString ::= {0, 0, 37, 242}

-- whiteSquareWithUpperRightQuadrant BMPString ::= {0, 0, 37, 243}

-- whiteCircleWithUpperLeftQuadrant BMPString ::= {0, 0, 37, 244}

-- whiteCircleWithLowerLeftQuadrant BMPString ::= {0, 0, 37, 245}

-- whiteCircleWithLowerRightQuadrant BMPString ::= {0, 0, 37, 246}

-- whiteCircleWithUpperRightQuadrant BMPString ::= {0, 0, 37, 247}

-- upperLeftTriangle BMPString ::= {0, 0, 37, 248}

-- upperRightTriangle BMPString ::= {0, 0, 37, 249}

-- lowerLeftTriangle BMPString ::= {0, 0, 37, 250}

-- whiteMediumSquare BMPString ::= {0, 0, 37, 251}

-- blackMediumSquare BMPString ::= {0, 0, 37, 252}

-- whiteMediumSmallSquare BMPString ::= {0, 0, 37, 253}

-- blackMediumSmallSquare BMPString ::= {0, 0, 37, 254}

-- lowerRightTriangle BMPString ::= {0, 0, 37, 255}

-- blackSunWithRays BMPString ::= {0, 0, 38, 0}

-- cloud BMPString ::= {0, 0, 38, 1}

-- umbrella BMPString ::= {0, 0, 38, 2}

-- snowman BMPString ::= {0, 0, 38, 3}

-- comet BMPString ::= {0, 0, 38, 4}

-- blackStar BMPString ::= {0, 0, 38, 5}

-- whiteStar BMPString ::= {0, 0, 38, 6}

-- lightning BMPString ::= {0, 0, 38, 7}

-- thunderstorm BMPString ::= {0, 0, 38, 8}

-- sun BMPString ::= {0, 0, 38, 9}

-- ascendingNode BMPString ::= {0, 0, 38, 10}

-- descendingNode BMPString ::= {0, 0, 38, 11}

-- conjunction BMPString ::= {0, 0, 38, 12}

-- opposition BMPString ::= {0, 0, 38, 13}

-- blackTelephone BMPString ::= {0, 0, 38, 14}

-- whiteTelephone BMPString ::= {0, 0, 38, 15}

-- ballotBox BMPString ::= {0, 0, 38, 16}

-- ballotBoxWithCheck BMPString ::= {0, 0, 38, 17}

-- ballotBoxWithX BMPString ::= {0, 0, 38, 18}

-- saltire BMPString ::= {0, 0, 38, 19}

-- whiteShogiPiece BMPString ::= {0, 0, 38, 22}

-- blackShogiPiece BMPString ::= {0, 0, 38, 23}

-- reversedRotatedFloralHeartBullet BMPString ::= {0, 0, 38, 25}

-- blackLeftPointingIndex BMPString ::= {0, 0, 38, 26}

-- blackRightPointingIndex BMPString ::= {0, 0, 38, 27}

-- whiteLeftPointingIndex BMPString ::= {0, 0, 38, 28}

-- whiteUpPointingIndex BMPString ::= {0, 0, 38, 29}

-- whiteRightPointingIndex BMPString ::= {0, 0, 38, 30}

-- whiteDownPointingIndex BMPString ::= {0, 0, 38, 31}

-- skullAndCrossbones BMPString ::= {0, 0, 38, 32}

-- cautionSign BMPString ::= {0, 0, 38, 33}

-- radioactiveSign BMPString ::= {0, 0, 38, 34}

-- biohazardSign BMPString ::= {0, 0, 38, 35}

-- caduceus BMPString ::= {0, 0, 38, 36}

-- ankh BMPString ::= {0, 0, 38, 37}

-- orthodoxCross BMPString ::= {0, 0, 38, 38}

-- chiRho BMPString ::= {0, 0, 38, 39}

-- crossOfLorraine BMPString ::= {0, 0, 38, 40}

-- crossOfJerusalem BMPString ::= {0, 0, 38, 41}

-- starAndCrescent BMPString ::= {0, 0, 38, 42}

-- farsiSymbol BMPString ::= {0, 0, 38, 43}

-- adiShakti BMPString ::= {0, 0, 38, 44}

-- hammerAndSickle BMPString ::= {0, 0, 38, 45}

-- peaceSymbol BMPString ::= {0, 0, 38, 46}

-- yinYang BMPString ::= {0, 0, 38, 47}

-- trigramForHeaven BMPString ::= {0, 0, 38, 48}

-- trigramForLake BMPString ::= {0, 0, 38, 49}

-- trigramForFire BMPString ::= {0, 0, 38, 50}

-- trigramForThunder BMPString ::= {0, 0, 38, 51}

-- trigramForWind BMPString ::= {0, 0, 38, 52}

-- trigramForWater BMPString ::= {0, 0, 38, 53}

-- trigramForMountain BMPString ::= {0, 0, 38, 54}

-- trigramForEarth BMPString ::= {0, 0, 38, 55}

-- wheelOfDharma BMPString ::= {0, 0, 38, 56}

-- whiteFrowningFace BMPString ::= {0, 0, 38, 57}

-- whiteSmilingFace BMPString ::= {0, 0, 38, 58}

-- blackSmilingFace BMPString ::= {0, 0, 38, 59}

-- whiteSunWithRays BMPString ::= {0, 0, 38, 60}

-- firstQuarterMoon BMPString ::= {0, 0, 38, 61}

-- lastQuarterMoon BMPString ::= {0, 0, 38, 62}

-- mercury BMPString ::= {0, 0, 38, 63}

-- femaleSign BMPString ::= {0, 0, 38, 64}

-- earth BMPString ::= {0, 0, 38, 65}

-- maleSign BMPString ::= {0, 0, 38, 66}

-- jupiter BMPString ::= {0, 0, 38, 67}

-- saturn BMPString ::= {0, 0, 38, 68}

-- uranus BMPString ::= {0, 0, 38, 69}

-- neptune BMPString ::= {0, 0, 38, 70}

-- pluto BMPString ::= {0, 0, 38, 71}

-- aries BMPString ::= {0, 0, 38, 72}

-- taurus BMPString ::= {0, 0, 38, 73}

-- gemini BMPString ::= {0, 0, 38, 74}

-- cancer BMPString ::= {0, 0, 38, 75}

-- leo BMPString ::= {0, 0, 38, 76}

-- virgo BMPString ::= {0, 0, 38, 77}

-- libra BMPString ::= {0, 0, 38, 78}

-- scorpius BMPString ::= {0, 0, 38, 79}

-- sagittarius BMPString ::= {0, 0, 38, 80}

-- capricorn BMPString ::= {0, 0, 38, 81}

-- aquarius BMPString ::= {0, 0, 38, 82}

-- pisces BMPString ::= {0, 0, 38, 83}

-- whiteChessKing BMPString ::= {0, 0, 38, 84}

-- whiteChessQueen BMPString ::= {0, 0, 38, 85}

-- whiteChessRook BMPString ::= {0, 0, 38, 86}

-- whiteChessBishop BMPString ::= {0, 0, 38, 87}

-- whiteChessKnight BMPString ::= {0, 0, 38, 88}

-- whiteChessPawn BMPString ::= {0, 0, 38, 89}

-- blackChessKing BMPString ::= {0, 0, 38, 90}

-- blackChessQueen BMPString ::= {0, 0, 38, 91}

-- blackChessRook BMPString ::= {0, 0, 38, 92}

-- blackChessBishop BMPString ::= {0, 0, 38, 93}

-- blackChessKnight BMPString ::= {0, 0, 38, 94}

-- blackChessPawn BMPString ::= {0, 0, 38, 95}

-- blackSpadeSuit BMPString ::= {0, 0, 38, 96}

-- whiteHeartSuit BMPString ::= {0, 0, 38, 97}

-- whiteDiamondSuit BMPString ::= {0, 0, 38, 98}

-- blackClubSuit BMPString ::= {0, 0, 38, 99}

-- whiteSpadeSuit BMPString ::= {0, 0, 38, 100}

-- blackHeartSuit BMPString ::= {0, 0, 38, 101}

-- blackDiamondSuit BMPString ::= {0, 0, 38, 102}

-- whiteClubSuit BMPString ::= {0, 0, 38, 103}

-- hotSprings BMPString ::= {0, 0, 38, 104}

-- quarterNote BMPString ::= {0, 0, 38, 105}

-- eighthNote BMPString ::= {0, 0, 38, 106}

-- beamedEighthNotes BMPString ::= {0, 0, 38, 107}

-- beamedSixteenthNotes BMPString ::= {0, 0, 38, 108}

-- musicFlatSign BMPString ::= {0, 0, 38, 109}

-- musicNaturalSign BMPString ::= {0, 0, 38, 110}

-- musicSharpSign BMPString ::= {0, 0, 38, 111}

-- westSyriacCross BMPString ::= {0, 0, 38, 112}

-- eastSyriacCross BMPString ::= {0, 0, 38, 113}

-- universalRecyclingSymbol BMPString ::= {0, 0, 38, 114}

-- recyclingSymbolForType-1Plastics BMPString ::= {0, 0, 38, 115}

-- recyclingSymbolForType-2Plastics BMPString ::= {0, 0, 38, 116}

-- recyclingSymbolForType-3Plastics BMPString ::= {0, 0, 38, 117}

-- recyclingSymbolForType-4Plastics BMPString ::= {0, 0, 38, 118}

-- recyclingSymbolForType-5Plastics BMPString ::= {0, 0, 38, 119}

-- recyclingSymbolForType-6Plastics BMPString ::= {0, 0, 38, 120}

-- recyclingSymbolForType-7Plastics BMPString ::= {0, 0, 38, 121}

-- recyclingSymbolForGenericMaterials BMPString ::= {0, 0, 38, 122}

-- blackUniversalRecyclingSymbol BMPString ::= {0, 0, 38, 123}

-- recycledPaperSymbol BMPString ::= {0, 0, 38, 124}

-- partially-recycledPaperSymbol BMPString ::= {0, 0, 38, 125}

-- dieFace-1 BMPString ::= {0, 0, 38, 128}

-- dieFace-2 BMPString ::= {0, 0, 38, 129}

-- dieFace-3 BMPString ::= {0, 0, 38, 130}

-- dieFace-4 BMPString ::= {0, 0, 38, 131}

-- dieFace-5 BMPString ::= {0, 0, 38, 132}

-- dieFace-6 BMPString ::= {0, 0, 38, 133}

-- whiteCircleWithDotRight BMPString ::= {0, 0, 38, 134}

-- whiteCircleWithTwoDots BMPString ::= {0, 0, 38, 135}

-- blackCircleWithWhiteDotRight BMPString ::= {0, 0, 38, 136}

-- blackCircleWithTwoWhiteDots BMPString ::= {0, 0, 38, 137}

-- upperBladeScissors BMPString ::= {0, 0, 39, 1}

-- blackScissors BMPString ::= {0, 0, 39, 2}

-- lowerBladeScissors BMPString ::= {0, 0, 39, 3}

-- whiteScissors BMPString ::= {0, 0, 39, 4}

-- telephoneLocationSign BMPString ::= {0, 0, 39, 6}

-- tapeDrive BMPString ::= {0, 0, 39, 7}

-- airplane BMPString ::= {0, 0, 39, 8}

-- envelope BMPString ::= {0, 0, 39, 9}

-- victoryHand BMPString ::= {0, 0, 39, 12}

-- writingHand BMPString ::= {0, 0, 39, 13}

-- lowerRightPencil BMPString ::= {0, 0, 39, 14}

-- pencil BMPString ::= {0, 0, 39, 15}

-- upperRightPencil BMPString ::= {0, 0, 39, 16}

-- whiteNib BMPString ::= {0, 0, 39, 17}

-- blackNib BMPString ::= {0, 0, 39, 18}

-- checkMark BMPString ::= {0, 0, 39, 19}

-- heavyCheckMark BMPString ::= {0, 0, 39, 20}

-- multiplicationX BMPString ::= {0, 0, 39, 21}

-- heavyMultiplicationX BMPString ::= {0, 0, 39, 22}

-- ballotX BMPString ::= {0, 0, 39, 23}

-- heavyBallotX BMPString ::= {0, 0, 39, 24}

-- outlinedGreekCross BMPString ::= {0, 0, 39, 25}

-- heavyGreekCross BMPString ::= {0, 0, 39, 26}

-- openCentreCross BMPString ::= {0, 0, 39, 27}

-- heavyOpenCentreCross BMPString ::= {0, 0, 39, 28}

-- latinCross BMPString ::= {0, 0, 39, 29}

-- shadowedWhiteLatinCross BMPString ::= {0, 0, 39, 30}

-- outlinedLatinCross BMPString ::= {0, 0, 39, 31}

-- malteseCross BMPString ::= {0, 0, 39, 32}

-- starOfDavid BMPString ::= {0, 0, 39, 33}

-- fourTeardrop-spokedAsterisk BMPString ::= {0, 0, 39, 34}

-- fourBalloon-spokedAsterisk BMPString ::= {0, 0, 39, 35}

-- heavyFourBalloon-spokedAsterisk BMPString ::= {0, 0, 39, 36}

-- fourClub-spokedAsterisk BMPString ::= {0, 0, 39, 37}

-- blackFourPointedStar BMPString ::= {0, 0, 39, 38}

-- whiteFourPointedStar BMPString ::= {0, 0, 39, 39}

-- stressOutlinedWhiteStar BMPString ::= {0, 0, 39, 41}

-- circledWhiteStar BMPString ::= {0, 0, 39, 42}

-- openCentreBlackStar BMPString ::= {0, 0, 39, 43}

-- blackCentreWhiteStar BMPString ::= {0, 0, 39, 44}

-- outlinedBlackStar BMPString ::= {0, 0, 39, 45}

-- heavyOutlinedBlackStar BMPString ::= {0, 0, 39, 46}

-- pinwheelStar BMPString ::= {0, 0, 39, 47}

-- shadowedWhiteStar BMPString ::= {0, 0, 39, 48}

-- heavyAsterisk BMPString ::= {0, 0, 39, 49}

-- openCentreAsterisk BMPString ::= {0, 0, 39, 50}

-- eightSpokedAsterisk BMPString ::= {0, 0, 39, 51}

-- eightPointedBlackStar BMPString ::= {0, 0, 39, 52}

-- eightPointedPinwheelStar BMPString ::= {0, 0, 39, 53}

-- sixPointedBlackStar BMPString ::= {0, 0, 39, 54}

-- eightPointedRectilinearBlackStar BMPString ::= {0, 0, 39, 55}

-- heavyEightPointedRectilinearBlackStar BMPString ::= {0, 0, 39, 56}

-- twelvePointedBlackStar BMPString ::= {0, 0, 39, 57}

-- sixteenPointedAsterisk BMPString ::= {0, 0, 39, 58}

-- teardrop-spokedAsterisk BMPString ::= {0, 0, 39, 59}

-- openCentreTeardrop-spokedAsterisk BMPString ::= {0, 0, 39, 60}

-- heavyTeardrop-spokedAsterisk BMPString ::= {0, 0, 39, 61}

-- sixPetalledBlackAndWhiteFlorette BMPString ::= {0, 0, 39, 62}

-- blackFlorette BMPString ::= {0, 0, 39, 63}

-- whiteFlorette BMPString ::= {0, 0, 39, 64}

-- eightPetalledOutlinedBlackFlorette BMPString ::= {0, 0, 39, 65}

-- circledOpenCentreEightPointedStar BMPString ::= {0, 0, 39, 66}

-- heavyTeardrop-spokedPinwheelAsterisk BMPString ::= {0, 0, 39, 67}

-- snowflake BMPString ::= {0, 0, 39, 68}

-- tightTrifoliateSnowflake BMPString ::= {0, 0, 39, 69}

-- heavyChevronSnowflake BMPString ::= {0, 0, 39, 70}

-- sparkle BMPString ::= {0, 0, 39, 71}

-- heavySparkle BMPString ::= {0, 0, 39, 72}

-- balloon-spokedAsterisk BMPString ::= {0, 0, 39, 73}

-- eightTeardrop-spokedPropellerAsterisk BMPString ::= {0, 0, 39, 74}

-- heavyEightTeardrop-spokedPropellerAsterisk BMPString ::= {0, 0, 39, 75}

-- shadowedWhiteCircle BMPString ::= {0, 0, 39, 77}

-- lowerRightDrop-shadowedWhiteSquare BMPString ::= {0, 0, 39, 79}

-- upperRightDrop-shadowedWhiteSquare BMPString ::= {0, 0, 39, 80}

-- lowerRightShadowedWhiteSquare BMPString ::= {0, 0, 39, 81}

-- upperRightShadowedWhiteSquare BMPString ::= {0, 0, 39, 82}

-- blackDiamondMinusWhiteX BMPString ::= {0, 0, 39, 86}

-- lightVerticalBar BMPString ::= {0, 0, 39, 88}

-- mediumVerticalBar BMPString ::= {0, 0, 39, 89}

-- heavyVerticalBar BMPString ::= {0, 0, 39, 90}

-- heavySingleTurnedCommaQuotationMarkOrnament BMPString ::= {0, 0, 39, 91}

-- heavySingleCommaQuotationMarkOrnament BMPString ::= {0, 0, 39, 92}

-- heavyDoubleTurnedCommaQuotationMarkOrnament BMPString ::= {0, 0, 39, 93}

-- heavyDoubleCommaQuotationMarkOrnament BMPString ::= {0, 0, 39, 94}

-- curvedStemParagraphSignOrnament BMPString ::= {0, 0, 39, 97}

-- heavyExclamationMarkOrnament BMPString ::= {0, 0, 39, 98}

-- heavyHeartExclamationMarkOrnament BMPString ::= {0, 0, 39, 99}

-- heavyBlackHeart BMPString ::= {0, 0, 39, 100}

-- rotatedHeavyBlackHeartBullet BMPString ::= {0, 0, 39, 101}

-- floralHeart BMPString ::= {0, 0, 39, 102}

-- rotatedFloralHeartBullet BMPString ::= {0, 0, 39, 103}

-- mediumLeftParenthesisOrnament BMPString ::= {0, 0, 39, 104}

-- mediumRightParenthesisOrnament BMPString ::= {0, 0, 39, 105}

-- mediumFlattenedLeftParenthesisOrnament BMPString ::= {0, 0, 39, 106}

-- mediumFlattenedRightParenthesisOrnament BMPString ::= {0, 0, 39, 107}

-- mediumLeft-pointingAngleBracketOrnament BMPString ::= {0, 0, 39, 108}

-- mediumRight-pointingAngleBracketOrnament BMPString ::= {0, 0, 39, 109}

-- heavyLeft-pointingAngleQuotationMarkOrnament BMPString ::= {0, 0, 39, 110}

-- heavyRight-pointingAngleQuotationMarkOrnament BMPString ::= {0, 0, 39, 111}

-- heavyLeft-pointingAngleBracketOrnament BMPString ::= {0, 0, 39, 112}

-- heavyRight-pointingAngleBracketOrnament BMPString ::= {0, 0, 39, 113}

-- lightLeftTortoiseShellBracketOrnament BMPString ::= {0, 0, 39, 114}

-- lightRightTortoiseShellBracketOrnament BMPString ::= {0, 0, 39, 115}

-- mediumLeftCurlyBracketOrnament BMPString ::= {0, 0, 39, 116}

-- mediumRightCurlyBracketOrnament BMPString ::= {0, 0, 39, 117}

-- dingbatNegativeCircledDigitOne BMPString ::= {0, 0, 39, 118}

-- dingbatNegativeCircledDigitTwo BMPString ::= {0, 0, 39, 119}

-- dingbatNegativeCircledDigitThree BMPString ::= {0, 0, 39, 120}

-- dingbatNegativeCircledDigitFour BMPString ::= {0, 0, 39, 121}

-- dingbatNegativeCircledDigitFive BMPString ::= {0, 0, 39, 122}

-- dingbatNegativeCircledDigitSix BMPString ::= {0, 0, 39, 123}

-- dingbatNegativeCircledDigitSeven BMPString ::= {0, 0, 39, 124}

-- dingbatNegativeCircledDigitEight BMPString ::= {0, 0, 39, 125}

-- dingbatNegativeCircledDigitNine BMPString ::= {0, 0, 39, 126}

-- dingbatNegativeCircledNumberTen BMPString ::= {0, 0, 39, 127}

-- dingbatCircledSans-serifDigitOne BMPString ::= {0, 0, 39, 128}

-- dingbatCircledSans-serifDigitTwo BMPString ::= {0, 0, 39, 129}

-- dingbatCircledSans-serifDigitThree BMPString ::= {0, 0, 39, 130}

-- dingbatCircledSans-serifDigitFour BMPString ::= {0, 0, 39, 131}

-- dingbatCircledSans-serifDigitFive BMPString ::= {0, 0, 39, 132}

-- dingbatCircledSans-serifDigitSix BMPString ::= {0, 0, 39, 133}

-- dingbatCircledSans-serifDigitSeven BMPString ::= {0, 0, 39, 134}

-- dingbatCircledSans-serifDigitEight BMPString ::= {0, 0, 39, 135}

-- dingbatCircledSans-serifDigitNine BMPString ::= {0, 0, 39, 136}

-- dingbatCircledSans-serifNumberTen BMPString ::= {0, 0, 39, 137}

-- dingbatNegativeCircledSans-serifDigitOne BMPString ::= {0, 0, 39, 138}

-- dingbatNegativeCircledSans-serifDigitTwo BMPString ::= {0, 0, 39, 139}

-- dingbatNegativeCircledSans-serifDigitThree BMPString ::= {0, 0, 39, 140}

-- dingbatNegativeCircledSans-serifDigitFour BMPString ::= {0, 0, 39, 141}

-- dingbatNegativeCircledSans-serifDigitFive BMPString ::= {0, 0, 39, 142}

-- dingbatNegativeCircledSans-serifDigitSix BMPString ::= {0, 0, 39, 143}

-- dingbatNegativeCircledSans-serifDigitSeven BMPString ::= {0, 0, 39, 144}

-- dingbatNegativeCircledSans-serifDigitEight BMPString ::= {0, 0, 39, 145}

-- dingbatNegativeCircledSans-serifDigitNine BMPString ::= {0, 0, 39, 146}

-- dingbatNegativeCircledSans-serifNumberTen BMPString ::= {0, 0, 39, 147}

-- heavyWide-headedRightwardsArrow BMPString ::= {0, 0, 39, 148}

-- heavySouthEastArrow BMPString ::= {0, 0, 39, 152}

-- heavyRightwardsArrow BMPString ::= {0, 0, 39, 153}

-- heavyNorthEastArrow BMPString ::= {0, 0, 39, 154}

-- draftingPointRightwardsArrow BMPString ::= {0, 0, 39, 155}

-- heavyRound-tippedRightwardsArrow BMPString ::= {0, 0, 39, 156}

-- triangle-headedRightwardsArrow BMPString ::= {0, 0, 39, 157}

-- heavyTriangle-headedRightwardsArrow BMPString ::= {0, 0, 39, 158}

-- dashedTriangle-headedRightwardsArrow BMPString ::= {0, 0, 39, 159}

-- heavyDashedTriangle-headedRightwardsArrow BMPString ::= {0, 0, 39, 160}

-- blackRightwardsArrow BMPString ::= {0, 0, 39, 161}

-- three-dTop-lightedRightwardsArrowhead BMPString ::= {0, 0, 39, 162}

-- three-dBottom-lightedRightwardsArrowhead BMPString ::= {0, 0, 39, 163}

-- blackRightwardsArrowhead BMPString ::= {0, 0, 39, 164}

-- heavyBlackCurvedDownwardsAndRightwardsArrow BMPString ::= {0, 0, 39, 165}

-- heavyBlackCurvedUpwardsAndRightwardsArrow BMPString ::= {0, 0, 39, 166}

-- squatBlackRightwardsArrow BMPString ::= {0, 0, 39, 167}

-- heavyConcave-pointedBlackRightwardsArrow BMPString ::= {0, 0, 39, 168}

-- right-shadedWhiteRightwardsArrow BMPString ::= {0, 0, 39, 169}

-- left-shadedWhiteRightwardsArrow BMPString ::= {0, 0, 39, 170}

-- back-tiltedShadowedWhiteRightwardsArrow BMPString ::= {0, 0, 39, 171}

-- front-tiltedShadowedWhiteRightwardsArrow BMPString ::= {0, 0, 39, 172}

-- heavyLowerRight-shadowedWhiteRightwardsArrow BMPString ::= {0, 0, 39, 173}

-- heavyUpperRight-shadowedWhiteRightwardsArrow BMPString ::= {0, 0, 39, 174}

-- notchedLowerRight-shadowedWhiteRightwardsArrow BMPString ::= {0, 0, 39, 175}

-- notchedUpperRight-shadowedWhiteRightwardsArrow BMPString ::= {0, 0, 39, 177}

-- circledHeavyWhiteRightwardsArrow BMPString ::= {0, 0, 39, 178}

-- white-featheredRightwardsArrow BMPString ::= {0, 0, 39, 179}

-- black-featheredSouthEastArrow BMPString ::= {0, 0, 39, 180}

-- black-featheredRightwardsArrow BMPString ::= {0, 0, 39, 181}

-- black-featheredNorthEastArrow BMPString ::= {0, 0, 39, 182}

-- heavyBlack-featheredSouthEastArrow BMPString ::= {0, 0, 39, 183}

-- heavyBlack-featheredRightwardsArrow BMPString ::= {0, 0, 39, 184}

-- heavyBlack-featheredNorthEastArrow BMPString ::= {0, 0, 39, 185}

-- teardrop-barbedRightwardsArrow BMPString ::= {0, 0, 39, 186}

-- heavyTeardrop-shankedRightwardsArrow BMPString ::= {0, 0, 39, 187}

-- wedge-tailedRightwardsArrow BMPString ::= {0, 0, 39, 188}

-- heavyWedge-tailedRightwardsArrow BMPString ::= {0, 0, 39, 189}

-- open-outlinedRightwardsArrow BMPString ::= {0, 0, 39, 190}

-- whiteDiamondWithCentredDot BMPString ::= {0, 0, 39, 208}

-- andWithDot BMPString ::= {0, 0, 39, 209}

-- elementOfOpeningUpwards BMPString ::= {0, 0, 39, 210}

-- lowerRightCornerWithDot BMPString ::= {0, 0, 39, 211}

-- upperLeftCornerWithDot BMPString ::= {0, 0, 39, 212}

-- leftOuterJoin BMPString ::= {0, 0, 39, 213}

-- rightOuterJoin BMPString ::= {0, 0, 39, 214}

-- fullOuterJoin BMPString ::= {0, 0, 39, 215}

-- largeUpTack BMPString ::= {0, 0, 39, 216}

-- largeDownTack BMPString ::= {0, 0, 39, 217}

-- leftAndRightDoubleTurnstile BMPString ::= {0, 0, 39, 218}

-- leftAndRightTack BMPString ::= {0, 0, 39, 219}

-- leftMultimap BMPString ::= {0, 0, 39, 220}

-- longRightTack BMPString ::= {0, 0, 39, 221}

-- longLeftTack BMPString ::= {0, 0, 39, 222}

-- upTackWithCircleAbove BMPString ::= {0, 0, 39, 223}

-- lozengeDividedByHorizontalRule BMPString ::= {0, 0, 39, 224}

-- whiteConcave-sidedDiamond BMPString ::= {0, 0, 39, 225}

-- whiteConcave-sidedDiamondWithLeftwardsTick BMPString ::= {0, 0, 39, 226}

-- whiteConcave-sidedDiamondWithRightwardsTick BMPString ::= {0, 0, 39, 227}

-- whiteSquareWithLeftwardsTick BMPString ::= {0, 0, 39, 228}

-- whiteSquareWithRightwardsTick BMPString ::= {0, 0, 39, 229}

-- mathematicalLeftWhiteSquareBracket BMPString ::= {0, 0, 39, 230}

-- mathematicalRightWhiteSquareBracket BMPString ::= {0, 0, 39, 231}

-- mathematicalLeftAngleBracket BMPString ::= {0, 0, 39, 232}

-- mathematicalRightAngleBracket BMPString ::= {0, 0, 39, 233}

-- mathematicalLeftDoubleAngleBracket BMPString ::= {0, 0, 39, 234}

-- mathematicalRightDoubleAngleBracket BMPString ::= {0, 0, 39, 235}

-- upwardsQuadrupleArrow BMPString ::= {0, 0, 39, 240}

-- downwardsQuadrupleArrow BMPString ::= {0, 0, 39, 241}

-- anticlockwiseGappedCircleArrow BMPString ::= {0, 0, 39, 242}

-- clockwiseGappedCircleArrow BMPString ::= {0, 0, 39, 243}

-- rightArrowWithCircledPlus BMPString ::= {0, 0, 39, 244}

-- longLeftwardsArrow BMPString ::= {0, 0, 39, 245}

-- longRightwardsArrow BMPString ::= {0, 0, 39, 246}

-- longLeftRightArrow BMPString ::= {0, 0, 39, 247}

-- longLeftwardsDoubleArrow BMPString ::= {0, 0, 39, 248}

-- longRightwardsDoubleArrow BMPString ::= {0, 0, 39, 249}

-- longLeftRightDoubleArrow BMPString ::= {0, 0, 39, 250}

-- longLeftwardsArrowFromBar BMPString ::= {0, 0, 39, 251}

-- longRightwardsArrowFromBar BMPString ::= {0, 0, 39, 252}

-- longLeftwardsDoubleArrowFromBar BMPString ::= {0, 0, 39, 253}

-- longRightwardsDoubleArrowFromBar BMPString ::= {0, 0, 39, 254}

-- longRightwardsSquiggleArrow BMPString ::= {0, 0, 39, 255}

-- braillePatternBlank BMPString ::= {0, 0, 40, 0}

-- braillePatternDots-1 BMPString ::= {0, 0, 40, 1}

-- braillePatternDots-2 BMPString ::= {0, 0, 40, 2}

-- braillePatternDots-12 BMPString ::= {0, 0, 40, 3}

-- braillePatternDots-3 BMPString ::= {0, 0, 40, 4}

-- braillePatternDots-13 BMPString ::= {0, 0, 40, 5}

-- braillePatternDots-23 BMPString ::= {0, 0, 40, 6}

-- braillePatternDots-123 BMPString ::= {0, 0, 40, 7}

-- braillePatternDots-4 BMPString ::= {0, 0, 40, 8}

-- braillePatternDots-14 BMPString ::= {0, 0, 40, 9}

-- braillePatternDots-24 BMPString ::= {0, 0, 40, 10}

-- braillePatternDots-124 BMPString ::= {0, 0, 40, 11}

-- braillePatternDots-34 BMPString ::= {0, 0, 40, 12}

-- braillePatternDots-134 BMPString ::= {0, 0, 40, 13}

-- braillePatternDots-234 BMPString ::= {0, 0, 40, 14}

-- braillePatternDots-1234 BMPString ::= {0, 0, 40, 15}

-- braillePatternDots-5 BMPString ::= {0, 0, 40, 16}

-- braillePatternDots-15 BMPString ::= {0, 0, 40, 17}

-- braillePatternDots-25 BMPString ::= {0, 0, 40, 18}

-- braillePatternDots-125 BMPString ::= {0, 0, 40, 19}

-- braillePatternDots-35 BMPString ::= {0, 0, 40, 20}

-- braillePatternDots-135 BMPString ::= {0, 0, 40, 21}

-- braillePatternDots-235 BMPString ::= {0, 0, 40, 22}

-- braillePatternDots-1235 BMPString ::= {0, 0, 40, 23}

-- braillePatternDots-45 BMPString ::= {0, 0, 40, 24}

-- braillePatternDots-145 BMPString ::= {0, 0, 40, 25}

-- braillePatternDots-245 BMPString ::= {0, 0, 40, 26}

-- braillePatternDots-1245 BMPString ::= {0, 0, 40, 27}

-- braillePatternDots-345 BMPString ::= {0, 0, 40, 28}

-- braillePatternDots-1345 BMPString ::= {0, 0, 40, 29}

-- braillePatternDots-2345 BMPString ::= {0, 0, 40, 30}

-- braillePatternDots-12345 BMPString ::= {0, 0, 40, 31}

-- braillePatternDots-6 BMPString ::= {0, 0, 40, 32}

-- braillePatternDots-16 BMPString ::= {0, 0, 40, 33}

-- braillePatternDots-26 BMPString ::= {0, 0, 40, 34}

-- braillePatternDots-126 BMPString ::= {0, 0, 40, 35}

-- braillePatternDots-36 BMPString ::= {0, 0, 40, 36}

-- braillePatternDots-136 BMPString ::= {0, 0, 40, 37}

-- braillePatternDots-236 BMPString ::= {0, 0, 40, 38}

-- braillePatternDots-1236 BMPString ::= {0, 0, 40, 39}

-- braillePatternDots-46 BMPString ::= {0, 0, 40, 40}

-- braillePatternDots-146 BMPString ::= {0, 0, 40, 41}

-- braillePatternDots-246 BMPString ::= {0, 0, 40, 42}

-- braillePatternDots-1246 BMPString ::= {0, 0, 40, 43}

-- braillePatternDots-346 BMPString ::= {0, 0, 40, 44}

-- braillePatternDots-1346 BMPString ::= {0, 0, 40, 45}

-- braillePatternDots-2346 BMPString ::= {0, 0, 40, 46}

-- braillePatternDots-12346 BMPString ::= {0, 0, 40, 47}

-- braillePatternDots-56 BMPString ::= {0, 0, 40, 48}

-- braillePatternDots-156 BMPString ::= {0, 0, 40, 49}

-- braillePatternDots-256 BMPString ::= {0, 0, 40, 50}

-- braillePatternDots-1256 BMPString ::= {0, 0, 40, 51}

-- braillePatternDots-356 BMPString ::= {0, 0, 40, 52}

-- braillePatternDots-1356 BMPString ::= {0, 0, 40, 53}

-- braillePatternDots-2356 BMPString ::= {0, 0, 40, 54}

-- braillePatternDots-12356 BMPString ::= {0, 0, 40, 55}

-- braillePatternDots-456 BMPString ::= {0, 0, 40, 56}

-- braillePatternDots-1456 BMPString ::= {0, 0, 40, 57}

-- braillePatternDots-2456 BMPString ::= {0, 0, 40, 58}

-- braillePatternDots-12456 BMPString ::= {0, 0, 40, 59}

-- braillePatternDots-3456 BMPString ::= {0, 0, 40, 60}

-- braillePatternDots-13456 BMPString ::= {0, 0, 40, 61}

-- braillePatternDots-23456 BMPString ::= {0, 0, 40, 62}

-- braillePatternDots-123456 BMPString ::= {0, 0, 40, 63}

-- braillePatternDots-7 BMPString ::= {0, 0, 40, 64}

-- braillePatternDots-17 BMPString ::= {0, 0, 40, 65}

-- braillePatternDots-27 BMPString ::= {0, 0, 40, 66}

-- braillePatternDots-127 BMPString ::= {0, 0, 40, 67}

-- braillePatternDots-37 BMPString ::= {0, 0, 40, 68}

-- braillePatternDots-137 BMPString ::= {0, 0, 40, 69}

-- braillePatternDots-237 BMPString ::= {0, 0, 40, 70}

-- braillePatternDots-1237 BMPString ::= {0, 0, 40, 71}

-- braillePatternDots-47 BMPString ::= {0, 0, 40, 72}

-- braillePatternDots-147 BMPString ::= {0, 0, 40, 73}

-- braillePatternDots-247 BMPString ::= {0, 0, 40, 74}

-- braillePatternDots-1247 BMPString ::= {0, 0, 40, 75}

-- braillePatternDots-347 BMPString ::= {0, 0, 40, 76}

-- braillePatternDots-1347 BMPString ::= {0, 0, 40, 77}

-- braillePatternDots-2347 BMPString ::= {0, 0, 40, 78}

-- braillePatternDots-12347 BMPString ::= {0, 0, 40, 79}

-- braillePatternDots-57 BMPString ::= {0, 0, 40, 80}

-- braillePatternDots-157 BMPString ::= {0, 0, 40, 81}

-- braillePatternDots-257 BMPString ::= {0, 0, 40, 82}

-- braillePatternDots-1257 BMPString ::= {0, 0, 40, 83}

-- braillePatternDots-357 BMPString ::= {0, 0, 40, 84}

-- braillePatternDots-1357 BMPString ::= {0, 0, 40, 85}

-- braillePatternDots-2357 BMPString ::= {0, 0, 40, 86}

-- braillePatternDots-12357 BMPString ::= {0, 0, 40, 87}

-- braillePatternDots-457 BMPString ::= {0, 0, 40, 88}

-- braillePatternDots-1457 BMPString ::= {0, 0, 40, 89}

-- braillePatternDots-2457 BMPString ::= {0, 0, 40, 90}

-- braillePatternDots-12457 BMPString ::= {0, 0, 40, 91}

-- braillePatternDots-3457 BMPString ::= {0, 0, 40, 92}

-- braillePatternDots-13457 BMPString ::= {0, 0, 40, 93}

-- braillePatternDots-23457 BMPString ::= {0, 0, 40, 94}

-- braillePatternDots-123457 BMPString ::= {0, 0, 40, 95}

-- braillePatternDots-67 BMPString ::= {0, 0, 40, 96}

-- braillePatternDots-167 BMPString ::= {0, 0, 40, 97}

-- braillePatternDots-267 BMPString ::= {0, 0, 40, 98}

-- braillePatternDots-1267 BMPString ::= {0, 0, 40, 99}

-- braillePatternDots-367 BMPString ::= {0, 0, 40, 100}

-- braillePatternDots-1367 BMPString ::= {0, 0, 40, 101}

-- braillePatternDots-2367 BMPString ::= {0, 0, 40, 102}

-- braillePatternDots-12367 BMPString ::= {0, 0, 40, 103}

-- braillePatternDots-467 BMPString ::= {0, 0, 40, 104}

-- braillePatternDots-1467 BMPString ::= {0, 0, 40, 105}

-- braillePatternDots-2467 BMPString ::= {0, 0, 40, 106}

-- braillePatternDots-12467 BMPString ::= {0, 0, 40, 107}

-- braillePatternDots-3467 BMPString ::= {0, 0, 40, 108}

-- braillePatternDots-13467 BMPString ::= {0, 0, 40, 109}

-- braillePatternDots-23467 BMPString ::= {0, 0, 40, 110}

-- braillePatternDots-123467 BMPString ::= {0, 0, 40, 111}

-- braillePatternDots-567 BMPString ::= {0, 0, 40, 112}

-- braillePatternDots-1567 BMPString ::= {0, 0, 40, 113}

-- braillePatternDots-2567 BMPString ::= {0, 0, 40, 114}

-- braillePatternDots-12567 BMPString ::= {0, 0, 40, 115}

-- braillePatternDots-3567 BMPString ::= {0, 0, 40, 116}

-- braillePatternDots-13567 BMPString ::= {0, 0, 40, 117}

-- braillePatternDots-23567 BMPString ::= {0, 0, 40, 118}

-- braillePatternDots-123567 BMPString ::= {0, 0, 40, 119}

-- braillePatternDots-4567 BMPString ::= {0, 0, 40, 120}

-- braillePatternDots-14567 BMPString ::= {0, 0, 40, 121}

-- braillePatternDots-24567 BMPString ::= {0, 0, 40, 122}

-- braillePatternDots-124567 BMPString ::= {0, 0, 40, 123}

-- braillePatternDots-34567 BMPString ::= {0, 0, 40, 124}

-- braillePatternDots-134567 BMPString ::= {0, 0, 40, 125}

-- braillePatternDots-234567 BMPString ::= {0, 0, 40, 126}

-- braillePatternDots-1234567 BMPString ::= {0, 0, 40, 127}

-- braillePatternDots-8 BMPString ::= {0, 0, 40, 128}

-- braillePatternDots-18 BMPString ::= {0, 0, 40, 129}

-- braillePatternDots-28 BMPString ::= {0, 0, 40, 130}

-- braillePatternDots-128 BMPString ::= {0, 0, 40, 131}

-- braillePatternDots-38 BMPString ::= {0, 0, 40, 132}

-- braillePatternDots-138 BMPString ::= {0, 0, 40, 133}

-- braillePatternDots-238 BMPString ::= {0, 0, 40, 134}

-- braillePatternDots-1238 BMPString ::= {0, 0, 40, 135}

-- braillePatternDots-48 BMPString ::= {0, 0, 40, 136}

-- braillePatternDots-148 BMPString ::= {0, 0, 40, 137}

-- braillePatternDots-248 BMPString ::= {0, 0, 40, 138}

-- braillePatternDots-1248 BMPString ::= {0, 0, 40, 139}

-- braillePatternDots-348 BMPString ::= {0, 0, 40, 140}

-- braillePatternDots-1348 BMPString ::= {0, 0, 40, 141}

-- braillePatternDots-2348 BMPString ::= {0, 0, 40, 142}

-- braillePatternDots-12348 BMPString ::= {0, 0, 40, 143}

-- braillePatternDots-58 BMPString ::= {0, 0, 40, 144}

-- braillePatternDots-158 BMPString ::= {0, 0, 40, 145}

-- braillePatternDots-258 BMPString ::= {0, 0, 40, 146}

-- braillePatternDots-1258 BMPString ::= {0, 0, 40, 147}

-- braillePatternDots-358 BMPString ::= {0, 0, 40, 148}

-- braillePatternDots-1358 BMPString ::= {0, 0, 40, 149}

-- braillePatternDots-2358 BMPString ::= {0, 0, 40, 150}

-- braillePatternDots-12358 BMPString ::= {0, 0, 40, 151}

-- braillePatternDots-458 BMPString ::= {0, 0, 40, 152}

-- braillePatternDots-1458 BMPString ::= {0, 0, 40, 153}

-- braillePatternDots-2458 BMPString ::= {0, 0, 40, 154}

-- braillePatternDots-12458 BMPString ::= {0, 0, 40, 155}

-- braillePatternDots-3458 BMPString ::= {0, 0, 40, 156}

-- braillePatternDots-13458 BMPString ::= {0, 0, 40, 157}

-- braillePatternDots-23458 BMPString ::= {0, 0, 40, 158}

-- braillePatternDots-123458 BMPString ::= {0, 0, 40, 159}

-- braillePatternDots-68 BMPString ::= {0, 0, 40, 160}

-- braillePatternDots-168 BMPString ::= {0, 0, 40, 161}

-- braillePatternDots-268 BMPString ::= {0, 0, 40, 162}

-- braillePatternDots-1268 BMPString ::= {0, 0, 40, 163}

-- braillePatternDots-368 BMPString ::= {0, 0, 40, 164}

-- braillePatternDots-1368 BMPString ::= {0, 0, 40, 165}

-- braillePatternDots-2368 BMPString ::= {0, 0, 40, 166}

-- braillePatternDots-12368 BMPString ::= {0, 0, 40, 167}

-- braillePatternDots-468 BMPString ::= {0, 0, 40, 168}

-- braillePatternDots-1468 BMPString ::= {0, 0, 40, 169}

-- braillePatternDots-2468 BMPString ::= {0, 0, 40, 170}

-- braillePatternDots-12468 BMPString ::= {0, 0, 40, 171}

-- braillePatternDots-3468 BMPString ::= {0, 0, 40, 172}

-- braillePatternDots-13468 BMPString ::= {0, 0, 40, 173}

-- braillePatternDots-23468 BMPString ::= {0, 0, 40, 174}

-- braillePatternDots-123468 BMPString ::= {0, 0, 40, 175}

-- braillePatternDots-568 BMPString ::= {0, 0, 40, 176}

-- braillePatternDots-1568 BMPString ::= {0, 0, 40, 177}

-- braillePatternDots-2568 BMPString ::= {0, 0, 40, 178}

-- braillePatternDots-12568 BMPString ::= {0, 0, 40, 179}

-- braillePatternDots-3568 BMPString ::= {0, 0, 40, 180}

-- braillePatternDots-13568 BMPString ::= {0, 0, 40, 181}

-- braillePatternDots-23568 BMPString ::= {0, 0, 40, 182}

-- braillePatternDots-123568 BMPString ::= {0, 0, 40, 183}

-- braillePatternDots-4568 BMPString ::= {0, 0, 40, 184}

-- braillePatternDots-14568 BMPString ::= {0, 0, 40, 185}

-- braillePatternDots-24568 BMPString ::= {0, 0, 40, 186}

-- braillePatternDots-124568 BMPString ::= {0, 0, 40, 187}

-- braillePatternDots-34568 BMPString ::= {0, 0, 40, 188}

-- braillePatternDots-134568 BMPString ::= {0, 0, 40, 189}

-- braillePatternDots-234568 BMPString ::= {0, 0, 40, 190}

-- braillePatternDots-1234568 BMPString ::= {0, 0, 40, 191}

-- braillePatternDots-78 BMPString ::= {0, 0, 40, 192}

-- braillePatternDots-178 BMPString ::= {0, 0, 40, 193}

-- braillePatternDots-278 BMPString ::= {0, 0, 40, 194}

-- braillePatternDots-1278 BMPString ::= {0, 0, 40, 195}

-- braillePatternDots-378 BMPString ::= {0, 0, 40, 196}

-- braillePatternDots-1378 BMPString ::= {0, 0, 40, 197}

-- braillePatternDots-2378 BMPString ::= {0, 0, 40, 198}

-- braillePatternDots-12378 BMPString ::= {0, 0, 40, 199}

-- braillePatternDots-478 BMPString ::= {0, 0, 40, 200}

-- braillePatternDots-1478 BMPString ::= {0, 0, 40, 201}

-- braillePatternDots-2478 BMPString ::= {0, 0, 40, 202}

-- braillePatternDots-12478 BMPString ::= {0, 0, 40, 203}

-- braillePatternDots-3478 BMPString ::= {0, 0, 40, 204}

-- braillePatternDots-13478 BMPString ::= {0, 0, 40, 205}

-- braillePatternDots-23478 BMPString ::= {0, 0, 40, 206}

-- braillePatternDots-123478 BMPString ::= {0, 0, 40, 207}

-- braillePatternDots-578 BMPString ::= {0, 0, 40, 208}

-- braillePatternDots-1578 BMPString ::= {0, 0, 40, 209}

-- braillePatternDots-2578 BMPString ::= {0, 0, 40, 210}

-- braillePatternDots-12578 BMPString ::= {0, 0, 40, 211}

-- braillePatternDots-3578 BMPString ::= {0, 0, 40, 212}

-- braillePatternDots-13578 BMPString ::= {0, 0, 40, 213}

-- braillePatternDots-23578 BMPString ::= {0, 0, 40, 214}

-- braillePatternDots-123578 BMPString ::= {0, 0, 40, 215}

-- braillePatternDots-4578 BMPString ::= {0, 0, 40, 216}

-- braillePatternDots-14578 BMPString ::= {0, 0, 40, 217}

-- braillePatternDots-24578 BMPString ::= {0, 0, 40, 218}

-- braillePatternDots-124578 BMPString ::= {0, 0, 40, 219}

-- braillePatternDots-34578 BMPString ::= {0, 0, 40, 220}

-- braillePatternDots-134578 BMPString ::= {0, 0, 40, 221}

-- braillePatternDots-234578 BMPString ::= {0, 0, 40, 222}

-- braillePatternDots-1234578 BMPString ::= {0, 0, 40, 223}

-- braillePatternDots-678 BMPString ::= {0, 0, 40, 224}

-- braillePatternDots-1678 BMPString ::= {0, 0, 40, 225}

-- braillePatternDots-2678 BMPString ::= {0, 0, 40, 226}

-- braillePatternDots-12678 BMPString ::= {0, 0, 40, 227}

-- braillePatternDots-3678 BMPString ::= {0, 0, 40, 228}

-- braillePatternDots-13678 BMPString ::= {0, 0, 40, 229}

-- braillePatternDots-23678 BMPString ::= {0, 0, 40, 230}

-- braillePatternDots-123678 BMPString ::= {0, 0, 40, 231}

-- braillePatternDots-4678 BMPString ::= {0, 0, 40, 232}

-- braillePatternDots-14678 BMPString ::= {0, 0, 40, 233}

-- braillePatternDots-24678 BMPString ::= {0, 0, 40, 234}

-- braillePatternDots-124678 BMPString ::= {0, 0, 40, 235}

-- braillePatternDots-34678 BMPString ::= {0, 0, 40, 236}

-- braillePatternDots-134678 BMPString ::= {0, 0, 40, 237}

-- braillePatternDots-234678 BMPString ::= {0, 0, 40, 238}

-- braillePatternDots-1234678 BMPString ::= {0, 0, 40, 239}

-- braillePatternDots-5678 BMPString ::= {0, 0, 40, 240}

-- braillePatternDots-15678 BMPString ::= {0, 0, 40, 241}

-- braillePatternDots-25678 BMPString ::= {0, 0, 40, 242}

-- braillePatternDots-125678 BMPString ::= {0, 0, 40, 243}

-- braillePatternDots-35678 BMPString ::= {0, 0, 40, 244}

-- braillePatternDots-135678 BMPString ::= {0, 0, 40, 245}

-- braillePatternDots-235678 BMPString ::= {0, 0, 40, 246}

-- braillePatternDots-1235678 BMPString ::= {0, 0, 40, 247}

-- braillePatternDots-45678 BMPString ::= {0, 0, 40, 248}

-- braillePatternDots-145678 BMPString ::= {0, 0, 40, 249}

-- braillePatternDots-245678 BMPString ::= {0, 0, 40, 250}

-- braillePatternDots-1245678 BMPString ::= {0, 0, 40, 251}

-- braillePatternDots-345678 BMPString ::= {0, 0, 40, 252}

-- braillePatternDots-1345678 BMPString ::= {0, 0, 40, 253}

-- braillePatternDots-2345678 BMPString ::= {0, 0, 40, 254}

-- braillePatternDots-12345678 BMPString ::= {0, 0, 40, 255}

-- rightwardsTwo-headedArrowWithVerticalStroke BMPString ::= {0, 0, 41, 0}

-- rightwardsTwo-headedArrowWithDoubleVerticalStroke BMPString ::= {0, 0, 41, 1}

-- leftwardsDoubleArrowWithVerticalStroke BMPString ::= {0, 0, 41, 2}

-- rightwardsDoubleArrowWithVerticalStroke BMPString ::= {0, 0, 41, 3}

-- leftRightDoubleArrowWithVerticalStroke BMPString ::= {0, 0, 41, 4}

-- rightwardsTwo-headedArrowFromBar BMPString ::= {0, 0, 41, 5}

-- leftwardsDoubleArrowFromBar BMPString ::= {0, 0, 41, 6}

-- rightwardsDoubleArrowFromBar BMPString ::= {0, 0, 41, 7}

-- downwardsArrowWithHorizontalStroke BMPString ::= {0, 0, 41, 8}

-- upwardsArrowWithHorizontalStroke BMPString ::= {0, 0, 41, 9}

-- upwardsTripleArrow BMPString ::= {0, 0, 41, 10}

-- downwardsTripleArrow BMPString ::= {0, 0, 41, 11}

-- leftwardsDoubleDashArrow BMPString ::= {0, 0, 41, 12}

-- rightwardsDoubleDashArrow BMPString ::= {0, 0, 41, 13}

-- leftwardsTripleDashArrow BMPString ::= {0, 0, 41, 14}

-- rightwardsTripleDashArrow BMPString ::= {0, 0, 41, 15}

-- rightwardsTwo-headedTripleDashArrow BMPString ::= {0, 0, 41, 16}

-- rightwardsArrowWithDottedStem BMPString ::= {0, 0, 41, 17}

-- upwardsArrowToBar BMPString ::= {0, 0, 41, 18}

-- downwardsArrowToBar BMPString ::= {0, 0, 41, 19}

-- rightwardsArrowWithTailWithVerticalStroke BMPString ::= {0, 0, 41, 20}

-- rightwardsArrowWithTailWithDoubleVerticalStroke BMPString ::= {0, 0, 41, 21}

-- rightwardsTwo-headedArrowWithTail BMPString ::= {0, 0, 41, 22}

-- rightwardsTwo-headedArrowWithTailWithVerticalStroke BMPString ::=
--   {0, 0, 41, 23}

-- rightwardsTwo-headedArrowWithTailWithDoubleVerticalStroke BMPString ::=
--   {0, 0, 41, 24}

-- leftwardsArrow-tail BMPString ::= {0, 0, 41, 25}

-- rightwardsArrow-tail BMPString ::= {0, 0, 41, 26}

-- leftwardsDoubleArrow-tail BMPString ::= {0, 0, 41, 27}

-- rightwardsDoubleArrow-tail BMPString ::= {0, 0, 41, 28}

-- leftwardsArrowToBlackDiamond BMPString ::= {0, 0, 41, 29}

-- rightwardsArrowToBlackDiamond BMPString ::= {0, 0, 41, 30}

-- leftwardsArrowFromBarToBlackDiamond BMPString ::= {0, 0, 41, 31}

-- rightwardsArrowFromBarToBlackDiamond BMPString ::= {0, 0, 41, 32}

-- northWestAndSouthEastArrow BMPString ::= {0, 0, 41, 33}

-- northEastAndSouthWestArrow BMPString ::= {0, 0, 41, 34}

-- northWestArrowWithHook BMPString ::= {0, 0, 41, 35}

-- northEastArrowWithHook BMPString ::= {0, 0, 41, 36}

-- southEastArrowWithHook BMPString ::= {0, 0, 41, 37}

-- southWestArrowWithHook BMPString ::= {0, 0, 41, 38}

-- northWestArrowAndNorthEastArrow BMPString ::= {0, 0, 41, 39}

-- northEastArrowAndSouthEastArrow BMPString ::= {0, 0, 41, 40}

-- southEastArrowAndSouthWestArrow BMPString ::= {0, 0, 41, 41}

-- southWestArrowAndNorthWestArrow BMPString ::= {0, 0, 41, 42}

-- risingDiagonalCrossingFallingDiagonal BMPString ::= {0, 0, 41, 43}

-- fallingDiagonalCrossingRisingDiagonal BMPString ::= {0, 0, 41, 44}

-- southEastArrowCrossingNorthEastArrow BMPString ::= {0, 0, 41, 45}

-- northEastArrowCrossingSouthEastArrow BMPString ::= {0, 0, 41, 46}

-- fallingDiagonalCrossingNorthEastArrow BMPString ::= {0, 0, 41, 47}

-- risingDiagonalCrossingSouthEastArrow BMPString ::= {0, 0, 41, 48}

-- northEastArrowCrossingNorthWestArrow BMPString ::= {0, 0, 41, 49}

-- northWestArrowCrossingNorthEastArrow BMPString ::= {0, 0, 41, 50}

-- waveArrowPointingDirectlyRight BMPString ::= {0, 0, 41, 51}

-- arrowPointingRightwardsThenCurvingUpwards BMPString ::= {0, 0, 41, 52}

-- arrowPointingRightwardsThenCurvingDownwards BMPString ::= {0, 0, 41, 53}

-- arrowPointingDownwardsThenCurvingLeftwards BMPString ::= {0, 0, 41, 54}

-- arrowPointingDownwardsThenCurvingRightwards BMPString ::= {0, 0, 41, 55}

-- right-sideArcClockwiseArrow BMPString ::= {0, 0, 41, 56}

-- left-sideArcAnticlockwiseArrow BMPString ::= {0, 0, 41, 57}

-- topArcAnticlockwiseArrow BMPString ::= {0, 0, 41, 58}

-- bottomArcAnticlockwiseArrow BMPString ::= {0, 0, 41, 59}

-- topArcClockwiseArrowWithMinus BMPString ::= {0, 0, 41, 60}

-- topArcAnticlockwiseArrowWithPlus BMPString ::= {0, 0, 41, 61}

-- lowerRightSemicircularClockwiseArrow BMPString ::= {0, 0, 41, 62}

-- lowerLeftSemicircularAnticlockwiseArrow BMPString ::= {0, 0, 41, 63}

-- anticlockwiseClosedCircleArrow BMPString ::= {0, 0, 41, 64}

-- clockwiseClosedCircleArrow BMPString ::= {0, 0, 41, 65}

-- rightwardsArrowAboveShortLeftwardsArrow BMPString ::= {0, 0, 41, 66}

-- leftwardsArrowAboveShortRightwardsArrow BMPString ::= {0, 0, 41, 67}

-- shortRightwardsArrowAboveLeftwardsArrow BMPString ::= {0, 0, 41, 68}

-- rightwardsArrowWithPlusBelow BMPString ::= {0, 0, 41, 69}

-- leftwardsArrowWithPlusBelow BMPString ::= {0, 0, 41, 70}

-- rightwardsArrowThroughX BMPString ::= {0, 0, 41, 71}

-- leftRightArrowThroughSmallCircle BMPString ::= {0, 0, 41, 72}

-- upwardsTwo-headedArrowFromSmallCircle BMPString ::= {0, 0, 41, 73}

-- leftBarbUpRightBarbDownHarpoon BMPString ::= {0, 0, 41, 74}

-- leftBarbDownRightBarbUpHarpoon BMPString ::= {0, 0, 41, 75}

-- upBarbRightDownBarbLeftHarpoon BMPString ::= {0, 0, 41, 76}

-- upBarbLeftDownBarbRightHarpoon BMPString ::= {0, 0, 41, 77}

-- leftBarbUpRightBarbUpHarpoon BMPString ::= {0, 0, 41, 78}

-- upBarbRightDownBarbRightHarpoon BMPString ::= {0, 0, 41, 79}

-- leftBarbDownRightBarbDownHarpoon BMPString ::= {0, 0, 41, 80}

-- upBarbLeftDownBarbLeftHarpoon BMPString ::= {0, 0, 41, 81}

-- leftwardsHarpoonWithBarbUpToBar BMPString ::= {0, 0, 41, 82}

-- rightwardsHarpoonWithBarbUpToBar BMPString ::= {0, 0, 41, 83}

-- upwardsHarpoonWithBarbRightToBar BMPString ::= {0, 0, 41, 84}

-- downwardsHarpoonWithBarbRightToBar BMPString ::= {0, 0, 41, 85}

-- leftwardsHarpoonWithBarbDownToBar BMPString ::= {0, 0, 41, 86}

-- rightwardsHarpoonWithBarbDownToBar BMPString ::= {0, 0, 41, 87}

-- upwardsHarpoonWithBarbLeftToBar BMPString ::= {0, 0, 41, 88}

-- downwardsHarpoonWithBarbLeftToBar BMPString ::= {0, 0, 41, 89}

-- leftwardsHarpoonWithBarbUpFromBar BMPString ::= {0, 0, 41, 90}

-- rightwardsHarpoonWithBarbUpFromBar BMPString ::= {0, 0, 41, 91}

-- upwardsHarpoonWithBarbRightFromBar BMPString ::= {0, 0, 41, 92}

-- downwardsHarpoonWithBarbRightFromBar BMPString ::= {0, 0, 41, 93}

-- leftwardsHarpoonWithBarbDownFromBar BMPString ::= {0, 0, 41, 94}

-- rightwardsHarpoonWithBarbDownFromBar BMPString ::= {0, 0, 41, 95}

-- upwardsHarpoonWithBarbLeftFromBar BMPString ::= {0, 0, 41, 96}

-- downwardsHarpoonWithBarbLeftFromBar BMPString ::= {0, 0, 41, 97}

-- leftwardsHarpoonWithBarbUpAboveLeftwardsHarpoonWithBarbDown BMPString ::=
--   {0, 0, 41, 98}

-- upwardsHarpoonWithBarbLeftBesideUpwardsHarpoonWithBarbRight BMPString ::=
--   {0, 0, 41, 99}

-- rightwardsHarpoonWithBarbUpAboveRightwardsHarpoonWithBarbDown BMPString ::=
--   {0, 0, 41, 100}

-- downwardsHarpoonWithBarbLeftBesideDownwardsHarpoonWithBarbRight BMPString ::=
--   {0, 0, 41, 101}

-- leftwardsHarpoonWithBarbUpAboveRightwardsHarpoonWithBarbUp BMPString ::=
--   {0, 0, 41, 102}

-- leftwardsHarpoonWithBarbDownAboveRightwardsHarpoonWithBarbDown BMPString ::=
--   {0, 0, 41, 103}

-- rightwardsHarpoonWithBarbUpAboveLeftwardsHarpoonWithBarbUp BMPString ::=
--   {0, 0, 41, 104}

-- rightwardsHarpoonWithBarbDownAboveLeftwardsHarpoonWithBarbDown BMPString ::=
--   {0, 0, 41, 105}

-- leftwardsHarpoonWithBarbUpAboveLongDash BMPString ::= {0, 0, 41, 106}

-- leftwardsHarpoonWithBarbDownBelowLongDash BMPString ::= {0, 0, 41, 107}

-- rightwardsHarpoonWithBarbUpAboveLongDash BMPString ::= {0, 0, 41, 108}

-- rightwardsHarpoonWithBarbDownBelowLongDash BMPString ::= {0, 0, 41, 109}

-- upwardsHarpoonWithBarbLeftBesideDownwardsHarpoonWithBarbRight BMPString ::=
--   {0, 0, 41, 110}

-- downwardsHarpoonWithBarbLeftBesideUpwardsHarpoonWithBarbRight BMPString ::=
--   {0, 0, 41, 111}

-- rightDoubleArrowWithRoundedHead BMPString ::= {0, 0, 41, 112}

-- equalsSignAboveRightwardsArrow BMPString ::= {0, 0, 41, 113}

-- tildeOperatorAboveRightwardsArrow BMPString ::= {0, 0, 41, 114}

-- leftwardsArrowAboveTildeOperator BMPString ::= {0, 0, 41, 115}

-- rightwardsArrowAboveTildeOperator BMPString ::= {0, 0, 41, 116}

-- rightwardsArrowAboveAlmostEqualTo BMPString ::= {0, 0, 41, 117}

-- less-thanAboveLeftwardsArrow BMPString ::= {0, 0, 41, 118}

-- leftwardsArrowThroughLess-than BMPString ::= {0, 0, 41, 119}

-- greater-thanAboveRightwardsArrow BMPString ::= {0, 0, 41, 120}

-- subsetAboveRightwardsArrow BMPString ::= {0, 0, 41, 121}

-- leftwardsArrowThroughSubset BMPString ::= {0, 0, 41, 122}

-- supersetAboveLeftwardsArrow BMPString ::= {0, 0, 41, 123}

-- leftFishTail BMPString ::= {0, 0, 41, 124}

-- rightFishTail BMPString ::= {0, 0, 41, 125}

-- upFishTail BMPString ::= {0, 0, 41, 126}

-- downFishTail BMPString ::= {0, 0, 41, 127}

-- tripleVerticalBarDelimiter BMPString ::= {0, 0, 41, 128}

-- zNotationSpot BMPString ::= {0, 0, 41, 129}

-- zNotationTypeColon BMPString ::= {0, 0, 41, 130}

-- leftWhiteCurlyBracket BMPString ::= {0, 0, 41, 131}

-- rightWhiteCurlyBracket BMPString ::= {0, 0, 41, 132}

-- leftWhiteParenthesis BMPString ::= {0, 0, 41, 133}

-- rightWhiteParenthesis BMPString ::= {0, 0, 41, 134}

-- zNotationLeftImageBracket BMPString ::= {0, 0, 41, 135}

-- zNotationRightImageBracket BMPString ::= {0, 0, 41, 136}

-- zNotationLeftBindingBracket BMPString ::= {0, 0, 41, 137}

-- zNotationRightBindingBracket BMPString ::= {0, 0, 41, 138}

-- leftSquareBracketWithUnderbar BMPString ::= {0, 0, 41, 139}

-- rightSquareBracketWithUnderbar BMPString ::= {0, 0, 41, 140}

-- leftSquareBracketWithTickInTopCorner BMPString ::= {0, 0, 41, 141}

-- rightSquareBracketWithTickInBottomCorner BMPString ::= {0, 0, 41, 142}

-- leftSquareBracketWithTickInBottomCorner BMPString ::= {0, 0, 41, 143}

-- rightSquareBracketWithTickInTopCorner BMPString ::= {0, 0, 41, 144}

-- leftAngleBracketWithDot BMPString ::= {0, 0, 41, 145}

-- rightAngleBracketWithDot BMPString ::= {0, 0, 41, 146}

-- leftArcLess-thanBracket BMPString ::= {0, 0, 41, 147}

-- rightArcGreater-thanBracket BMPString ::= {0, 0, 41, 148}

-- doubleLeftArcGreater-thanBracket BMPString ::= {0, 0, 41, 149}

-- doubleRightArcLess-thanBracket BMPString ::= {0, 0, 41, 150}

-- leftBlackTortoiseShellBracket BMPString ::= {0, 0, 41, 151}

-- rightBlackTortoiseShellBracket BMPString ::= {0, 0, 41, 152}

-- dottedFence BMPString ::= {0, 0, 41, 153}

-- verticalZigzagLine BMPString ::= {0, 0, 41, 154}

-- measuredAngleOpeningLeft BMPString ::= {0, 0, 41, 155}

-- rightAngleVariantWithSquare BMPString ::= {0, 0, 41, 156}

-- measuredRightAngleWithDot BMPString ::= {0, 0, 41, 157}

-- angleWithSInside BMPString ::= {0, 0, 41, 158}

-- acuteAngle BMPString ::= {0, 0, 41, 159}

-- sphericalAngleOpeningLeft BMPString ::= {0, 0, 41, 160}

-- sphericalAngleOpeningUp BMPString ::= {0, 0, 41, 161}

-- turnedAngle BMPString ::= {0, 0, 41, 162}

-- reversedAngle BMPString ::= {0, 0, 41, 163}

-- angleWithUnderbar BMPString ::= {0, 0, 41, 164}

-- reversedAngleWithUnderbar BMPString ::= {0, 0, 41, 165}

-- obliqueAngleOpeningUp BMPString ::= {0, 0, 41, 166}

-- obliqueAngleOpeningDown BMPString ::= {0, 0, 41, 167}

-- measuredAngleWithOpenArmEndingInArrowPointingUpAndRight BMPString ::=
--   {0, 0, 41, 168}

-- measuredAngleWithOpenArmEndingInArrowPointingUpAndLeft BMPString ::=
--   {0, 0, 41, 169}

-- measuredAngleWithOpenArmEndingInArrowPointingDownAndRight BMPString ::=
--   {0, 0, 41, 170}

-- measuredAngleWithOpenArmEndingInArrowPointingDownAndLeft BMPString ::=
--   {0, 0, 41, 171}

-- measuredAngleWithOpenArmEndingInArrowPointingRightAndUp BMPString ::=
--   {0, 0, 41, 172}

-- measuredAngleWithOpenArmEndingInArrowPointingLeftAndUp BMPString ::=
--   {0, 0, 41, 173}

-- measuredAngleWithOpenArmEndingInArrowPointingRightAndDown BMPString ::=
--   {0, 0, 41, 174}

-- measuredAngleWithOpenArmEndingInArrowPointingLeftAndDown BMPString ::=
--   {0, 0, 41, 175}

-- reversedEmptySet BMPString ::= {0, 0, 41, 176}

-- emptySetWithOverbar BMPString ::= {0, 0, 41, 177}

-- emptySetWithSmallCircleAbove BMPString ::= {0, 0, 41, 178}

-- emptySetWithRightArrowAbove BMPString ::= {0, 0, 41, 179}

-- emptySetWithLeftArrowAbove BMPString ::= {0, 0, 41, 180}

-- circleWithHorizontalBar BMPString ::= {0, 0, 41, 181}

-- circledVerticalBar BMPString ::= {0, 0, 41, 182}

-- circledParallel BMPString ::= {0, 0, 41, 183}

-- circledReverseSolidus BMPString ::= {0, 0, 41, 184}

-- circledPerpendicular BMPString ::= {0, 0, 41, 185}

-- circleDividedByHorizontalBarAndTopHalfDividedByVerticalBar BMPString ::=
--   {0, 0, 41, 186}

-- circleWithSuperimposedX BMPString ::= {0, 0, 41, 187}

-- circledAnticlockwise-rotatedDivisionSign BMPString ::= {0, 0, 41, 188}

-- upArrowThroughCircle BMPString ::= {0, 0, 41, 189}

-- circledWhiteBullet BMPString ::= {0, 0, 41, 190}

-- circledBullet BMPString ::= {0, 0, 41, 191}

-- circledLess-than BMPString ::= {0, 0, 41, 192}

-- circledGreater-than BMPString ::= {0, 0, 41, 193}

-- circleWithSmallCircleToTheRight BMPString ::= {0, 0, 41, 194}

-- circleWithTwoHorizontalStrokesToTheRight BMPString ::= {0, 0, 41, 195}

-- squaredRisingDiagonalSlash BMPString ::= {0, 0, 41, 196}

-- squaredFallingDiagonalSlash BMPString ::= {0, 0, 41, 197}

-- squaredAsterisk BMPString ::= {0, 0, 41, 198}

-- squaredSmallCircle BMPString ::= {0, 0, 41, 199}

-- squaredSquare BMPString ::= {0, 0, 41, 200}

-- twoJoinedSquares BMPString ::= {0, 0, 41, 201}

-- triangleWithDotAbove BMPString ::= {0, 0, 41, 202}

-- triangleWithUnderbar BMPString ::= {0, 0, 41, 203}

-- sInTriangle BMPString ::= {0, 0, 41, 204}

-- triangleWithSerifsAtBottom BMPString ::= {0, 0, 41, 205}

-- rightTriangleAboveLeftTriangle BMPString ::= {0, 0, 41, 206}

-- leftTriangleBesideVerticalBar BMPString ::= {0, 0, 41, 207}

-- verticalBarBesideRightTriangle BMPString ::= {0, 0, 41, 208}

-- bowtieWithLeftHalfBlack BMPString ::= {0, 0, 41, 209}

-- bowtieWithRightHalfBlack BMPString ::= {0, 0, 41, 210}

-- blackBowtie BMPString ::= {0, 0, 41, 211}

-- timesWithLeftHalfBlack BMPString ::= {0, 0, 41, 212}

-- timesWithRightHalfBlack BMPString ::= {0, 0, 41, 213}

-- whiteHourglass BMPString ::= {0, 0, 41, 214}

-- blackHourglass BMPString ::= {0, 0, 41, 215}

-- leftWigglyFence BMPString ::= {0, 0, 41, 216}

-- rightWigglyFence BMPString ::= {0, 0, 41, 217}

-- leftDoubleWigglyFence BMPString ::= {0, 0, 41, 218}

-- rightDoubleWigglyFence BMPString ::= {0, 0, 41, 219}

-- incompleteInfinity BMPString ::= {0, 0, 41, 220}

-- tieOverInfinity BMPString ::= {0, 0, 41, 221}

-- infinityNegatedWithVerticalBar BMPString ::= {0, 0, 41, 222}

-- double-endedMultimap BMPString ::= {0, 0, 41, 223}

-- squareWithContouredOutline BMPString ::= {0, 0, 41, 224}

-- increasesAs BMPString ::= {0, 0, 41, 225}

-- shuffleProduct BMPString ::= {0, 0, 41, 226}

-- equalsSignAndSlantedParallel BMPString ::= {0, 0, 41, 227}

-- equalsSignAndSlantedParallelWithTildeAbove BMPString ::= {0, 0, 41, 228}

-- identicalToAndSlantedParallel BMPString ::= {0, 0, 41, 229}

-- gleichStark BMPString ::= {0, 0, 41, 230}

-- thermodynamic BMPString ::= {0, 0, 41, 231}

-- down-pointingTriangleWithLeftHalfBlack BMPString ::= {0, 0, 41, 232}

-- down-pointingTriangleWithRightHalfBlack BMPString ::= {0, 0, 41, 233}

-- blackDiamondWithDownArrow BMPString ::= {0, 0, 41, 234}

-- blackLozenge BMPString ::= {0, 0, 41, 235}

-- whiteCircleWithDownArrow BMPString ::= {0, 0, 41, 236}

-- blackCircleWithDownArrow BMPString ::= {0, 0, 41, 237}

-- error-barredWhiteSquare BMPString ::= {0, 0, 41, 238}

-- error-barredBlackSquare BMPString ::= {0, 0, 41, 239}

-- error-barredWhiteDiamond BMPString ::= {0, 0, 41, 240}

-- error-barredBlackDiamond BMPString ::= {0, 0, 41, 241}

-- error-barredWhiteCircle BMPString ::= {0, 0, 41, 242}

-- error-barredBlackCircle BMPString ::= {0, 0, 41, 243}

-- rule-delayed BMPString ::= {0, 0, 41, 244}

-- reverseSolidusOperator BMPString ::= {0, 0, 41, 245}

-- solidusWithOverbar BMPString ::= {0, 0, 41, 246}

-- reverseSolidusWithHorizontalStroke BMPString ::= {0, 0, 41, 247}

-- bigSolidus BMPString ::= {0, 0, 41, 248}

-- bigReverseSolidus BMPString ::= {0, 0, 41, 249}

-- doublePlus BMPString ::= {0, 0, 41, 250}

-- triplePlus BMPString ::= {0, 0, 41, 251}

-- left-pointingCurvedAngleBracket BMPString ::= {0, 0, 41, 252}

-- right-pointingCurvedAngleBracket BMPString ::= {0, 0, 41, 253}

-- tiny BMPString ::= {0, 0, 41, 254}

-- miny BMPString ::= {0, 0, 41, 255}

-- n-aryCircledDotOperator BMPString ::= {0, 0, 42, 0}

-- n-aryCircledPlusOperator BMPString ::= {0, 0, 42, 1}

-- n-aryCircledTimesOperator BMPString ::= {0, 0, 42, 2}

-- n-aryUnionOperatorWithDot BMPString ::= {0, 0, 42, 3}

-- n-aryUnionOperatorWithPlus BMPString ::= {0, 0, 42, 4}

-- n-arySquareIntersectionOperator BMPString ::= {0, 0, 42, 5}

-- n-arySquareUnionOperator BMPString ::= {0, 0, 42, 6}

-- twoLogicalAndOperator BMPString ::= {0, 0, 42, 7}

-- twoLogicalOrOperator BMPString ::= {0, 0, 42, 8}

-- n-aryTimesOperator BMPString ::= {0, 0, 42, 9}

-- moduloTwoSum BMPString ::= {0, 0, 42, 10}

-- summationWithIntegral BMPString ::= {0, 0, 42, 11}

-- quadrupleIntegralOperator BMPString ::= {0, 0, 42, 12}

-- finitePartIntegral BMPString ::= {0, 0, 42, 13}

-- integralWithDoubleStroke BMPString ::= {0, 0, 42, 14}

-- integralAverageWithSlash BMPString ::= {0, 0, 42, 15}

-- circulationFunction BMPString ::= {0, 0, 42, 16}

-- anticlockwiseIntegration BMPString ::= {0, 0, 42, 17}

-- lineIntegrationWithRectangularPathAroundPole BMPString ::= {0, 0, 42, 18}

-- lineIntegrationWithSemicircularPathAroundPole BMPString ::= {0, 0, 42, 19}

-- lineIntegrationNotIncludingThePole BMPString ::= {0, 0, 42, 20}

-- integralAroundAPointOperator BMPString ::= {0, 0, 42, 21}

-- quaternionIntegralOperator BMPString ::= {0, 0, 42, 22}

-- integralWithLeftwardsArrowWithHook BMPString ::= {0, 0, 42, 23}

-- integralWithTimesSign BMPString ::= {0, 0, 42, 24}

-- integralWithIntersection BMPString ::= {0, 0, 42, 25}

-- integralWithUnion BMPString ::= {0, 0, 42, 26}

-- integralWithOverbar BMPString ::= {0, 0, 42, 27}

-- integralWithUnderbar BMPString ::= {0, 0, 42, 28}

-- join BMPString ::= {0, 0, 42, 29}

-- largeLeftTriangleOperator BMPString ::= {0, 0, 42, 30}

-- zNotationSchemaComposition BMPString ::= {0, 0, 42, 31}

-- zNotationSchemaPiping BMPString ::= {0, 0, 42, 32}

-- zNotationSchemaProjection BMPString ::= {0, 0, 42, 33}

-- plusSignWithSmallCircleAbove BMPString ::= {0, 0, 42, 34}

-- plusSignWithCircumflexAccentAbove BMPString ::= {0, 0, 42, 35}

-- plusSignWithTildeAbove BMPString ::= {0, 0, 42, 36}

-- plusSignWithDotBelow BMPString ::= {0, 0, 42, 37}

-- plusSignWithTildeBelow BMPString ::= {0, 0, 42, 38}

-- plusSignWithSubscriptTwo BMPString ::= {0, 0, 42, 39}

-- plusSignWithBlackTriangle BMPString ::= {0, 0, 42, 40}

-- minusSignWithCommaAbove BMPString ::= {0, 0, 42, 41}

-- minusSignWithDotBelow BMPString ::= {0, 0, 42, 42}

-- minusSignWithFallingDots BMPString ::= {0, 0, 42, 43}

-- minusSignWithRisingDots BMPString ::= {0, 0, 42, 44}

-- plusSignInLeftHalfCircle BMPString ::= {0, 0, 42, 45}

-- plusSignInRightHalfCircle BMPString ::= {0, 0, 42, 46}

-- vectorOrCrossProduct BMPString ::= {0, 0, 42, 47}

-- multiplicationSignWithDotAbove BMPString ::= {0, 0, 42, 48}

-- multiplicationSignWithUnderbar BMPString ::= {0, 0, 42, 49}

-- semidirectProductWithBottomClosed BMPString ::= {0, 0, 42, 50}

-- smashProduct BMPString ::= {0, 0, 42, 51}

-- multiplicationSignInLeftHalfCircle BMPString ::= {0, 0, 42, 52}

-- multiplicationSignInRightHalfCircle BMPString ::= {0, 0, 42, 53}

-- circledMultiplicationSignWithCircumflexAccent BMPString ::= {0, 0, 42, 54}

-- multiplicationSignInDoubleCircle BMPString ::= {0, 0, 42, 55}

-- circledDivisionSign BMPString ::= {0, 0, 42, 56}

-- plusSignInTriangle BMPString ::= {0, 0, 42, 57}

-- minusSignInTriangle BMPString ::= {0, 0, 42, 58}

-- multiplicationSignInTriangle BMPString ::= {0, 0, 42, 59}

-- interiorProduct BMPString ::= {0, 0, 42, 60}

-- righthandInteriorProduct BMPString ::= {0, 0, 42, 61}

-- zNotationRelationalComposition BMPString ::= {0, 0, 42, 62}

-- amalgamationOrCoproduct BMPString ::= {0, 0, 42, 63}

-- intersectionWithDot BMPString ::= {0, 0, 42, 64}

-- unionWithMinusSign BMPString ::= {0, 0, 42, 65}

-- unionWithOverbar BMPString ::= {0, 0, 42, 66}

-- intersectionWithOverbar BMPString ::= {0, 0, 42, 67}

-- intersectionWithLogicalAnd BMPString ::= {0, 0, 42, 68}

-- unionWithLogicalOr BMPString ::= {0, 0, 42, 69}

-- unionAboveIntersection BMPString ::= {0, 0, 42, 70}

-- intersectionAboveUnion BMPString ::= {0, 0, 42, 71}

-- unionAboveBarAboveIntersection BMPString ::= {0, 0, 42, 72}

-- intersectionAboveBarAboveUnion BMPString ::= {0, 0, 42, 73}

-- unionBesideAndJoinedWithUnion BMPString ::= {0, 0, 42, 74}

-- intersectionBesideAndJoinedWithIntersection BMPString ::= {0, 0, 42, 75}

-- closedUnionWithSerifs BMPString ::= {0, 0, 42, 76}

-- closedIntersectionWithSerifs BMPString ::= {0, 0, 42, 77}

-- doubleSquareIntersection BMPString ::= {0, 0, 42, 78}

-- doubleSquareUnion BMPString ::= {0, 0, 42, 79}

-- closedUnionWithSerifsAndSmashProduct BMPString ::= {0, 0, 42, 80}

-- logicalAndWithDotAbove BMPString ::= {0, 0, 42, 81}

-- logicalOrWithDotAbove BMPString ::= {0, 0, 42, 82}

-- doubleLogicalAnd BMPString ::= {0, 0, 42, 83}

-- doubleLogicalOr BMPString ::= {0, 0, 42, 84}

-- twoIntersectingLogicalAnd BMPString ::= {0, 0, 42, 85}

-- twoIntersectingLogicalOr BMPString ::= {0, 0, 42, 86}

-- slopingLargeOr BMPString ::= {0, 0, 42, 87}

-- slopingLargeAnd BMPString ::= {0, 0, 42, 88}

-- logicalOrOverlappingLogicalAnd BMPString ::= {0, 0, 42, 89}

-- logicalAndWithMiddleStem BMPString ::= {0, 0, 42, 90}

-- logicalOrWithMiddleStem BMPString ::= {0, 0, 42, 91}

-- logicalAndWithHorizontalDash BMPString ::= {0, 0, 42, 92}

-- logicalOrWithHorizontalDash BMPString ::= {0, 0, 42, 93}

-- logicalAndWithDoubleOverbar BMPString ::= {0, 0, 42, 94}

-- logicalAndWithUnderbar BMPString ::= {0, 0, 42, 95}

-- logicalAndWithDoubleUnderbar BMPString ::= {0, 0, 42, 96}

-- smallVeeWithUnderbar BMPString ::= {0, 0, 42, 97}

-- logicalOrWithDoubleOverbar BMPString ::= {0, 0, 42, 98}

-- logicalOrWithDoubleUnderbar BMPString ::= {0, 0, 42, 99}

-- zNotationDomainAntirestriction BMPString ::= {0, 0, 42, 100}

-- zNotationRangeAntirestriction BMPString ::= {0, 0, 42, 101}

-- equalsSignWithDotBelow BMPString ::= {0, 0, 42, 102}

-- identicalWithDotAbove BMPString ::= {0, 0, 42, 103}

-- tripleHorizontalBarWithDoubleVerticalStroke BMPString ::= {0, 0, 42, 104}

-- tripleHorizontalBarWithTripleVerticalStroke BMPString ::= {0, 0, 42, 105}

-- tildeOperatorWithDotAbove BMPString ::= {0, 0, 42, 106}

-- tildeOperatorWithRisingDots BMPString ::= {0, 0, 42, 107}

-- similarMinusSimilar BMPString ::= {0, 0, 42, 108}

-- congruentWithDotAbove BMPString ::= {0, 0, 42, 109}

-- equalsWithAsterisk BMPString ::= {0, 0, 42, 110}

-- almostEqualToWithCircumflexAccent BMPString ::= {0, 0, 42, 111}

-- approximatelyEqualOrEqualTo BMPString ::= {0, 0, 42, 112}

-- equalsSignAbovePlusSign BMPString ::= {0, 0, 42, 113}

-- plusSignAboveEqualsSign BMPString ::= {0, 0, 42, 114}

-- equalsSignAboveTildeOperator BMPString ::= {0, 0, 42, 115}

-- doubleColonEqual BMPString ::= {0, 0, 42, 116}

-- twoConsecutiveEqualsSigns BMPString ::= {0, 0, 42, 117}

-- threeConsecutiveEqualsSigns BMPString ::= {0, 0, 42, 118}

-- equalsSignWithTwoDotsAboveAndTwoDotsBelow BMPString ::= {0, 0, 42, 119}

-- equivalentWithFourDotsAbove BMPString ::= {0, 0, 42, 120}

-- less-thanWithCircleInside BMPString ::= {0, 0, 42, 121}

-- greater-thanWithCircleInside BMPString ::= {0, 0, 42, 122}

-- less-thanWithQuestionMarkAbove BMPString ::= {0, 0, 42, 123}

-- greater-thanWithQuestionMarkAbove BMPString ::= {0, 0, 42, 124}

-- less-thanOrSlantedEqualTo BMPString ::= {0, 0, 42, 125}

-- greater-thanOrSlantedEqualTo BMPString ::= {0, 0, 42, 126}

-- less-thanOrSlantedEqualToWithDotInside BMPString ::= {0, 0, 42, 127}

-- greater-thanOrSlantedEqualToWithDotInside BMPString ::= {0, 0, 42, 128}

-- less-thanOrSlantedEqualToWithDotAbove BMPString ::= {0, 0, 42, 129}

-- greater-thanOrSlantedEqualToWithDotAbove BMPString ::= {0, 0, 42, 130}

-- less-thanOrSlantedEqualToWithDotAboveRight BMPString ::= {0, 0, 42, 131}

-- greater-thanOrSlantedEqualToWithDotAboveLeft BMPString ::= {0, 0, 42, 132}

-- less-thanOrApproximate BMPString ::= {0, 0, 42, 133}

-- greater-thanOrApproximate BMPString ::= {0, 0, 42, 134}

-- less-thanAndSingle-lineNotEqualTo BMPString ::= {0, 0, 42, 135}

-- greater-thanAndSingle-lineNotEqualTo BMPString ::= {0, 0, 42, 136}

-- less-thanAndNotApproximate BMPString ::= {0, 0, 42, 137}

-- greater-thanAndNotApproximate BMPString ::= {0, 0, 42, 138}

-- less-thanAboveDouble-lineEqualAboveGreater-than BMPString ::= {0, 0, 42, 139}

-- greater-thanAboveDouble-lineEqualAboveLess-than BMPString ::= {0, 0, 42, 140}

-- less-thanAboveSimilarOrEqual BMPString ::= {0, 0, 42, 141}

-- greater-thanAboveSimilarOrEqual BMPString ::= {0, 0, 42, 142}

-- less-thanAboveSimilarAboveGreater-than BMPString ::= {0, 0, 42, 143}

-- greater-thanAboveSimilarAboveLess-than BMPString ::= {0, 0, 42, 144}

-- less-thanAboveGreater-thanAboveDouble-lineEqual BMPString ::= {0, 0, 42, 145}

-- greater-thanAboveLess-thanAboveDouble-lineEqual BMPString ::= {0, 0, 42, 146}

-- less-thanAboveSlantedEqualAboveGreater-thanAboveSlantedEqual BMPString ::=
--   {0, 0, 42, 147}

-- greater-thanAboveSlantedEqualAboveLess-thanAboveSlantedEqual BMPString ::=
--   {0, 0, 42, 148}

-- slantedEqualToOrLess-than BMPString ::= {0, 0, 42, 149}

-- slantedEqualToOrGreater-than BMPString ::= {0, 0, 42, 150}

-- slantedEqualToOrLess-thanWithDotInside BMPString ::= {0, 0, 42, 151}

-- slantedEqualToOrGreater-thanWithDotInside BMPString ::= {0, 0, 42, 152}

-- double-lineEqualToOrLess-than BMPString ::= {0, 0, 42, 153}

-- double-lineEqualToOrGreater-than BMPString ::= {0, 0, 42, 154}

-- double-lineSlantedEqualToOrLess-than BMPString ::= {0, 0, 42, 155}

-- double-lineSlantedEqualToOrGreater-than BMPString ::= {0, 0, 42, 156}

-- similarOrLess-than BMPString ::= {0, 0, 42, 157}

-- similarOrGreater-than BMPString ::= {0, 0, 42, 158}

-- similarAboveLess-thanAboveEqualsSign BMPString ::= {0, 0, 42, 159}

-- similarAboveGreater-thanAboveEqualsSign BMPString ::= {0, 0, 42, 160}

-- doubleNestedLess-than BMPString ::= {0, 0, 42, 161}

-- doubleNestedGreater-than BMPString ::= {0, 0, 42, 162}

-- doubleNestedLess-thanWithUnderbar BMPString ::= {0, 0, 42, 163}

-- greater-thanOverlappingLess-than BMPString ::= {0, 0, 42, 164}

-- greater-thanBesideLess-than BMPString ::= {0, 0, 42, 165}

-- less-thanClosedByCurve BMPString ::= {0, 0, 42, 166}

-- greater-thanClosedByCurve BMPString ::= {0, 0, 42, 167}

-- less-thanClosedByCurveAboveSlantedEqual BMPString ::= {0, 0, 42, 168}

-- greater-thanClosedByCurveAboveSlantedEqual BMPString ::= {0, 0, 42, 169}

-- smallerThan BMPString ::= {0, 0, 42, 170}

-- largerThan BMPString ::= {0, 0, 42, 171}

-- smallerThanOrEqualTo BMPString ::= {0, 0, 42, 172}

-- largerThanOrEqualTo BMPString ::= {0, 0, 42, 173}

-- equalsSignWithBumpyAbove BMPString ::= {0, 0, 42, 174}

-- precedesAboveSingle-lineEqualsSign BMPString ::= {0, 0, 42, 175}

-- succeedsAboveSingle-lineEqualsSign BMPString ::= {0, 0, 42, 176}

-- precedesAboveSingle-lineNotEqualTo BMPString ::= {0, 0, 42, 177}

-- succeedsAboveSingle-lineNotEqualTo BMPString ::= {0, 0, 42, 178}

-- precedesAboveEqualsSign BMPString ::= {0, 0, 42, 179}

-- succeedsAboveEqualsSign BMPString ::= {0, 0, 42, 180}

-- precedesAboveNotEqualTo BMPString ::= {0, 0, 42, 181}

-- succeedsAboveNotEqualTo BMPString ::= {0, 0, 42, 182}

-- precedesAboveAlmostEqualTo BMPString ::= {0, 0, 42, 183}

-- succeedsAboveAlmostEqualTo BMPString ::= {0, 0, 42, 184}

-- precedesAboveNotAlmostEqualTo BMPString ::= {0, 0, 42, 185}

-- succeedsAboveNotAlmostEqualTo BMPString ::= {0, 0, 42, 186}

-- doublePrecedes BMPString ::= {0, 0, 42, 187}

-- doubleSucceeds BMPString ::= {0, 0, 42, 188}

-- subsetWithDot BMPString ::= {0, 0, 42, 189}

-- supersetWithDot BMPString ::= {0, 0, 42, 190}

-- subsetWithPlusSignBelow BMPString ::= {0, 0, 42, 191}

-- supersetWithPlusSignBelow BMPString ::= {0, 0, 42, 192}

-- subsetWithMultiplicationSignBelow BMPString ::= {0, 0, 42, 193}

-- supersetWithMultiplicationSignBelow BMPString ::= {0, 0, 42, 194}

-- subsetOfOrEqualToWithDotAbove BMPString ::= {0, 0, 42, 195}

-- supersetOfOrEqualToWithDotAbove BMPString ::= {0, 0, 42, 196}

-- subsetOfAboveEqualsSign BMPString ::= {0, 0, 42, 197}

-- supersetOfAboveEqualsSign BMPString ::= {0, 0, 42, 198}

-- subsetOfAboveTildeOperator BMPString ::= {0, 0, 42, 199}

-- supersetOfAboveTildeOperator BMPString ::= {0, 0, 42, 200}

-- subsetOfAboveAlmostEqualTo BMPString ::= {0, 0, 42, 201}

-- supersetOfAboveAlmostEqualTo BMPString ::= {0, 0, 42, 202}

-- subsetOfAboveNotEqualTo BMPString ::= {0, 0, 42, 203}

-- supersetOfAboveNotEqualTo BMPString ::= {0, 0, 42, 204}

-- squareLeftOpenBoxOperator BMPString ::= {0, 0, 42, 205}

-- squareRightOpenBoxOperator BMPString ::= {0, 0, 42, 206}

-- closedSubset BMPString ::= {0, 0, 42, 207}

-- closedSuperset BMPString ::= {0, 0, 42, 208}

-- closedSubsetOrEqualTo BMPString ::= {0, 0, 42, 209}

-- closedSupersetOrEqualTo BMPString ::= {0, 0, 42, 210}

-- subsetAboveSuperset BMPString ::= {0, 0, 42, 211}

-- supersetAboveSubset BMPString ::= {0, 0, 42, 212}

-- subsetAboveSubset BMPString ::= {0, 0, 42, 213}

-- supersetAboveSuperset BMPString ::= {0, 0, 42, 214}

-- supersetBesideSubset BMPString ::= {0, 0, 42, 215}

-- supersetBesideAndJoinedByDashWithSubset BMPString ::= {0, 0, 42, 216}

-- elementOfOpeningDownwards BMPString ::= {0, 0, 42, 217}

-- pitchforkWithTeeTop BMPString ::= {0, 0, 42, 218}

-- transversalIntersection BMPString ::= {0, 0, 42, 219}

-- forking BMPString ::= {0, 0, 42, 220}

-- nonforking BMPString ::= {0, 0, 42, 221}

-- shortLeftTack BMPString ::= {0, 0, 42, 222}

-- shortDownTack BMPString ::= {0, 0, 42, 223}

-- shortUpTack BMPString ::= {0, 0, 42, 224}

-- perpendicularWithS BMPString ::= {0, 0, 42, 225}

-- verticalBarTripleRightTurnstile BMPString ::= {0, 0, 42, 226}

-- doubleVerticalBarLeftTurnstile BMPString ::= {0, 0, 42, 227}

-- verticalBarDoubleLeftTurnstile BMPString ::= {0, 0, 42, 228}

-- doubleVerticalBarDoubleLeftTurnstile BMPString ::= {0, 0, 42, 229}

-- longDashFromLeftMemberOfDoubleVertical BMPString ::= {0, 0, 42, 230}

-- shortDownTackWithOverbar BMPString ::= {0, 0, 42, 231}

-- shortUpTackWithUnderbar BMPString ::= {0, 0, 42, 232}

-- shortUpTackAboveShortDownTack BMPString ::= {0, 0, 42, 233}

-- doubleDownTack BMPString ::= {0, 0, 42, 234}

-- doubleUpTack BMPString ::= {0, 0, 42, 235}

-- doubleStrokeNotSign BMPString ::= {0, 0, 42, 236}

-- reversedDoubleStrokeNotSign BMPString ::= {0, 0, 42, 237}

-- doesNotDivideWithReversedNegationSlash BMPString ::= {0, 0, 42, 238}

-- verticalLineWithCircleAbove BMPString ::= {0, 0, 42, 239}

-- verticalLineWithCircleBelow BMPString ::= {0, 0, 42, 240}

-- downTackWithCircleBelow BMPString ::= {0, 0, 42, 241}

-- parallelWithHorizontalStroke BMPString ::= {0, 0, 42, 242}

-- parallelWithTildeOperator BMPString ::= {0, 0, 42, 243}

-- tripleVerticalBarBinaryRelation BMPString ::= {0, 0, 42, 244}

-- tripleVerticalBarWithHorizontalStroke BMPString ::= {0, 0, 42, 245}

-- tripleColonOperator BMPString ::= {0, 0, 42, 246}

-- tripleNestedLess-than BMPString ::= {0, 0, 42, 247}

-- tripleNestedGreater-than BMPString ::= {0, 0, 42, 248}

-- double-lineSlantedLess-thanOrEqualTo BMPString ::= {0, 0, 42, 249}

-- double-lineSlantedGreater-thanOrEqualTo BMPString ::= {0, 0, 42, 250}

-- tripleSolidusBinaryRelation BMPString ::= {0, 0, 42, 251}

-- largeTripleVerticalBarOperator BMPString ::= {0, 0, 42, 252}

-- doubleSolidusOperator BMPString ::= {0, 0, 42, 253}

-- whiteVerticalBar BMPString ::= {0, 0, 42, 254}

-- n-aryWhiteVerticalBar BMPString ::= {0, 0, 42, 255}

-- cjkRadicalRepeat BMPString ::= {0, 0, 46, 128}

-- cjkRadicalCliff BMPString ::= {0, 0, 46, 129}

-- cjkRadicalSecondOne BMPString ::= {0, 0, 46, 130}

-- cjkRadicalSecondTwo BMPString ::= {0, 0, 46, 131}

-- cjkRadicalSecondThree BMPString ::= {0, 0, 46, 132}

-- cjkRadicalPerson BMPString ::= {0, 0, 46, 133}

-- cjkRadicalBox BMPString ::= {0, 0, 46, 134}

-- cjkRadicalTable BMPString ::= {0, 0, 46, 135}

-- cjkRadicalKnifeOne BMPString ::= {0, 0, 46, 136}

-- cjkRadicalKnifeTwo BMPString ::= {0, 0, 46, 137}

-- cjkRadicalDivination BMPString ::= {0, 0, 46, 138}

-- cjkRadicalSeal BMPString ::= {0, 0, 46, 139}

-- cjkRadicalSmallOne BMPString ::= {0, 0, 46, 140}

-- cjkRadicalSmallTwo BMPString ::= {0, 0, 46, 141}

-- cjkRadicalLameOne BMPString ::= {0, 0, 46, 142}

-- cjkRadicalLameTwo BMPString ::= {0, 0, 46, 143}

-- cjkRadicalLameThree BMPString ::= {0, 0, 46, 144}

-- cjkRadicalLameFour BMPString ::= {0, 0, 46, 145}

-- cjkRadicalSnake BMPString ::= {0, 0, 46, 146}

-- cjkRadicalThread BMPString ::= {0, 0, 46, 147}

-- cjkRadicalSnoutOne BMPString ::= {0, 0, 46, 148}

-- cjkRadicalSnoutTwo BMPString ::= {0, 0, 46, 149}

-- cjkRadicalHeartOne BMPString ::= {0, 0, 46, 150}

-- cjkRadicalHeartTwo BMPString ::= {0, 0, 46, 151}

-- cjkRadicalHand BMPString ::= {0, 0, 46, 152}

-- cjkRadicalRap BMPString ::= {0, 0, 46, 153}

-- cjkRadicalChoke BMPString ::= {0, 0, 46, 155}

-- cjkRadicalSun BMPString ::= {0, 0, 46, 156}

-- cjkRadicalMoon BMPString ::= {0, 0, 46, 157}

-- cjkRadicalDeath BMPString ::= {0, 0, 46, 158}

-- cjkRadicalMother BMPString ::= {0, 0, 46, 159}

-- cjkRadicalCivilian BMPString ::= {0, 0, 46, 160}

-- cjkRadicalWaterOne BMPString ::= {0, 0, 46, 161}

-- cjkRadicalWaterTwo BMPString ::= {0, 0, 46, 162}

-- cjkRadicalFire BMPString ::= {0, 0, 46, 163}

-- cjkRadicalPawOne BMPString ::= {0, 0, 46, 164}

-- cjkRadicalPawTwo BMPString ::= {0, 0, 46, 165}

-- cjkRadicalSimplifiedHalfTreeTrunk BMPString ::= {0, 0, 46, 166}

-- cjkRadicalCow BMPString ::= {0, 0, 46, 167}

-- cjkRadicalDog BMPString ::= {0, 0, 46, 168}

-- cjkRadicalJade BMPString ::= {0, 0, 46, 169}

-- cjkRadicalBoltOfCloth BMPString ::= {0, 0, 46, 170}

-- cjkRadicalEye BMPString ::= {0, 0, 46, 171}

-- cjkRadicalSpiritOne BMPString ::= {0, 0, 46, 172}

-- cjkRadicalSpiritTwo BMPString ::= {0, 0, 46, 173}

-- cjkRadicalBamboo BMPString ::= {0, 0, 46, 174}

-- cjkRadicalSilk BMPString ::= {0, 0, 46, 175}

-- cjkRadicalC-simplifiedSilk BMPString ::= {0, 0, 46, 176}

-- cjkRadicalNetOne BMPString ::= {0, 0, 46, 177}

-- cjkRadicalNetTwo BMPString ::= {0, 0, 46, 178}

-- cjkRadicalNetThree BMPString ::= {0, 0, 46, 179}

-- cjkRadicalNetFour BMPString ::= {0, 0, 46, 180}

-- cjkRadicalMesh BMPString ::= {0, 0, 46, 181}

-- cjkRadicalSheep BMPString ::= {0, 0, 46, 182}

-- cjkRadicalRam BMPString ::= {0, 0, 46, 183}

-- cjkRadicalEwe BMPString ::= {0, 0, 46, 184}

-- cjkRadicalOld BMPString ::= {0, 0, 46, 185}

-- cjkRadicalBrushOne BMPString ::= {0, 0, 46, 186}

-- cjkRadicalBrushTwo BMPString ::= {0, 0, 46, 187}

-- cjkRadicalMeat BMPString ::= {0, 0, 46, 188}

-- cjkRadicalMortar BMPString ::= {0, 0, 46, 189}

-- cjkRadicalGrassOne BMPString ::= {0, 0, 46, 190}

-- cjkRadicalGrassTwo BMPString ::= {0, 0, 46, 191}

-- cjkRadicalGrassThree BMPString ::= {0, 0, 46, 192}

-- cjkRadicalTiger BMPString ::= {0, 0, 46, 193}

-- cjkRadicalClothes BMPString ::= {0, 0, 46, 194}

-- cjkRadicalWestOne BMPString ::= {0, 0, 46, 195}

-- cjkRadicalWestTwo BMPString ::= {0, 0, 46, 196}

-- cjkRadicalC-simplifiedSee BMPString ::= {0, 0, 46, 197}

-- cjkRadicalSimplifiedHorn BMPString ::= {0, 0, 46, 198}

-- cjkRadicalHorn BMPString ::= {0, 0, 46, 199}

-- cjkRadicalC-simplifiedSpeech BMPString ::= {0, 0, 46, 200}

-- cjkRadicalC-simplifiedShell BMPString ::= {0, 0, 46, 201}

-- cjkRadicalFoot BMPString ::= {0, 0, 46, 202}

-- cjkRadicalC-simplifiedCart BMPString ::= {0, 0, 46, 203}

-- cjkRadicalSimplifiedWalk BMPString ::= {0, 0, 46, 204}

-- cjkRadicalWalkOne BMPString ::= {0, 0, 46, 205}

-- cjkRadicalWalkTwo BMPString ::= {0, 0, 46, 206}

-- cjkRadicalCity BMPString ::= {0, 0, 46, 207}

-- cjkRadicalC-simplifiedGold BMPString ::= {0, 0, 46, 208}

-- cjkRadicalLongOne BMPString ::= {0, 0, 46, 209}

-- cjkRadicalLongTwo BMPString ::= {0, 0, 46, 210}

-- cjkRadicalC-simplifiedLong BMPString ::= {0, 0, 46, 211}

-- cjkRadicalC-simplifiedGate BMPString ::= {0, 0, 46, 212}

-- cjkRadicalMoundOne BMPString ::= {0, 0, 46, 213}

-- cjkRadicalMoundTwo BMPString ::= {0, 0, 46, 214}

-- cjkRadicalRain BMPString ::= {0, 0, 46, 215}

-- cjkRadicalBlue BMPString ::= {0, 0, 46, 216}

-- cjkRadicalC-simplifiedTannedLeather BMPString ::= {0, 0, 46, 217}

-- cjkRadicalC-simplifiedLeaf BMPString ::= {0, 0, 46, 218}

-- cjkRadicalC-simplifiedWind BMPString ::= {0, 0, 46, 219}

-- cjkRadicalC-simplifiedFly BMPString ::= {0, 0, 46, 220}

-- cjkRadicalEatOne BMPString ::= {0, 0, 46, 221}

-- cjkRadicalEatTwo BMPString ::= {0, 0, 46, 222}

-- cjkRadicalEatThree BMPString ::= {0, 0, 46, 223}

-- cjkRadicalC-simplifiedEat BMPString ::= {0, 0, 46, 224}

-- cjkRadicalHead BMPString ::= {0, 0, 46, 225}

-- cjkRadicalC-simplifiedHorse BMPString ::= {0, 0, 46, 226}

-- cjkRadicalBone BMPString ::= {0, 0, 46, 227}

-- cjkRadicalGhost BMPString ::= {0, 0, 46, 228}

-- cjkRadicalC-simplifiedFish BMPString ::= {0, 0, 46, 229}

-- cjkRadicalC-simplifiedBird BMPString ::= {0, 0, 46, 230}

-- cjkRadicalC-simplifiedSalt BMPString ::= {0, 0, 46, 231}

-- cjkRadicalSimplifiedWheat BMPString ::= {0, 0, 46, 232}

-- cjkRadicalSimplifiedYellow BMPString ::= {0, 0, 46, 233}

-- cjkRadicalC-simplifiedFrog BMPString ::= {0, 0, 46, 234}

-- cjkRadicalJ-simplifiedEven BMPString ::= {0, 0, 46, 235}

-- cjkRadicalC-simplifiedEven BMPString ::= {0, 0, 46, 236}

-- cjkRadicalJ-simplifiedTooth BMPString ::= {0, 0, 46, 237}

-- cjkRadicalC-simplifiedTooth BMPString ::= {0, 0, 46, 238}

-- cjkRadicalJ-simplifiedDragon BMPString ::= {0, 0, 46, 239}

-- cjkRadicalC-simplifiedDragon BMPString ::= {0, 0, 46, 240}

-- cjkRadicalTurtle BMPString ::= {0, 0, 46, 241}

-- cjkRadicalJ-simplifiedTurtle BMPString ::= {0, 0, 46, 242}

-- cjkRadicalC-simplifiedTurtle BMPString ::= {0, 0, 46, 243}

-- kangxiRadicalOne BMPString ::= {0, 0, 47, 0}

-- kangxiRadicalLine BMPString ::= {0, 0, 47, 1}

-- kangxiRadicalDot BMPString ::= {0, 0, 47, 2}

-- kangxiRadicalSlash BMPString ::= {0, 0, 47, 3}

-- kangxiRadicalSecond BMPString ::= {0, 0, 47, 4}

-- kangxiRadicalHook BMPString ::= {0, 0, 47, 5}

-- kangxiRadicalTwo BMPString ::= {0, 0, 47, 6}

-- kangxiRadicalLid BMPString ::= {0, 0, 47, 7}

-- kangxiRadicalMan BMPString ::= {0, 0, 47, 8}

-- kangxiRadicalLegs BMPString ::= {0, 0, 47, 9}

-- kangxiRadicalEnter BMPString ::= {0, 0, 47, 10}

-- kangxiRadicalEight BMPString ::= {0, 0, 47, 11}

-- kangxiRadicalDownBox BMPString ::= {0, 0, 47, 12}

-- kangxiRadicalCover BMPString ::= {0, 0, 47, 13}

-- kangxiRadicalIce BMPString ::= {0, 0, 47, 14}

-- kangxiRadicalTable BMPString ::= {0, 0, 47, 15}

-- kangxiRadicalOpenBox BMPString ::= {0, 0, 47, 16}

-- kangxiRadicalKnife BMPString ::= {0, 0, 47, 17}

-- kangxiRadicalPower BMPString ::= {0, 0, 47, 18}

-- kangxiRadicalWrap BMPString ::= {0, 0, 47, 19}

-- kangxiRadicalSpoon BMPString ::= {0, 0, 47, 20}

-- kangxiRadicalRightOpenBox BMPString ::= {0, 0, 47, 21}

-- kangxiRadicalHidingEnclosure BMPString ::= {0, 0, 47, 22}

-- kangxiRadicalTen BMPString ::= {0, 0, 47, 23}

-- kangxiRadicalDivination BMPString ::= {0, 0, 47, 24}

-- kangxiRadicalSeal BMPString ::= {0, 0, 47, 25}

-- kangxiRadicalCliff BMPString ::= {0, 0, 47, 26}

-- kangxiRadicalPrivate BMPString ::= {0, 0, 47, 27}

-- kangxiRadicalAgain BMPString ::= {0, 0, 47, 28}

-- kangxiRadicalMouth BMPString ::= {0, 0, 47, 29}

-- kangxiRadicalEnclosure BMPString ::= {0, 0, 47, 30}

-- kangxiRadicalEarth BMPString ::= {0, 0, 47, 31}

-- kangxiRadicalScholar BMPString ::= {0, 0, 47, 32}

-- kangxiRadicalGo BMPString ::= {0, 0, 47, 33}

-- kangxiRadicalGoSlowly BMPString ::= {0, 0, 47, 34}

-- kangxiRadicalEvening BMPString ::= {0, 0, 47, 35}

-- kangxiRadicalBig BMPString ::= {0, 0, 47, 36}

-- kangxiRadicalWoman BMPString ::= {0, 0, 47, 37}

-- kangxiRadicalChild BMPString ::= {0, 0, 47, 38}

-- kangxiRadicalRoof BMPString ::= {0, 0, 47, 39}

-- kangxiRadicalInch BMPString ::= {0, 0, 47, 40}

-- kangxiRadicalSmall BMPString ::= {0, 0, 47, 41}

-- kangxiRadicalLame BMPString ::= {0, 0, 47, 42}

-- kangxiRadicalCorpse BMPString ::= {0, 0, 47, 43}

-- kangxiRadicalSprout BMPString ::= {0, 0, 47, 44}

-- kangxiRadicalMountain BMPString ::= {0, 0, 47, 45}

-- kangxiRadicalRiver BMPString ::= {0, 0, 47, 46}

-- kangxiRadicalWork BMPString ::= {0, 0, 47, 47}

-- kangxiRadicalOneself BMPString ::= {0, 0, 47, 48}

-- kangxiRadicalTurban BMPString ::= {0, 0, 47, 49}

-- kangxiRadicalDry BMPString ::= {0, 0, 47, 50}

-- kangxiRadicalShortThread BMPString ::= {0, 0, 47, 51}

-- kangxiRadicalDottedCliff BMPString ::= {0, 0, 47, 52}

-- kangxiRadicalLongStride BMPString ::= {0, 0, 47, 53}

-- kangxiRadicalTwoHands BMPString ::= {0, 0, 47, 54}

-- kangxiRadicalShoot BMPString ::= {0, 0, 47, 55}

-- kangxiRadicalBow BMPString ::= {0, 0, 47, 56}

-- kangxiRadicalSnout BMPString ::= {0, 0, 47, 57}

-- kangxiRadicalBristle BMPString ::= {0, 0, 47, 58}

-- kangxiRadicalStep BMPString ::= {0, 0, 47, 59}

-- kangxiRadicalHeart BMPString ::= {0, 0, 47, 60}

-- kangxiRadicalHalberd BMPString ::= {0, 0, 47, 61}

-- kangxiRadicalDoor BMPString ::= {0, 0, 47, 62}

-- kangxiRadicalHand BMPString ::= {0, 0, 47, 63}

-- kangxiRadicalBranch BMPString ::= {0, 0, 47, 64}

-- kangxiRadicalRap BMPString ::= {0, 0, 47, 65}

-- kangxiRadicalScript BMPString ::= {0, 0, 47, 66}

-- kangxiRadicalDipper BMPString ::= {0, 0, 47, 67}

-- kangxiRadicalAxe BMPString ::= {0, 0, 47, 68}

-- kangxiRadicalSquare BMPString ::= {0, 0, 47, 69}

-- kangxiRadicalNot BMPString ::= {0, 0, 47, 70}

-- kangxiRadicalSun BMPString ::= {0, 0, 47, 71}

-- kangxiRadicalSay BMPString ::= {0, 0, 47, 72}

-- kangxiRadicalMoon BMPString ::= {0, 0, 47, 73}

-- kangxiRadicalTree BMPString ::= {0, 0, 47, 74}

-- kangxiRadicalLack BMPString ::= {0, 0, 47, 75}

-- kangxiRadicalStop BMPString ::= {0, 0, 47, 76}

-- kangxiRadicalDeath BMPString ::= {0, 0, 47, 77}

-- kangxiRadicalWeapon BMPString ::= {0, 0, 47, 78}

-- kangxiRadicalDoNot BMPString ::= {0, 0, 47, 79}

-- kangxiRadicalCompare BMPString ::= {0, 0, 47, 80}

-- kangxiRadicalFur BMPString ::= {0, 0, 47, 81}

-- kangxiRadicalClan BMPString ::= {0, 0, 47, 82}

-- kangxiRadicalSteam BMPString ::= {0, 0, 47, 83}

-- kangxiRadicalWater BMPString ::= {0, 0, 47, 84}

-- kangxiRadicalFire BMPString ::= {0, 0, 47, 85}

-- kangxiRadicalClaw BMPString ::= {0, 0, 47, 86}

-- kangxiRadicalFather BMPString ::= {0, 0, 47, 87}

-- kangxiRadicalDoubleX BMPString ::= {0, 0, 47, 88}

-- kangxiRadicalHalfTreeTrunk BMPString ::= {0, 0, 47, 89}

-- kangxiRadicalSlice BMPString ::= {0, 0, 47, 90}

-- kangxiRadicalFang BMPString ::= {0, 0, 47, 91}

-- kangxiRadicalCow BMPString ::= {0, 0, 47, 92}

-- kangxiRadicalDog BMPString ::= {0, 0, 47, 93}

-- kangxiRadicalProfound BMPString ::= {0, 0, 47, 94}

-- kangxiRadicalJade BMPString ::= {0, 0, 47, 95}

-- kangxiRadicalMelon BMPString ::= {0, 0, 47, 96}

-- kangxiRadicalTile BMPString ::= {0, 0, 47, 97}

-- kangxiRadicalSweet BMPString ::= {0, 0, 47, 98}

-- kangxiRadicalLife BMPString ::= {0, 0, 47, 99}

-- kangxiRadicalUse BMPString ::= {0, 0, 47, 100}

-- kangxiRadicalField BMPString ::= {0, 0, 47, 101}

-- kangxiRadicalBoltOfCloth BMPString ::= {0, 0, 47, 102}

-- kangxiRadicalSickness BMPString ::= {0, 0, 47, 103}

-- kangxiRadicalDottedTent BMPString ::= {0, 0, 47, 104}

-- kangxiRadicalWhite BMPString ::= {0, 0, 47, 105}

-- kangxiRadicalSkin BMPString ::= {0, 0, 47, 106}

-- kangxiRadicalDish BMPString ::= {0, 0, 47, 107}

-- kangxiRadicalEye BMPString ::= {0, 0, 47, 108}

-- kangxiRadicalSpear BMPString ::= {0, 0, 47, 109}

-- kangxiRadicalArrow BMPString ::= {0, 0, 47, 110}

-- kangxiRadicalStone BMPString ::= {0, 0, 47, 111}

-- kangxiRadicalSpirit BMPString ::= {0, 0, 47, 112}

-- kangxiRadicalTrack BMPString ::= {0, 0, 47, 113}

-- kangxiRadicalGrain BMPString ::= {0, 0, 47, 114}

-- kangxiRadicalCave BMPString ::= {0, 0, 47, 115}

-- kangxiRadicalStand BMPString ::= {0, 0, 47, 116}

-- kangxiRadicalBamboo BMPString ::= {0, 0, 47, 117}

-- kangxiRadicalRice BMPString ::= {0, 0, 47, 118}

-- kangxiRadicalSilk BMPString ::= {0, 0, 47, 119}

-- kangxiRadicalJar BMPString ::= {0, 0, 47, 120}

-- kangxiRadicalNet BMPString ::= {0, 0, 47, 121}

-- kangxiRadicalSheep BMPString ::= {0, 0, 47, 122}

-- kangxiRadicalFeather BMPString ::= {0, 0, 47, 123}

-- kangxiRadicalOld BMPString ::= {0, 0, 47, 124}

-- kangxiRadicalAnd BMPString ::= {0, 0, 47, 125}

-- kangxiRadicalPlow BMPString ::= {0, 0, 47, 126}

-- kangxiRadicalEar BMPString ::= {0, 0, 47, 127}

-- kangxiRadicalBrush BMPString ::= {0, 0, 47, 128}

-- kangxiRadicalMeat BMPString ::= {0, 0, 47, 129}

-- kangxiRadicalMinister BMPString ::= {0, 0, 47, 130}

-- kangxiRadicalSelf BMPString ::= {0, 0, 47, 131}

-- kangxiRadicalArrive BMPString ::= {0, 0, 47, 132}

-- kangxiRadicalMortar BMPString ::= {0, 0, 47, 133}

-- kangxiRadicalTongue BMPString ::= {0, 0, 47, 134}

-- kangxiRadicalOppose BMPString ::= {0, 0, 47, 135}

-- kangxiRadicalBoat BMPString ::= {0, 0, 47, 136}

-- kangxiRadicalStopping BMPString ::= {0, 0, 47, 137}

-- kangxiRadicalColor BMPString ::= {0, 0, 47, 138}

-- kangxiRadicalGrass BMPString ::= {0, 0, 47, 139}

-- kangxiRadicalTiger BMPString ::= {0, 0, 47, 140}

-- kangxiRadicalInsect BMPString ::= {0, 0, 47, 141}

-- kangxiRadicalBlood BMPString ::= {0, 0, 47, 142}

-- kangxiRadicalWalkEnclosure BMPString ::= {0, 0, 47, 143}

-- kangxiRadicalClothes BMPString ::= {0, 0, 47, 144}

-- kangxiRadicalWest BMPString ::= {0, 0, 47, 145}

-- kangxiRadicalSee BMPString ::= {0, 0, 47, 146}

-- kangxiRadicalHorn BMPString ::= {0, 0, 47, 147}

-- kangxiRadicalSpeech BMPString ::= {0, 0, 47, 148}

-- kangxiRadicalValley BMPString ::= {0, 0, 47, 149}

-- kangxiRadicalBean BMPString ::= {0, 0, 47, 150}

-- kangxiRadicalPig BMPString ::= {0, 0, 47, 151}

-- kangxiRadicalBadger BMPString ::= {0, 0, 47, 152}

-- kangxiRadicalShell BMPString ::= {0, 0, 47, 153}

-- kangxiRadicalRed BMPString ::= {0, 0, 47, 154}

-- kangxiRadicalRun BMPString ::= {0, 0, 47, 155}

-- kangxiRadicalFoot BMPString ::= {0, 0, 47, 156}

-- kangxiRadicalBody BMPString ::= {0, 0, 47, 157}

-- kangxiRadicalCart BMPString ::= {0, 0, 47, 158}

-- kangxiRadicalBitter BMPString ::= {0, 0, 47, 159}

-- kangxiRadicalMorning BMPString ::= {0, 0, 47, 160}

-- kangxiRadicalWalk BMPString ::= {0, 0, 47, 161}

-- kangxiRadicalCity BMPString ::= {0, 0, 47, 162}

-- kangxiRadicalWine BMPString ::= {0, 0, 47, 163}

-- kangxiRadicalDistinguish BMPString ::= {0, 0, 47, 164}

-- kangxiRadicalVillage BMPString ::= {0, 0, 47, 165}

-- kangxiRadicalGold BMPString ::= {0, 0, 47, 166}

-- kangxiRadicalLong BMPString ::= {0, 0, 47, 167}

-- kangxiRadicalGate BMPString ::= {0, 0, 47, 168}

-- kangxiRadicalMound BMPString ::= {0, 0, 47, 169}

-- kangxiRadicalSlave BMPString ::= {0, 0, 47, 170}

-- kangxiRadicalShortTailedBird BMPString ::= {0, 0, 47, 171}

-- kangxiRadicalRain BMPString ::= {0, 0, 47, 172}

-- kangxiRadicalBlue BMPString ::= {0, 0, 47, 173}

-- kangxiRadicalWrong BMPString ::= {0, 0, 47, 174}

-- kangxiRadicalFace BMPString ::= {0, 0, 47, 175}

-- kangxiRadicalLeather BMPString ::= {0, 0, 47, 176}

-- kangxiRadicalTannedLeather BMPString ::= {0, 0, 47, 177}

-- kangxiRadicalLeek BMPString ::= {0, 0, 47, 178}

-- kangxiRadicalSound BMPString ::= {0, 0, 47, 179}

-- kangxiRadicalLeaf BMPString ::= {0, 0, 47, 180}

-- kangxiRadicalWind BMPString ::= {0, 0, 47, 181}

-- kangxiRadicalFly BMPString ::= {0, 0, 47, 182}

-- kangxiRadicalEat BMPString ::= {0, 0, 47, 183}

-- kangxiRadicalHead BMPString ::= {0, 0, 47, 184}

-- kangxiRadicalFragrant BMPString ::= {0, 0, 47, 185}

-- kangxiRadicalHorse BMPString ::= {0, 0, 47, 186}

-- kangxiRadicalBone BMPString ::= {0, 0, 47, 187}

-- kangxiRadicalTall BMPString ::= {0, 0, 47, 188}

-- kangxiRadicalHair BMPString ::= {0, 0, 47, 189}

-- kangxiRadicalFight BMPString ::= {0, 0, 47, 190}

-- kangxiRadicalSacrificialWine BMPString ::= {0, 0, 47, 191}

-- kangxiRadicalCauldron BMPString ::= {0, 0, 47, 192}

-- kangxiRadicalGhost BMPString ::= {0, 0, 47, 193}

-- kangxiRadicalFish BMPString ::= {0, 0, 47, 194}

-- kangxiRadicalBird BMPString ::= {0, 0, 47, 195}

-- kangxiRadicalSalt BMPString ::= {0, 0, 47, 196}

-- kangxiRadicalDeer BMPString ::= {0, 0, 47, 197}

-- kangxiRadicalWheat BMPString ::= {0, 0, 47, 198}

-- kangxiRadicalHemp BMPString ::= {0, 0, 47, 199}

-- kangxiRadicalYellow BMPString ::= {0, 0, 47, 200}

-- kangxiRadicalMillet BMPString ::= {0, 0, 47, 201}

-- kangxiRadicalBlack BMPString ::= {0, 0, 47, 202}

-- kangxiRadicalEmbroidery BMPString ::= {0, 0, 47, 203}

-- kangxiRadicalFrog BMPString ::= {0, 0, 47, 204}

-- kangxiRadicalTripod BMPString ::= {0, 0, 47, 205}

-- kangxiRadicalDrum BMPString ::= {0, 0, 47, 206}

-- kangxiRadicalRat BMPString ::= {0, 0, 47, 207}

-- kangxiRadicalNose BMPString ::= {0, 0, 47, 208}

-- kangxiRadicalEven BMPString ::= {0, 0, 47, 209}

-- kangxiRadicalTooth BMPString ::= {0, 0, 47, 210}

-- kangxiRadicalDragon BMPString ::= {0, 0, 47, 211}

-- kangxiRadicalTurtle BMPString ::= {0, 0, 47, 212}

-- kangxiRadicalFlute BMPString ::= {0, 0, 47, 213}

-- ideographicDescriptionCharacterLeftToRight BMPString ::= {0, 0, 47, 240}

-- ideographicDescriptionCharacterAboveToBelow BMPString ::= {0, 0, 47, 241}

-- ideographicDescriptionCharacterLeftToMiddleAndRight BMPString ::=
--   {0, 0, 47, 242}

-- ideographicDescriptionCharacterAboveToMiddleAndBelow BMPString ::=
--   {0, 0, 47, 243}

-- ideographicDescriptionCharacterFullSurround BMPString ::= {0, 0, 47, 244}

-- ideographicDescriptionCharacterSurroundFromAbove BMPString ::= {0, 0, 47, 245}

-- ideographicDescriptionCharacterSurroundFromBelow BMPString ::= {0, 0, 47, 246}

-- ideographicDescriptionCharacterSurroundFromLeft BMPString ::= {0, 0, 47, 247}

-- ideographicDescriptionCharacterSurroundFromUpperLeft BMPString ::=
--   {0, 0, 47, 248}

-- ideographicDescriptionCharacterSurroundFromUpperRight BMPString ::=
--   {0, 0, 47, 249}

-- ideographicDescriptionCharacterSurroundFromLowerLeft BMPString ::=
--   {0, 0, 47, 250}

-- ideographicDescriptionCharacterOverlaid BMPString ::= {0, 0, 47, 251}

-- ideographicSpace BMPString ::= {0, 0, 48, 0}

-- ideographicComma BMPString ::= {0, 0, 48, 1}

-- ideographicFullStop BMPString ::= {0, 0, 48, 2}

-- dittoMark BMPString ::= {0, 0, 48, 3}

-- japaneseIndustrialStandardSymbol BMPString ::= {0, 0, 48, 4}

-- ideographicIterationMark BMPString ::= {0, 0, 48, 5}

-- ideographicClosingMark BMPString ::= {0, 0, 48, 6}

-- ideographicNumberZero BMPString ::= {0, 0, 48, 7}

-- leftAngleBracket BMPString ::= {0, 0, 48, 8}

-- rightAngleBracket BMPString ::= {0, 0, 48, 9}

-- leftDoubleAngleBracket BMPString ::= {0, 0, 48, 10}

-- rightDoubleAngleBracket BMPString ::= {0, 0, 48, 11}

-- leftCornerBracket BMPString ::= {0, 0, 48, 12}

-- rightCornerBracket BMPString ::= {0, 0, 48, 13}

-- leftWhiteCornerBracket BMPString ::= {0, 0, 48, 14}

-- rightWhiteCornerBracket BMPString ::= {0, 0, 48, 15}

-- leftBlackLenticularBracket BMPString ::= {0, 0, 48, 16}

-- rightBlackLenticularBracket BMPString ::= {0, 0, 48, 17}

-- postalMark BMPString ::= {0, 0, 48, 18}

-- getaMark BMPString ::= {0, 0, 48, 19}

-- leftTortoiseShellBracket BMPString ::= {0, 0, 48, 20}

-- rightTortoiseShellBracket BMPString ::= {0, 0, 48, 21}

-- leftWhiteLenticularBracket BMPString ::= {0, 0, 48, 22}

-- rightWhiteLenticularBracket BMPString ::= {0, 0, 48, 23}

-- leftWhiteTortoiseShellBracket BMPString ::= {0, 0, 48, 24}

-- rightWhiteTortoiseShellBracket BMPString ::= {0, 0, 48, 25}

-- leftWhiteSquareBracket BMPString ::= {0, 0, 48, 26}

-- rightWhiteSquareBracket BMPString ::= {0, 0, 48, 27}

-- waveDash BMPString ::= {0, 0, 48, 28}

-- reversedDoublePrimeQuotationMark BMPString ::= {0, 0, 48, 29}

-- doublePrimeQuotationMark BMPString ::= {0, 0, 48, 30}

-- lowDoublePrimeQuotationMark BMPString ::= {0, 0, 48, 31}

-- postalMarkFace BMPString ::= {0, 0, 48, 32}

-- hangzhouNumeralOne BMPString ::= {0, 0, 48, 33}

-- hangzhouNumeralTwo BMPString ::= {0, 0, 48, 34}

-- hangzhouNumeralThree BMPString ::= {0, 0, 48, 35}

-- hangzhouNumeralFour BMPString ::= {0, 0, 48, 36}

-- hangzhouNumeralFive BMPString ::= {0, 0, 48, 37}

-- hangzhouNumeralSix BMPString ::= {0, 0, 48, 38}

-- hangzhouNumeralSeven BMPString ::= {0, 0, 48, 39}

-- hangzhouNumeralEight BMPString ::= {0, 0, 48, 40}

-- hangzhouNumeralNine BMPString ::= {0, 0, 48, 41}

-- ideographicLevelToneMark BMPString ::= {0, 0, 48, 42}

-- ideographicRisingToneMark BMPString ::= {0, 0, 48, 43}

-- ideographicDepartingToneMark BMPString ::= {0, 0, 48, 44}

-- ideographicEnteringToneMark BMPString ::= {0, 0, 48, 45}

-- hangulSingleDotToneMark BMPString ::= {0, 0, 48, 46}

-- hangulDoubleDotToneMark BMPString ::= {0, 0, 48, 47}

-- wavyDash BMPString ::= {0, 0, 48, 48}

-- verticalKanaRepeatMark BMPString ::= {0, 0, 48, 49}

-- verticalKanaRepeatWithVoicedSoundMark BMPString ::= {0, 0, 48, 50}

-- verticalKanaRepeatMarkUpperHalf BMPString ::= {0, 0, 48, 51}

-- verticalKanaRepeatWithVoicedSoundMarkUpperHalf BMPString ::= {0, 0, 48, 52}

-- verticalKanaRepeatMarkLowerHalf BMPString ::= {0, 0, 48, 53}

-- circledPostalMark BMPString ::= {0, 0, 48, 54}

-- ideographicTelegraphLineFeedSeparatorSymbol BMPString ::= {0, 0, 48, 55}

-- hangzhouNumeralTen BMPString ::= {0, 0, 48, 56}

-- hangzhouNumeralTwenty BMPString ::= {0, 0, 48, 57}

-- hangzhouNumeralThirty BMPString ::= {0, 0, 48, 58}

-- verticalIdeographicIterationMark BMPString ::= {0, 0, 48, 59}

-- masuMark BMPString ::= {0, 0, 48, 60}

-- partAlternationMark BMPString ::= {0, 0, 48, 61}

-- ideographicVariationIndicator BMPString ::= {0, 0, 48, 62}

-- ideographicHalfFillSpace BMPString ::= {0, 0, 48, 63}

-- hiraganaLetterSmallA BMPString ::= {0, 0, 48, 65}

-- hiraganaLetterA BMPString ::= {0, 0, 48, 66}

-- hiraganaLetterSmallI BMPString ::= {0, 0, 48, 67}

-- hiraganaLetterI BMPString ::= {0, 0, 48, 68}

-- hiraganaLetterSmallU BMPString ::= {0, 0, 48, 69}

-- hiraganaLetterU BMPString ::= {0, 0, 48, 70}

-- hiraganaLetterSmallE BMPString ::= {0, 0, 48, 71}

-- hiraganaLetterE BMPString ::= {0, 0, 48, 72}

-- hiraganaLetterSmallO BMPString ::= {0, 0, 48, 73}

-- hiraganaLetterO BMPString ::= {0, 0, 48, 74}

-- hiraganaLetterKa BMPString ::= {0, 0, 48, 75}

-- hiraganaLetterGa BMPString ::= {0, 0, 48, 76}

-- hiraganaLetterKi BMPString ::= {0, 0, 48, 77}

-- hiraganaLetterGi BMPString ::= {0, 0, 48, 78}

-- hiraganaLetterKu BMPString ::= {0, 0, 48, 79}

-- hiraganaLetterGu BMPString ::= {0, 0, 48, 80}

-- hiraganaLetterKe BMPString ::= {0, 0, 48, 81}

-- hiraganaLetterGe BMPString ::= {0, 0, 48, 82}

-- hiraganaLetterKo BMPString ::= {0, 0, 48, 83}

-- hiraganaLetterGo BMPString ::= {0, 0, 48, 84}

-- hiraganaLetterSa BMPString ::= {0, 0, 48, 85}

-- hiraganaLetterZa BMPString ::= {0, 0, 48, 86}

-- hiraganaLetterSi BMPString ::= {0, 0, 48, 87}

-- hiraganaLetterZi BMPString ::= {0, 0, 48, 88}

-- hiraganaLetterSu BMPString ::= {0, 0, 48, 89}

-- hiraganaLetterZu BMPString ::= {0, 0, 48, 90}

-- hiraganaLetterSe BMPString ::= {0, 0, 48, 91}

-- hiraganaLetterZe BMPString ::= {0, 0, 48, 92}

-- hiraganaLetterSo BMPString ::= {0, 0, 48, 93}

-- hiraganaLetterZo BMPString ::= {0, 0, 48, 94}

-- hiraganaLetterTa BMPString ::= {0, 0, 48, 95}

-- hiraganaLetterDa BMPString ::= {0, 0, 48, 96}

-- hiraganaLetterTi BMPString ::= {0, 0, 48, 97}

-- hiraganaLetterDi BMPString ::= {0, 0, 48, 98}

-- hiraganaLetterSmallTu BMPString ::= {0, 0, 48, 99}

-- hiraganaLetterTu BMPString ::= {0, 0, 48, 100}

-- hiraganaLetterDu BMPString ::= {0, 0, 48, 101}

-- hiraganaLetterTe BMPString ::= {0, 0, 48, 102}

-- hiraganaLetterDe BMPString ::= {0, 0, 48, 103}

-- hiraganaLetterTo BMPString ::= {0, 0, 48, 104}

-- hiraganaLetterDo BMPString ::= {0, 0, 48, 105}

-- hiraganaLetterNa BMPString ::= {0, 0, 48, 106}

-- hiraganaLetterNi BMPString ::= {0, 0, 48, 107}

-- hiraganaLetterNu BMPString ::= {0, 0, 48, 108}

-- hiraganaLetterNe BMPString ::= {0, 0, 48, 109}

-- hiraganaLetterNo BMPString ::= {0, 0, 48, 110}

-- hiraganaLetterHa BMPString ::= {0, 0, 48, 111}

-- hiraganaLetterBa BMPString ::= {0, 0, 48, 112}

-- hiraganaLetterPa BMPString ::= {0, 0, 48, 113}

-- hiraganaLetterHi BMPString ::= {0, 0, 48, 114}

-- hiraganaLetterBi BMPString ::= {0, 0, 48, 115}

-- hiraganaLetterPi BMPString ::= {0, 0, 48, 116}

-- hiraganaLetterHu BMPString ::= {0, 0, 48, 117}

-- hiraganaLetterBu BMPString ::= {0, 0, 48, 118}

-- hiraganaLetterPu BMPString ::= {0, 0, 48, 119}

-- hiraganaLetterHe BMPString ::= {0, 0, 48, 120}

-- hiraganaLetterBe BMPString ::= {0, 0, 48, 121}

-- hiraganaLetterPe BMPString ::= {0, 0, 48, 122}

-- hiraganaLetterHo BMPString ::= {0, 0, 48, 123}

-- hiraganaLetterBo BMPString ::= {0, 0, 48, 124}

-- hiraganaLetterPo BMPString ::= {0, 0, 48, 125}

-- hiraganaLetterMa BMPString ::= {0, 0, 48, 126}

-- hiraganaLetterMi BMPString ::= {0, 0, 48, 127}

-- hiraganaLetterMu BMPString ::= {0, 0, 48, 128}

-- hiraganaLetterMe BMPString ::= {0, 0, 48, 129}

-- hiraganaLetterMo BMPString ::= {0, 0, 48, 130}

-- hiraganaLetterSmallYa BMPString ::= {0, 0, 48, 131}

-- hiraganaLetterYa BMPString ::= {0, 0, 48, 132}

-- hiraganaLetterSmallYu BMPString ::= {0, 0, 48, 133}

-- hiraganaLetterYu BMPString ::= {0, 0, 48, 134}

-- hiraganaLetterSmallYo BMPString ::= {0, 0, 48, 135}

-- hiraganaLetterYo BMPString ::= {0, 0, 48, 136}

-- hiraganaLetterRa BMPString ::= {0, 0, 48, 137}

-- hiraganaLetterRi BMPString ::= {0, 0, 48, 138}

-- hiraganaLetterRu BMPString ::= {0, 0, 48, 139}

-- hiraganaLetterRe BMPString ::= {0, 0, 48, 140}

-- hiraganaLetterRo BMPString ::= {0, 0, 48, 141}

-- hiraganaLetterSmallWa BMPString ::= {0, 0, 48, 142}

-- hiraganaLetterWa BMPString ::= {0, 0, 48, 143}

-- hiraganaLetterWi BMPString ::= {0, 0, 48, 144}

-- hiraganaLetterWe BMPString ::= {0, 0, 48, 145}

-- hiraganaLetterWo BMPString ::= {0, 0, 48, 146}

-- hiraganaLetterN BMPString ::= {0, 0, 48, 147}

-- hiraganaLetterVu BMPString ::= {0, 0, 48, 148}

-- hiraganaLetterSmallKa BMPString ::= {0, 0, 48, 149}

-- hiraganaLetterSmallKe BMPString ::= {0, 0, 48, 150}

-- combiningKatakana-hiraganaVoicedSoundMark BMPString ::= {0, 0, 48, 153}

-- combiningKatakana-hiraganaSemi-voicedSoundMark BMPString ::= {0, 0, 48, 154}

-- katakana-hiraganaVoicedSoundMark BMPString ::= {0, 0, 48, 155}

-- katakana-hiraganaSemi-voicedSoundMark BMPString ::= {0, 0, 48, 156}

-- hiraganaIterationMark BMPString ::= {0, 0, 48, 157}

-- hiraganaVoicedIterationMark BMPString ::= {0, 0, 48, 158}

-- hiraganaDigraphYori BMPString ::= {0, 0, 48, 159}

-- katakana-hiraganaDoubleHyphen BMPString ::= {0, 0, 48, 160}

-- katakanaLetterSmallA BMPString ::= {0, 0, 48, 161}

-- katakanaLetterA BMPString ::= {0, 0, 48, 162}

-- katakanaLetterSmallI BMPString ::= {0, 0, 48, 163}

-- katakanaLetterI BMPString ::= {0, 0, 48, 164}

-- katakanaLetterSmallU BMPString ::= {0, 0, 48, 165}

-- katakanaLetterU BMPString ::= {0, 0, 48, 166}

-- katakanaLetterSmallE BMPString ::= {0, 0, 48, 167}

-- katakanaLetterE BMPString ::= {0, 0, 48, 168}

-- katakanaLetterSmallO BMPString ::= {0, 0, 48, 169}

-- katakanaLetterO BMPString ::= {0, 0, 48, 170}

-- katakanaLetterKa BMPString ::= {0, 0, 48, 171}

-- katakanaLetterGa BMPString ::= {0, 0, 48, 172}

-- katakanaLetterKi BMPString ::= {0, 0, 48, 173}

-- katakanaLetterGi BMPString ::= {0, 0, 48, 174}

-- katakanaLetterKu BMPString ::= {0, 0, 48, 175}

-- katakanaLetterGu BMPString ::= {0, 0, 48, 176}

-- katakanaLetterKe BMPString ::= {0, 0, 48, 177}

-- katakanaLetterGe BMPString ::= {0, 0, 48, 178}

-- katakanaLetterKo BMPString ::= {0, 0, 48, 179}

-- katakanaLetterGo BMPString ::= {0, 0, 48, 180}

-- katakanaLetterSa BMPString ::= {0, 0, 48, 181}

-- katakanaLetterZa BMPString ::= {0, 0, 48, 182}

-- katakanaLetterSi BMPString ::= {0, 0, 48, 183}

-- katakanaLetterZi BMPString ::= {0, 0, 48, 184}

-- katakanaLetterSu BMPString ::= {0, 0, 48, 185}

-- katakanaLetterZu BMPString ::= {0, 0, 48, 186}

-- katakanaLetterSe BMPString ::= {0, 0, 48, 187}

-- katakanaLetterZe BMPString ::= {0, 0, 48, 188}

-- katakanaLetterSo BMPString ::= {0, 0, 48, 189}

-- katakanaLetterZo BMPString ::= {0, 0, 48, 190}

-- katakanaLetterTa BMPString ::= {0, 0, 48, 191}

-- katakanaLetterDa BMPString ::= {0, 0, 48, 192}

-- katakanaLetterTi BMPString ::= {0, 0, 48, 193}

-- katakanaLetterDi BMPString ::= {0, 0, 48, 194}

-- katakanaLetterSmallTu BMPString ::= {0, 0, 48, 195}

-- katakanaLetterTu BMPString ::= {0, 0, 48, 196}

-- katakanaLetterDu BMPString ::= {0, 0, 48, 197}

-- katakanaLetterTe BMPString ::= {0, 0, 48, 198}

-- katakanaLetterDe BMPString ::= {0, 0, 48, 199}

-- katakanaLetterTo BMPString ::= {0, 0, 48, 200}

-- katakanaLetterDo BMPString ::= {0, 0, 48, 201}

-- katakanaLetterNa BMPString ::= {0, 0, 48, 202}

-- katakanaLetterNi BMPString ::= {0, 0, 48, 203}

-- katakanaLetterNu BMPString ::= {0, 0, 48, 204}

-- katakanaLetterNe BMPString ::= {0, 0, 48, 205}

-- katakanaLetterNo BMPString ::= {0, 0, 48, 206}

-- katakanaLetterHa BMPString ::= {0, 0, 48, 207}

-- katakanaLetterBa BMPString ::= {0, 0, 48, 208}

-- katakanaLetterPa BMPString ::= {0, 0, 48, 209}

-- katakanaLetterHi BMPString ::= {0, 0, 48, 210}

-- katakanaLetterBi BMPString ::= {0, 0, 48, 211}

-- katakanaLetterPi BMPString ::= {0, 0, 48, 212}

-- katakanaLetterHu BMPString ::= {0, 0, 48, 213}

-- katakanaLetterBu BMPString ::= {0, 0, 48, 214}

-- katakanaLetterPu BMPString ::= {0, 0, 48, 215}

-- katakanaLetterHe BMPString ::= {0, 0, 48, 216}

-- katakanaLetterBe BMPString ::= {0, 0, 48, 217}

-- katakanaLetterPe BMPString ::= {0, 0, 48, 218}

-- katakanaLetterHo BMPString ::= {0, 0, 48, 219}

-- katakanaLetterBo BMPString ::= {0, 0, 48, 220}

-- katakanaLetterPo BMPString ::= {0, 0, 48, 221}

-- katakanaLetterMa BMPString ::= {0, 0, 48, 222}

-- katakanaLetterMi BMPString ::= {0, 0, 48, 223}

-- katakanaLetterMu BMPString ::= {0, 0, 48, 224}

-- katakanaLetterMe BMPString ::= {0, 0, 48, 225}

-- katakanaLetterMo BMPString ::= {0, 0, 48, 226}

-- katakanaLetterSmallYa BMPString ::= {0, 0, 48, 227}

-- katakanaLetterYa BMPString ::= {0, 0, 48, 228}

-- katakanaLetterSmallYu BMPString ::= {0, 0, 48, 229}

-- katakanaLetterYu BMPString ::= {0, 0, 48, 230}

-- katakanaLetterSmallYo BMPString ::= {0, 0, 48, 231}

-- katakanaLetterYo BMPString ::= {0, 0, 48, 232}

-- katakanaLetterRa BMPString ::= {0, 0, 48, 233}

-- katakanaLetterRi BMPString ::= {0, 0, 48, 234}

-- katakanaLetterRu BMPString ::= {0, 0, 48, 235}

-- katakanaLetterRe BMPString ::= {0, 0, 48, 236}

-- katakanaLetterRo BMPString ::= {0, 0, 48, 237}

-- katakanaLetterSmallWa BMPString ::= {0, 0, 48, 238}

-- katakanaLetterWa BMPString ::= {0, 0, 48, 239}

-- katakanaLetterWi BMPString ::= {0, 0, 48, 240}

-- katakanaLetterWe BMPString ::= {0, 0, 48, 241}

-- katakanaLetterWo BMPString ::= {0, 0, 48, 242}

-- katakanaLetterN BMPString ::= {0, 0, 48, 243}

-- katakanaLetterVu BMPString ::= {0, 0, 48, 244}

-- katakanaLetterSmallKa BMPString ::= {0, 0, 48, 245}

-- katakanaLetterSmallKe BMPString ::= {0, 0, 48, 246}

-- katakanaLetterVa BMPString ::= {0, 0, 48, 247}

-- katakanaLetterVi BMPString ::= {0, 0, 48, 248}

-- katakanaLetterVe BMPString ::= {0, 0, 48, 249}

-- katakanaLetterVo BMPString ::= {0, 0, 48, 250}

-- katakanaMiddleDot BMPString ::= {0, 0, 48, 251}

-- katakana-hiraganaProlongedSoundMark BMPString ::= {0, 0, 48, 252}

-- katakanaIterationMark BMPString ::= {0, 0, 48, 253}

-- katakanaVoicedIterationMark BMPString ::= {0, 0, 48, 254}

-- katakanaDigraphKoto BMPString ::= {0, 0, 48, 255}

-- bopomofoLetterB BMPString ::= {0, 0, 49, 5}

-- bopomofoLetterP BMPString ::= {0, 0, 49, 6}

-- bopomofoLetterM BMPString ::= {0, 0, 49, 7}

-- bopomofoLetterF BMPString ::= {0, 0, 49, 8}

-- bopomofoLetterD BMPString ::= {0, 0, 49, 9}

-- bopomofoLetterT BMPString ::= {0, 0, 49, 10}

-- bopomofoLetterN BMPString ::= {0, 0, 49, 11}

-- bopomofoLetterL BMPString ::= {0, 0, 49, 12}

-- bopomofoLetterG BMPString ::= {0, 0, 49, 13}

-- bopomofoLetterK BMPString ::= {0, 0, 49, 14}

-- bopomofoLetterH BMPString ::= {0, 0, 49, 15}

-- bopomofoLetterJ BMPString ::= {0, 0, 49, 16}

-- bopomofoLetterQ BMPString ::= {0, 0, 49, 17}

-- bopomofoLetterX BMPString ::= {0, 0, 49, 18}

-- bopomofoLetterZh BMPString ::= {0, 0, 49, 19}

-- bopomofoLetterCh BMPString ::= {0, 0, 49, 20}

-- bopomofoLetterSh BMPString ::= {0, 0, 49, 21}

-- bopomofoLetterR BMPString ::= {0, 0, 49, 22}

-- bopomofoLetterZ BMPString ::= {0, 0, 49, 23}

-- bopomofoLetterC BMPString ::= {0, 0, 49, 24}

-- bopomofoLetterS BMPString ::= {0, 0, 49, 25}

-- bopomofoLetterA BMPString ::= {0, 0, 49, 26}

-- bopomofoLetterO BMPString ::= {0, 0, 49, 27}

-- bopomofoLetterE BMPString ::= {0, 0, 49, 28}

-- bopomofoLetterEh BMPString ::= {0, 0, 49, 29}

-- bopomofoLetterAi BMPString ::= {0, 0, 49, 30}

-- bopomofoLetterEi BMPString ::= {0, 0, 49, 31}

-- bopomofoLetterAu BMPString ::= {0, 0, 49, 32}

-- bopomofoLetterOu BMPString ::= {0, 0, 49, 33}

-- bopomofoLetterAn BMPString ::= {0, 0, 49, 34}

-- bopomofoLetterEn BMPString ::= {0, 0, 49, 35}

-- bopomofoLetterAng BMPString ::= {0, 0, 49, 36}

-- bopomofoLetterEng BMPString ::= {0, 0, 49, 37}

-- bopomofoLetterEr BMPString ::= {0, 0, 49, 38}

-- bopomofoLetterI BMPString ::= {0, 0, 49, 39}

-- bopomofoLetterU BMPString ::= {0, 0, 49, 40}

-- bopomofoLetterIu BMPString ::= {0, 0, 49, 41}

-- bopomofoLetterV BMPString ::= {0, 0, 49, 42}

-- bopomofoLetterNg BMPString ::= {0, 0, 49, 43}

-- bopomofoLetterGn BMPString ::= {0, 0, 49, 44}

-- hangulLetterKiyeok BMPString ::= {0, 0, 49, 49}

-- hangulLetterSsangkiyeok BMPString ::= {0, 0, 49, 50}

-- hangulLetterKiyeok-sios BMPString ::= {0, 0, 49, 51}

-- hangulLetterNieun BMPString ::= {0, 0, 49, 52}

-- hangulLetterNieun-cieuc BMPString ::= {0, 0, 49, 53}

-- hangulLetterNieun-hieuh BMPString ::= {0, 0, 49, 54}

-- hangulLetterTikeut BMPString ::= {0, 0, 49, 55}

-- hangulLetterSsangtikeut BMPString ::= {0, 0, 49, 56}

-- hangulLetterRieul BMPString ::= {0, 0, 49, 57}

-- hangulLetterRieul-kiyeok BMPString ::= {0, 0, 49, 58}

-- hangulLetterRieul-mieum BMPString ::= {0, 0, 49, 59}

-- hangulLetterRieul-pieup BMPString ::= {0, 0, 49, 60}

-- hangulLetterRieul-sios BMPString ::= {0, 0, 49, 61}

-- hangulLetterRieul-thieuth BMPString ::= {0, 0, 49, 62}

-- hangulLetterRieul-phieuph BMPString ::= {0, 0, 49, 63}

-- hangulLetterRieul-hieuh BMPString ::= {0, 0, 49, 64}

-- hangulLetterMieum BMPString ::= {0, 0, 49, 65}

-- hangulLetterPieup BMPString ::= {0, 0, 49, 66}

-- hangulLetterSsangpieup BMPString ::= {0, 0, 49, 67}

-- hangulLetterPieup-sios BMPString ::= {0, 0, 49, 68}

-- hangulLetterSios BMPString ::= {0, 0, 49, 69}

-- hangulLetterSsangsios BMPString ::= {0, 0, 49, 70}

-- hangulLetterIeung BMPString ::= {0, 0, 49, 71}

-- hangulLetterCieuc BMPString ::= {0, 0, 49, 72}

-- hangulLetterSsangcieuc BMPString ::= {0, 0, 49, 73}

-- hangulLetterChieuch BMPString ::= {0, 0, 49, 74}

-- hangulLetterKhieukh BMPString ::= {0, 0, 49, 75}

-- hangulLetterThieuth BMPString ::= {0, 0, 49, 76}

-- hangulLetterPhieuph BMPString ::= {0, 0, 49, 77}

-- hangulLetterHieuh BMPString ::= {0, 0, 49, 78}

-- hangulLetterA BMPString ::= {0, 0, 49, 79}

-- hangulLetterAe BMPString ::= {0, 0, 49, 80}

-- hangulLetterYa BMPString ::= {0, 0, 49, 81}

-- hangulLetterYae BMPString ::= {0, 0, 49, 82}

-- hangulLetterEo BMPString ::= {0, 0, 49, 83}

-- hangulLetterE BMPString ::= {0, 0, 49, 84}

-- hangulLetterYeo BMPString ::= {0, 0, 49, 85}

-- hangulLetterYe BMPString ::= {0, 0, 49, 86}

-- hangulLetterO BMPString ::= {0, 0, 49, 87}

-- hangulLetterWa BMPString ::= {0, 0, 49, 88}

-- hangulLetterWae BMPString ::= {0, 0, 49, 89}

-- hangulLetterOe BMPString ::= {0, 0, 49, 90}

-- hangulLetterYo BMPString ::= {0, 0, 49, 91}

-- hangulLetterU BMPString ::= {0, 0, 49, 92}

-- hangulLetterWeo BMPString ::= {0, 0, 49, 93}

-- hangulLetterWe BMPString ::= {0, 0, 49, 94}

-- hangulLetterWi BMPString ::= {0, 0, 49, 95}

-- hangulLetterYu BMPString ::= {0, 0, 49, 96}

-- hangulLetterEu BMPString ::= {0, 0, 49, 97}

-- hangulLetterYi BMPString ::= {0, 0, 49, 98}

-- hangulLetterI BMPString ::= {0, 0, 49, 99}

-- hangulFiller BMPString ::= {0, 0, 49, 100}

-- hangulLetterSsangnieun BMPString ::= {0, 0, 49, 101}

-- hangulLetterNieun-tikeut BMPString ::= {0, 0, 49, 102}

-- hangulLetterNieun-sios BMPString ::= {0, 0, 49, 103}

-- hangulLetterNieun-pansios BMPString ::= {0, 0, 49, 104}

-- hangulLetterRieul-kiyeok-sios BMPString ::= {0, 0, 49, 105}

-- hangulLetterRieul-tikeut BMPString ::= {0, 0, 49, 106}

-- hangulLetterRieul-pieup-sios BMPString ::= {0, 0, 49, 107}

-- hangulLetterRieul-pansios BMPString ::= {0, 0, 49, 108}

-- hangulLetterRieul-yeorinhieuh BMPString ::= {0, 0, 49, 109}

-- hangulLetterMieum-pieup BMPString ::= {0, 0, 49, 110}

-- hangulLetterMieum-sios BMPString ::= {0, 0, 49, 111}

-- hangulLetterMieum-pansios BMPString ::= {0, 0, 49, 112}

-- hangulLetterKapyeounmieum BMPString ::= {0, 0, 49, 113}

-- hangulLetterPieup-kiyeok BMPString ::= {0, 0, 49, 114}

-- hangulLetterPieup-tikeut BMPString ::= {0, 0, 49, 115}

-- hangulLetterPieup-sios-kiyeok BMPString ::= {0, 0, 49, 116}

-- hangulLetterPieup-sios-tikeut BMPString ::= {0, 0, 49, 117}

-- hangulLetterPieup-cieuc BMPString ::= {0, 0, 49, 118}

-- hangulLetterPieup-thieuth BMPString ::= {0, 0, 49, 119}

-- hangulLetterKapyeounpieup BMPString ::= {0, 0, 49, 120}

-- hangulLetterKapyeounssangpieup BMPString ::= {0, 0, 49, 121}

-- hangulLetterSios-kiyeok BMPString ::= {0, 0, 49, 122}

-- hangulLetterSios-nieun BMPString ::= {0, 0, 49, 123}

-- hangulLetterSios-tikeut BMPString ::= {0, 0, 49, 124}

-- hangulLetterSios-pieup BMPString ::= {0, 0, 49, 125}

-- hangulLetterSios-cieuc BMPString ::= {0, 0, 49, 126}

-- hangulLetterPansios BMPString ::= {0, 0, 49, 127}

-- hangulLetterSsangieung BMPString ::= {0, 0, 49, 128}

-- hangulLetterYesieung BMPString ::= {0, 0, 49, 129}

-- hangulLetterYesieung-sios BMPString ::= {0, 0, 49, 130}

-- hangulLetterYesieung-pansios BMPString ::= {0, 0, 49, 131}

-- hangulLetterKapyeounphieuph BMPString ::= {0, 0, 49, 132}

-- hangulLetterSsanghieuh BMPString ::= {0, 0, 49, 133}

-- hangulLetterYeorinhieuh BMPString ::= {0, 0, 49, 134}

-- hangulLetterYo-ya BMPString ::= {0, 0, 49, 135}

-- hangulLetterYo-yae BMPString ::= {0, 0, 49, 136}

-- hangulLetterYo-i BMPString ::= {0, 0, 49, 137}

-- hangulLetterYu-yeo BMPString ::= {0, 0, 49, 138}

-- hangulLetterYu-ye BMPString ::= {0, 0, 49, 139}

-- hangulLetterYu-i BMPString ::= {0, 0, 49, 140}

-- hangulLetterAraea BMPString ::= {0, 0, 49, 141}

-- hangulLetterAraeae BMPString ::= {0, 0, 49, 142}

-- ideographicAnnotationLinkingMark BMPString ::= {0, 0, 49, 144}

-- ideographicAnnotationReverseMark BMPString ::= {0, 0, 49, 145}

-- ideographicAnnotationOneMark BMPString ::= {0, 0, 49, 146}

-- ideographicAnnotationTwoMark BMPString ::= {0, 0, 49, 147}

-- ideographicAnnotationThreeMark BMPString ::= {0, 0, 49, 148}

-- ideographicAnnotationFourMark BMPString ::= {0, 0, 49, 149}

-- ideographicAnnotationTopMark BMPString ::= {0, 0, 49, 150}

-- ideographicAnnotationMiddleMark BMPString ::= {0, 0, 49, 151}

-- ideographicAnnotationBottomMark BMPString ::= {0, 0, 49, 152}

-- ideographicAnnotationFirstMark BMPString ::= {0, 0, 49, 153}

-- ideographicAnnotationSecondMark BMPString ::= {0, 0, 49, 154}

-- ideographicAnnotationThirdMark BMPString ::= {0, 0, 49, 155}

-- ideographicAnnotationFourthMark BMPString ::= {0, 0, 49, 156}

-- ideographicAnnotationHeavenMark BMPString ::= {0, 0, 49, 157}

-- ideographicAnnotationEarthMark BMPString ::= {0, 0, 49, 158}

-- ideographicAnnotationManMark BMPString ::= {0, 0, 49, 159}

-- bopomofoLetterBu BMPString ::= {0, 0, 49, 160}

-- bopomofoLetterZi BMPString ::= {0, 0, 49, 161}

-- bopomofoLetterJi BMPString ::= {0, 0, 49, 162}

-- bopomofoLetterGu BMPString ::= {0, 0, 49, 163}

-- bopomofoLetterEe BMPString ::= {0, 0, 49, 164}

-- bopomofoLetterEnn BMPString ::= {0, 0, 49, 165}

-- bopomofoLetterOo BMPString ::= {0, 0, 49, 166}

-- bopomofoLetterOnn BMPString ::= {0, 0, 49, 167}

-- bopomofoLetterIr BMPString ::= {0, 0, 49, 168}

-- bopomofoLetterAnn BMPString ::= {0, 0, 49, 169}

-- bopomofoLetterInn BMPString ::= {0, 0, 49, 170}

-- bopomofoLetterUnn BMPString ::= {0, 0, 49, 171}

-- bopomofoLetterIm BMPString ::= {0, 0, 49, 172}

-- bopomofoLetterNgg BMPString ::= {0, 0, 49, 173}

-- bopomofoLetterAinn BMPString ::= {0, 0, 49, 174}

-- bopomofoLetterAunn BMPString ::= {0, 0, 49, 175}

-- bopomofoLetterAm BMPString ::= {0, 0, 49, 176}

-- bopomofoLetterOm BMPString ::= {0, 0, 49, 177}

-- bopomofoLetterOng BMPString ::= {0, 0, 49, 178}

-- bopomofoLetterInnn BMPString ::= {0, 0, 49, 179}

-- bopomofoFinalLetterP BMPString ::= {0, 0, 49, 180}

-- bopomofoFinalLetterT BMPString ::= {0, 0, 49, 181}

-- bopomofoFinalLetterK BMPString ::= {0, 0, 49, 182}

-- bopomofoFinalLetterH BMPString ::= {0, 0, 49, 183}

-- katakanaLetterSmallKu BMPString ::= {0, 0, 49, 240}

-- katakanaLetterSmallSi BMPString ::= {0, 0, 49, 241}

-- katakanaLetterSmallSu BMPString ::= {0, 0, 49, 242}

-- katakanaLetterSmallTo BMPString ::= {0, 0, 49, 243}

-- katakanaLetterSmallNu BMPString ::= {0, 0, 49, 244}

-- katakanaLetterSmallHa BMPString ::= {0, 0, 49, 245}

-- katakanaLetterSmallHi BMPString ::= {0, 0, 49, 246}

-- katakanaLetterSmallHu BMPString ::= {0, 0, 49, 247}

-- katakanaLetterSmallHe BMPString ::= {0, 0, 49, 248}

-- katakanaLetterSmallHo BMPString ::= {0, 0, 49, 249}

-- katakanaLetterSmallMu BMPString ::= {0, 0, 49, 250}

-- katakanaLetterSmallRa BMPString ::= {0, 0, 49, 251}

-- katakanaLetterSmallRi BMPString ::= {0, 0, 49, 252}

-- katakanaLetterSmallRu BMPString ::= {0, 0, 49, 253}

-- katakanaLetterSmallRe BMPString ::= {0, 0, 49, 254}

-- katakanaLetterSmallRo BMPString ::= {0, 0, 49, 255}

-- parenthesizedHangulKiyeok BMPString ::= {0, 0, 50, 0}

-- parenthesizedHangulNieun BMPString ::= {0, 0, 50, 1}

-- parenthesizedHangulTikeut BMPString ::= {0, 0, 50, 2}

-- parenthesizedHangulRieul BMPString ::= {0, 0, 50, 3}

-- parenthesizedHangulMieum BMPString ::= {0, 0, 50, 4}

-- parenthesizedHangulPieup BMPString ::= {0, 0, 50, 5}

-- parenthesizedHangulSios BMPString ::= {0, 0, 50, 6}

-- parenthesizedHangulIeung BMPString ::= {0, 0, 50, 7}

-- parenthesizedHangulCieuc BMPString ::= {0, 0, 50, 8}

-- parenthesizedHangulChieuch BMPString ::= {0, 0, 50, 9}

-- parenthesizedHangulKhieukh BMPString ::= {0, 0, 50, 10}

-- parenthesizedHangulThieuth BMPString ::= {0, 0, 50, 11}

-- parenthesizedHangulPhieuph BMPString ::= {0, 0, 50, 12}

-- parenthesizedHangulHieuh BMPString ::= {0, 0, 50, 13}

-- parenthesizedHangulKiyeokA BMPString ::= {0, 0, 50, 14}

-- parenthesizedHangulNieunA BMPString ::= {0, 0, 50, 15}

-- parenthesizedHangulTikeutA BMPString ::= {0, 0, 50, 16}

-- parenthesizedHangulRieulA BMPString ::= {0, 0, 50, 17}

-- parenthesizedHangulMieumA BMPString ::= {0, 0, 50, 18}

-- parenthesizedHangulPieupA BMPString ::= {0, 0, 50, 19}

-- parenthesizedHangulSiosA BMPString ::= {0, 0, 50, 20}

-- parenthesizedHangulIeungA BMPString ::= {0, 0, 50, 21}

-- parenthesizedHangulCieucA BMPString ::= {0, 0, 50, 22}

-- parenthesizedHangulChieuchA BMPString ::= {0, 0, 50, 23}

-- parenthesizedHangulKhieukhA BMPString ::= {0, 0, 50, 24}

-- parenthesizedHangulThieuthA BMPString ::= {0, 0, 50, 25}

-- parenthesizedHangulPhieuphA BMPString ::= {0, 0, 50, 26}

-- parenthesizedHangulHieuhA BMPString ::= {0, 0, 50, 27}

-- parenthesizedHangulCieucU BMPString ::= {0, 0, 50, 28}

-- parenthesizedIdeographOne BMPString ::= {0, 0, 50, 32}

-- parenthesizedIdeographTwo BMPString ::= {0, 0, 50, 33}

-- parenthesizedIdeographThree BMPString ::= {0, 0, 50, 34}

-- parenthesizedIdeographFour BMPString ::= {0, 0, 50, 35}

-- parenthesizedIdeographFive BMPString ::= {0, 0, 50, 36}

-- parenthesizedIdeographSix BMPString ::= {0, 0, 50, 37}

-- parenthesizedIdeographSeven BMPString ::= {0, 0, 50, 38}

-- parenthesizedIdeographEight BMPString ::= {0, 0, 50, 39}

-- parenthesizedIdeographNine BMPString ::= {0, 0, 50, 40}

-- parenthesizedIdeographTen BMPString ::= {0, 0, 50, 41}

-- parenthesizedIdeographMoon BMPString ::= {0, 0, 50, 42}

-- parenthesizedIdeographFire BMPString ::= {0, 0, 50, 43}

-- parenthesizedIdeographWater BMPString ::= {0, 0, 50, 44}

-- parenthesizedIdeographWood BMPString ::= {0, 0, 50, 45}

-- parenthesizedIdeographMetal BMPString ::= {0, 0, 50, 46}

-- parenthesizedIdeographEarth BMPString ::= {0, 0, 50, 47}

-- parenthesizedIdeographSun BMPString ::= {0, 0, 50, 48}

-- parenthesizedIdeographStock BMPString ::= {0, 0, 50, 49}

-- parenthesizedIdeographHave BMPString ::= {0, 0, 50, 50}

-- parenthesizedIdeographSociety BMPString ::= {0, 0, 50, 51}

-- parenthesizedIdeographName BMPString ::= {0, 0, 50, 52}

-- parenthesizedIdeographSpecial BMPString ::= {0, 0, 50, 53}

-- parenthesizedIdeographFinancial BMPString ::= {0, 0, 50, 54}

-- parenthesizedIdeographCongratulation BMPString ::= {0, 0, 50, 55}

-- parenthesizedIdeographLabor BMPString ::= {0, 0, 50, 56}

-- parenthesizedIdeographRepresent BMPString ::= {0, 0, 50, 57}

-- parenthesizedIdeographCall BMPString ::= {0, 0, 50, 58}

-- parenthesizedIdeographStudy BMPString ::= {0, 0, 50, 59}

-- parenthesizedIdeographSupervise BMPString ::= {0, 0, 50, 60}

-- parenthesizedIdeographEnterprise BMPString ::= {0, 0, 50, 61}

-- parenthesizedIdeographResource BMPString ::= {0, 0, 50, 62}

-- parenthesizedIdeographAlliance BMPString ::= {0, 0, 50, 63}

-- parenthesizedIdeographFestival BMPString ::= {0, 0, 50, 64}

-- parenthesizedIdeographRest BMPString ::= {0, 0, 50, 65}

-- parenthesizedIdeographSelf BMPString ::= {0, 0, 50, 66}

-- parenthesizedIdeographReach BMPString ::= {0, 0, 50, 67}

-- circledNumberTwentyOne BMPString ::= {0, 0, 50, 81}

-- circledNumberTwentyTwo BMPString ::= {0, 0, 50, 82}

-- circledNumberTwentyThree BMPString ::= {0, 0, 50, 83}

-- circledNumberTwentyFour BMPString ::= {0, 0, 50, 84}

-- circledNumberTwentyFive BMPString ::= {0, 0, 50, 85}

-- circledNumberTwentySix BMPString ::= {0, 0, 50, 86}

-- circledNumberTwentySeven BMPString ::= {0, 0, 50, 87}

-- circledNumberTwentyEight BMPString ::= {0, 0, 50, 88}

-- circledNumberTwentyNine BMPString ::= {0, 0, 50, 89}

-- circledNumberThirty BMPString ::= {0, 0, 50, 90}

-- circledNumberThirtyOne BMPString ::= {0, 0, 50, 91}

-- circledNumberThirtyTwo BMPString ::= {0, 0, 50, 92}

-- circledNumberThirtyThree BMPString ::= {0, 0, 50, 93}

-- circledNumberThirtyFour BMPString ::= {0, 0, 50, 94}

-- circledNumberThirtyFive BMPString ::= {0, 0, 50, 95}

-- circledHangulKiyeok BMPString ::= {0, 0, 50, 96}

-- circledHangulNieun BMPString ::= {0, 0, 50, 97}

-- circledHangulTikeut BMPString ::= {0, 0, 50, 98}

-- circledHangulRieul BMPString ::= {0, 0, 50, 99}

-- circledHangulMieum BMPString ::= {0, 0, 50, 100}

-- circledHangulPieup BMPString ::= {0, 0, 50, 101}

-- circledHangulSios BMPString ::= {0, 0, 50, 102}

-- circledHangulIeung BMPString ::= {0, 0, 50, 103}

-- circledHangulCieuc BMPString ::= {0, 0, 50, 104}

-- circledHangulChieuch BMPString ::= {0, 0, 50, 105}

-- circledHangulKhieukh BMPString ::= {0, 0, 50, 106}

-- circledHangulThieuth BMPString ::= {0, 0, 50, 107}

-- circledHangulPhieuph BMPString ::= {0, 0, 50, 108}

-- circledHangulHieuh BMPString ::= {0, 0, 50, 109}

-- circledHangulKiyeokA BMPString ::= {0, 0, 50, 110}

-- circledHangulNieunA BMPString ::= {0, 0, 50, 111}

-- circledHangulTikeutA BMPString ::= {0, 0, 50, 112}

-- circledHangulRieulA BMPString ::= {0, 0, 50, 113}

-- circledHangulMieumA BMPString ::= {0, 0, 50, 114}

-- circledHangulPieupA BMPString ::= {0, 0, 50, 115}

-- circledHangulSiosA BMPString ::= {0, 0, 50, 116}

-- circledHangulIeungA BMPString ::= {0, 0, 50, 117}

-- circledHangulCieucA BMPString ::= {0, 0, 50, 118}

-- circledHangulChieuchA BMPString ::= {0, 0, 50, 119}

-- circledHangulKhieukhA BMPString ::= {0, 0, 50, 120}

-- circledHangulThieuthA BMPString ::= {0, 0, 50, 121}

-- circledHangulPhieuphA BMPString ::= {0, 0, 50, 122}

-- circledHangulHieuhA BMPString ::= {0, 0, 50, 123}

-- koreanStandardSymbol BMPString ::= {0, 0, 50, 127}

-- circledIdeographOne BMPString ::= {0, 0, 50, 128}

-- circledIdeographTwo BMPString ::= {0, 0, 50, 129}

-- circledIdeographThree BMPString ::= {0, 0, 50, 130}

-- circledIdeographFour BMPString ::= {0, 0, 50, 131}

-- circledIdeographFive BMPString ::= {0, 0, 50, 132}

-- circledIdeographSix BMPString ::= {0, 0, 50, 133}

-- circledIdeographSeven BMPString ::= {0, 0, 50, 134}

-- circledIdeographEight BMPString ::= {0, 0, 50, 135}

-- circledIdeographNine BMPString ::= {0, 0, 50, 136}

-- circledIdeographTen BMPString ::= {0, 0, 50, 137}

-- circledIdeographMoon BMPString ::= {0, 0, 50, 138}

-- circledIdeographFire BMPString ::= {0, 0, 50, 139}

-- circledIdeographWater BMPString ::= {0, 0, 50, 140}

-- circledIdeographWood BMPString ::= {0, 0, 50, 141}

-- circledIdeographMetal BMPString ::= {0, 0, 50, 142}

-- circledIdeographEarth BMPString ::= {0, 0, 50, 143}

-- circledIdeographSun BMPString ::= {0, 0, 50, 144}

-- circledIdeographStock BMPString ::= {0, 0, 50, 145}

-- circledIdeographHave BMPString ::= {0, 0, 50, 146}

-- circledIdeographSociety BMPString ::= {0, 0, 50, 147}

-- circledIdeographName BMPString ::= {0, 0, 50, 148}

-- circledIdeographSpecial BMPString ::= {0, 0, 50, 149}

-- circledIdeographFinancial BMPString ::= {0, 0, 50, 150}

-- circledIdeographCongratulation BMPString ::= {0, 0, 50, 151}

-- circledIdeographLabor BMPString ::= {0, 0, 50, 152}

-- circledIdeographSecret BMPString ::= {0, 0, 50, 153}

-- circledIdeographMale BMPString ::= {0, 0, 50, 154}

-- circledIdeographFemale BMPString ::= {0, 0, 50, 155}

-- circledIdeographSuitable BMPString ::= {0, 0, 50, 156}

-- circledIdeographExcellent BMPString ::= {0, 0, 50, 157}

-- circledIdeographPrint BMPString ::= {0, 0, 50, 158}

-- circledIdeographAttention BMPString ::= {0, 0, 50, 159}

-- circledIdeographItem BMPString ::= {0, 0, 50, 160}

-- circledIdeographRest BMPString ::= {0, 0, 50, 161}

-- circledIdeographCopy BMPString ::= {0, 0, 50, 162}

-- circledIdeographCorrect BMPString ::= {0, 0, 50, 163}

-- circledIdeographHigh BMPString ::= {0, 0, 50, 164}

-- circledIdeographCentre BMPString ::= {0, 0, 50, 165}

-- circledIdeographLow BMPString ::= {0, 0, 50, 166}

-- circledIdeographLeft BMPString ::= {0, 0, 50, 167}

-- circledIdeographRight BMPString ::= {0, 0, 50, 168}

-- circledIdeographMedicine BMPString ::= {0, 0, 50, 169}

-- circledIdeographReligion BMPString ::= {0, 0, 50, 170}

-- circledIdeographStudy BMPString ::= {0, 0, 50, 171}

-- circledIdeographSupervise BMPString ::= {0, 0, 50, 172}

-- circledIdeographEnterprise BMPString ::= {0, 0, 50, 173}

-- circledIdeographResource BMPString ::= {0, 0, 50, 174}

-- circledIdeographAlliance BMPString ::= {0, 0, 50, 175}

-- circledIdeographNight BMPString ::= {0, 0, 50, 176}

-- circledNumberThirtySix BMPString ::= {0, 0, 50, 177}

-- circledNumberThirtySeven BMPString ::= {0, 0, 50, 178}

-- circledNumberThirtyEight BMPString ::= {0, 0, 50, 179}

-- circledNumberThirtyNine BMPString ::= {0, 0, 50, 180}

-- circledNumberForty BMPString ::= {0, 0, 50, 181}

-- circledNumberFortyOne BMPString ::= {0, 0, 50, 182}

-- circledNumberFortyTwo BMPString ::= {0, 0, 50, 183}

-- circledNumberFortyThree BMPString ::= {0, 0, 50, 184}

-- circledNumberFortyFour BMPString ::= {0, 0, 50, 185}

-- circledNumberFortyFive BMPString ::= {0, 0, 50, 186}

-- circledNumberFortySix BMPString ::= {0, 0, 50, 187}

-- circledNumberFortySeven BMPString ::= {0, 0, 50, 188}

-- circledNumberFortyEight BMPString ::= {0, 0, 50, 189}

-- circledNumberFortyNine BMPString ::= {0, 0, 50, 190}

-- circledNumberFifty BMPString ::= {0, 0, 50, 191}

-- ideographicTelegraphSymbolForJanuary BMPString ::= {0, 0, 50, 192}

-- ideographicTelegraphSymbolForFebruary BMPString ::= {0, 0, 50, 193}

-- ideographicTelegraphSymbolForMarch BMPString ::= {0, 0, 50, 194}

-- ideographicTelegraphSymbolForApril BMPString ::= {0, 0, 50, 195}

-- ideographicTelegraphSymbolForMay BMPString ::= {0, 0, 50, 196}

-- ideographicTelegraphSymbolForJune BMPString ::= {0, 0, 50, 197}

-- ideographicTelegraphSymbolForJuly BMPString ::= {0, 0, 50, 198}

-- ideographicTelegraphSymbolForAugust BMPString ::= {0, 0, 50, 199}

-- ideographicTelegraphSymbolForSeptember BMPString ::= {0, 0, 50, 200}

-- ideographicTelegraphSymbolForOctober BMPString ::= {0, 0, 50, 201}

-- ideographicTelegraphSymbolForNovember BMPString ::= {0, 0, 50, 202}

-- ideographicTelegraphSymbolForDecember BMPString ::= {0, 0, 50, 203}

-- circledKatakanaA BMPString ::= {0, 0, 50, 208}

-- circledKatakanaI BMPString ::= {0, 0, 50, 209}

-- circledKatakanaU BMPString ::= {0, 0, 50, 210}

-- circledKatakanaE BMPString ::= {0, 0, 50, 211}

-- circledKatakanaO BMPString ::= {0, 0, 50, 212}

-- circledKatakanaKa BMPString ::= {0, 0, 50, 213}

-- circledKatakanaKi BMPString ::= {0, 0, 50, 214}

-- circledKatakanaKu BMPString ::= {0, 0, 50, 215}

-- circledKatakanaKe BMPString ::= {0, 0, 50, 216}

-- circledKatakanaKo BMPString ::= {0, 0, 50, 217}

-- circledKatakanaSa BMPString ::= {0, 0, 50, 218}

-- circledKatakanaSi BMPString ::= {0, 0, 50, 219}

-- circledKatakanaSu BMPString ::= {0, 0, 50, 220}

-- circledKatakanaSe BMPString ::= {0, 0, 50, 221}

-- circledKatakanaSo BMPString ::= {0, 0, 50, 222}

-- circledKatakanaTa BMPString ::= {0, 0, 50, 223}

-- circledKatakanaTi BMPString ::= {0, 0, 50, 224}

-- circledKatakanaTu BMPString ::= {0, 0, 50, 225}

-- circledKatakanaTe BMPString ::= {0, 0, 50, 226}

-- circledKatakanaTo BMPString ::= {0, 0, 50, 227}

-- circledKatakanaNa BMPString ::= {0, 0, 50, 228}

-- circledKatakanaNi BMPString ::= {0, 0, 50, 229}

-- circledKatakanaNu BMPString ::= {0, 0, 50, 230}

-- circledKatakanaNe BMPString ::= {0, 0, 50, 231}

-- circledKatakanaNo BMPString ::= {0, 0, 50, 232}

-- circledKatakanaHa BMPString ::= {0, 0, 50, 233}

-- circledKatakanaHi BMPString ::= {0, 0, 50, 234}

-- circledKatakanaHu BMPString ::= {0, 0, 50, 235}

-- circledKatakanaHe BMPString ::= {0, 0, 50, 236}

-- circledKatakanaHo BMPString ::= {0, 0, 50, 237}

-- circledKatakanaMa BMPString ::= {0, 0, 50, 238}

-- circledKatakanaMi BMPString ::= {0, 0, 50, 239}

-- circledKatakanaMu BMPString ::= {0, 0, 50, 240}

-- circledKatakanaMe BMPString ::= {0, 0, 50, 241}

-- circledKatakanaMo BMPString ::= {0, 0, 50, 242}

-- circledKatakanaYa BMPString ::= {0, 0, 50, 243}

-- circledKatakanaYu BMPString ::= {0, 0, 50, 244}

-- circledKatakanaYo BMPString ::= {0, 0, 50, 245}

-- circledKatakanaRa BMPString ::= {0, 0, 50, 246}

-- circledKatakanaRi BMPString ::= {0, 0, 50, 247}

-- circledKatakanaRu BMPString ::= {0, 0, 50, 248}

-- circledKatakanaRe BMPString ::= {0, 0, 50, 249}

-- circledKatakanaRo BMPString ::= {0, 0, 50, 250}

-- circledKatakanaWa BMPString ::= {0, 0, 50, 251}

-- circledKatakanaWi BMPString ::= {0, 0, 50, 252}

-- circledKatakanaWe BMPString ::= {0, 0, 50, 253}

-- circledKatakanaWo BMPString ::= {0, 0, 50, 254}

-- squareApaato BMPString ::= {0, 0, 51, 0}

-- squareAruhua BMPString ::= {0, 0, 51, 1}

-- squareAnpea BMPString ::= {0, 0, 51, 2}

-- squareAaru BMPString ::= {0, 0, 51, 3}

-- squareIningu BMPString ::= {0, 0, 51, 4}

-- squareInti BMPString ::= {0, 0, 51, 5}

-- squareUon BMPString ::= {0, 0, 51, 6}

-- squareEsukuudo BMPString ::= {0, 0, 51, 7}

-- squareEekaa BMPString ::= {0, 0, 51, 8}

-- squareOnsu BMPString ::= {0, 0, 51, 9}

-- squareOomu BMPString ::= {0, 0, 51, 10}

-- squareKairi BMPString ::= {0, 0, 51, 11}

-- squareKaratto BMPString ::= {0, 0, 51, 12}

-- squareKarorii BMPString ::= {0, 0, 51, 13}

-- squareGaron BMPString ::= {0, 0, 51, 14}

-- squareGanma BMPString ::= {0, 0, 51, 15}

-- squareGiga BMPString ::= {0, 0, 51, 16}

-- squareGinii BMPString ::= {0, 0, 51, 17}

-- squareKyurii BMPString ::= {0, 0, 51, 18}

-- squareGirudaa BMPString ::= {0, 0, 51, 19}

-- squareKiro BMPString ::= {0, 0, 51, 20}

-- squareKiroguramu BMPString ::= {0, 0, 51, 21}

-- squareKiromeetoru BMPString ::= {0, 0, 51, 22}

-- squareKirowatto BMPString ::= {0, 0, 51, 23}

-- squareGuramu BMPString ::= {0, 0, 51, 24}

-- squareGuramuton BMPString ::= {0, 0, 51, 25}

-- squareKuruzeiro BMPString ::= {0, 0, 51, 26}

-- squareKuroone BMPString ::= {0, 0, 51, 27}

-- squareKeesu BMPString ::= {0, 0, 51, 28}

-- squareKoruna BMPString ::= {0, 0, 51, 29}

-- squareKoopo BMPString ::= {0, 0, 51, 30}

-- squareSaikuru BMPString ::= {0, 0, 51, 31}

-- squareSantiimu BMPString ::= {0, 0, 51, 32}

-- squareSiringu BMPString ::= {0, 0, 51, 33}

-- squareSenti BMPString ::= {0, 0, 51, 34}

-- squareSento BMPString ::= {0, 0, 51, 35}

-- squareDaasu BMPString ::= {0, 0, 51, 36}

-- squareDesi BMPString ::= {0, 0, 51, 37}

-- squareDoru BMPString ::= {0, 0, 51, 38}

-- squareTon BMPString ::= {0, 0, 51, 39}

-- squareNano BMPString ::= {0, 0, 51, 40}

-- squareNotto BMPString ::= {0, 0, 51, 41}

-- squareHaitu BMPString ::= {0, 0, 51, 42}

-- squarePaasento BMPString ::= {0, 0, 51, 43}

-- squarePaatu BMPString ::= {0, 0, 51, 44}

-- squareBaareru BMPString ::= {0, 0, 51, 45}

-- squarePiasutoru BMPString ::= {0, 0, 51, 46}

-- squarePikuru BMPString ::= {0, 0, 51, 47}

-- squarePiko BMPString ::= {0, 0, 51, 48}

-- squareBiru BMPString ::= {0, 0, 51, 49}

-- squareHuaraddo BMPString ::= {0, 0, 51, 50}

-- squareHuiito BMPString ::= {0, 0, 51, 51}

-- squareBussyeru BMPString ::= {0, 0, 51, 52}

-- squareHuran BMPString ::= {0, 0, 51, 53}

-- squareHekutaaru BMPString ::= {0, 0, 51, 54}

-- squarePeso BMPString ::= {0, 0, 51, 55}

-- squarePenihi BMPString ::= {0, 0, 51, 56}

-- squareHerutu BMPString ::= {0, 0, 51, 57}

-- squarePensu BMPString ::= {0, 0, 51, 58}

-- squarePeezi BMPString ::= {0, 0, 51, 59}

-- squareBeeta BMPString ::= {0, 0, 51, 60}

-- squarePointo BMPString ::= {0, 0, 51, 61}

-- squareBoruto BMPString ::= {0, 0, 51, 62}

-- squareHon BMPString ::= {0, 0, 51, 63}

-- squarePondo BMPString ::= {0, 0, 51, 64}

-- squareHooru BMPString ::= {0, 0, 51, 65}

-- squareHoon BMPString ::= {0, 0, 51, 66}

-- squareMaikuro BMPString ::= {0, 0, 51, 67}

-- squareMairu BMPString ::= {0, 0, 51, 68}

-- squareMahha BMPString ::= {0, 0, 51, 69}

-- squareMaruku BMPString ::= {0, 0, 51, 70}

-- squareMansyon BMPString ::= {0, 0, 51, 71}

-- squareMikuron BMPString ::= {0, 0, 51, 72}

-- squareMiri BMPString ::= {0, 0, 51, 73}

-- squareMiribaaru BMPString ::= {0, 0, 51, 74}

-- squareMega BMPString ::= {0, 0, 51, 75}

-- squareMegaton BMPString ::= {0, 0, 51, 76}

-- squareMeetoru BMPString ::= {0, 0, 51, 77}

-- squareYaado BMPString ::= {0, 0, 51, 78}

-- squareYaaru BMPString ::= {0, 0, 51, 79}

-- squareYuan BMPString ::= {0, 0, 51, 80}

-- squareRittoru BMPString ::= {0, 0, 51, 81}

-- squareRira BMPString ::= {0, 0, 51, 82}

-- squareRupii BMPString ::= {0, 0, 51, 83}

-- squareRuuburu BMPString ::= {0, 0, 51, 84}

-- squareRemu BMPString ::= {0, 0, 51, 85}

-- squareRentogen BMPString ::= {0, 0, 51, 86}

-- squareWatto BMPString ::= {0, 0, 51, 87}

-- ideographicTelegraphSymbolForHourZero BMPString ::= {0, 0, 51, 88}

-- ideographicTelegraphSymbolForHourOne BMPString ::= {0, 0, 51, 89}

-- ideographicTelegraphSymbolForHourTwo BMPString ::= {0, 0, 51, 90}

-- ideographicTelegraphSymbolForHourThree BMPString ::= {0, 0, 51, 91}

-- ideographicTelegraphSymbolForHourFour BMPString ::= {0, 0, 51, 92}

-- ideographicTelegraphSymbolForHourFive BMPString ::= {0, 0, 51, 93}

-- ideographicTelegraphSymbolForHourSix BMPString ::= {0, 0, 51, 94}

-- ideographicTelegraphSymbolForHourSeven BMPString ::= {0, 0, 51, 95}

-- ideographicTelegraphSymbolForHourEight BMPString ::= {0, 0, 51, 96}

-- ideographicTelegraphSymbolForHourNine BMPString ::= {0, 0, 51, 97}

-- ideographicTelegraphSymbolForHourTen BMPString ::= {0, 0, 51, 98}

-- ideographicTelegraphSymbolForHourEleven BMPString ::= {0, 0, 51, 99}

-- ideographicTelegraphSymbolForHourTwelve BMPString ::= {0, 0, 51, 100}

-- ideographicTelegraphSymbolForHourThirteen BMPString ::= {0, 0, 51, 101}

-- ideographicTelegraphSymbolForHourFourteen BMPString ::= {0, 0, 51, 102}

-- ideographicTelegraphSymbolForHourFifteen BMPString ::= {0, 0, 51, 103}

-- ideographicTelegraphSymbolForHourSixteen BMPString ::= {0, 0, 51, 104}

-- ideographicTelegraphSymbolForHourSeventeen BMPString ::= {0, 0, 51, 105}

-- ideographicTelegraphSymbolForHourEighteen BMPString ::= {0, 0, 51, 106}

-- ideographicTelegraphSymbolForHourNineteen BMPString ::= {0, 0, 51, 107}

-- ideographicTelegraphSymbolForHourTwenty BMPString ::= {0, 0, 51, 108}

-- ideographicTelegraphSymbolForHourTwenty-one BMPString ::= {0, 0, 51, 109}

-- ideographicTelegraphSymbolForHourTwenty-two BMPString ::= {0, 0, 51, 110}

-- ideographicTelegraphSymbolForHourTwenty-three BMPString ::= {0, 0, 51, 111}

-- ideographicTelegraphSymbolForHourTwenty-four BMPString ::= {0, 0, 51, 112}

-- squareHpa BMPString ::= {0, 0, 51, 113}

-- squareDa BMPString ::= {0, 0, 51, 114}

-- squareAu BMPString ::= {0, 0, 51, 115}

-- squareBar BMPString ::= {0, 0, 51, 116}

-- squareOv BMPString ::= {0, 0, 51, 117}

-- squarePc BMPString ::= {0, 0, 51, 118}

-- squareEraNameHeisei BMPString ::= {0, 0, 51, 123}

-- squareEraNameSyouwa BMPString ::= {0, 0, 51, 124}

-- squareEraNameTaisyou BMPString ::= {0, 0, 51, 125}

-- squareEraNameMeizi BMPString ::= {0, 0, 51, 126}

-- squareCorporation BMPString ::= {0, 0, 51, 127}

-- squarePaAmps BMPString ::= {0, 0, 51, 128}

-- squareNa BMPString ::= {0, 0, 51, 129}

-- squareMuA BMPString ::= {0, 0, 51, 130}

-- squareMa BMPString ::= {0, 0, 51, 131}

-- squareKa BMPString ::= {0, 0, 51, 132}

-- squareKb BMPString ::= {0, 0, 51, 133}

-- squareMb BMPString ::= {0, 0, 51, 134}

-- squareGb BMPString ::= {0, 0, 51, 135}

-- squareCal BMPString ::= {0, 0, 51, 136}

-- squareKcal BMPString ::= {0, 0, 51, 137}

-- squarePf BMPString ::= {0, 0, 51, 138}

-- squareNf BMPString ::= {0, 0, 51, 139}

-- squareMuF BMPString ::= {0, 0, 51, 140}

-- squareMuG BMPString ::= {0, 0, 51, 141}

-- squareMg BMPString ::= {0, 0, 51, 142}

-- squareKg BMPString ::= {0, 0, 51, 143}

-- squareHz BMPString ::= {0, 0, 51, 144}

-- squareKhz BMPString ::= {0, 0, 51, 145}

-- squareMhz BMPString ::= {0, 0, 51, 146}

-- squareGhz BMPString ::= {0, 0, 51, 147}

-- squareThz BMPString ::= {0, 0, 51, 148}

-- squareMuL BMPString ::= {0, 0, 51, 149}

-- squareMl BMPString ::= {0, 0, 51, 150}

-- squareDl BMPString ::= {0, 0, 51, 151}

-- squareKl BMPString ::= {0, 0, 51, 152}

-- squareFm BMPString ::= {0, 0, 51, 153}

-- squareNm BMPString ::= {0, 0, 51, 154}

-- squareMuM BMPString ::= {0, 0, 51, 155}

-- squareMm BMPString ::= {0, 0, 51, 156}

-- squareCm BMPString ::= {0, 0, 51, 157}

-- squareKm BMPString ::= {0, 0, 51, 158}

-- squareMmSquared BMPString ::= {0, 0, 51, 159}

-- squareCmSquared BMPString ::= {0, 0, 51, 160}

-- squareMSquared BMPString ::= {0, 0, 51, 161}

-- squareKmSquared BMPString ::= {0, 0, 51, 162}

-- squareMmCubed BMPString ::= {0, 0, 51, 163}

-- squareCmCubed BMPString ::= {0, 0, 51, 164}

-- squareMCubed BMPString ::= {0, 0, 51, 165}

-- squareKmCubed BMPString ::= {0, 0, 51, 166}

-- squareMOverS BMPString ::= {0, 0, 51, 167}

-- squareMOverSSquared BMPString ::= {0, 0, 51, 168}

-- squarePa BMPString ::= {0, 0, 51, 169}

-- squareKpa BMPString ::= {0, 0, 51, 170}

-- squareMpa BMPString ::= {0, 0, 51, 171}

-- squareGpa BMPString ::= {0, 0, 51, 172}

-- squareRad BMPString ::= {0, 0, 51, 173}

-- squareRadOverS BMPString ::= {0, 0, 51, 174}

-- squareRadOverSSquared BMPString ::= {0, 0, 51, 175}

-- squarePs BMPString ::= {0, 0, 51, 176}

-- squareNs BMPString ::= {0, 0, 51, 177}

-- squareMuS BMPString ::= {0, 0, 51, 178}

-- squareMs BMPString ::= {0, 0, 51, 179}

-- squarePv BMPString ::= {0, 0, 51, 180}

-- squareNv BMPString ::= {0, 0, 51, 181}

-- squareMuV BMPString ::= {0, 0, 51, 182}

-- squareMv BMPString ::= {0, 0, 51, 183}

-- squareKv BMPString ::= {0, 0, 51, 184}

-- squareMvMega BMPString ::= {0, 0, 51, 185}

-- squarePw BMPString ::= {0, 0, 51, 186}

-- squareNw BMPString ::= {0, 0, 51, 187}

-- squareMuW BMPString ::= {0, 0, 51, 188}

-- squareMw BMPString ::= {0, 0, 51, 189}

-- squareKw BMPString ::= {0, 0, 51, 190}

-- squareMwMega BMPString ::= {0, 0, 51, 191}

-- squareKOhm BMPString ::= {0, 0, 51, 192}

-- squareMOhm BMPString ::= {0, 0, 51, 193}

-- squareAm BMPString ::= {0, 0, 51, 194}

-- squareBq BMPString ::= {0, 0, 51, 195}

-- squareCc BMPString ::= {0, 0, 51, 196}

-- squareCd BMPString ::= {0, 0, 51, 197}

-- squareCOverKg BMPString ::= {0, 0, 51, 198}

-- squareCo BMPString ::= {0, 0, 51, 199}

-- squareDb BMPString ::= {0, 0, 51, 200}

-- squareGy BMPString ::= {0, 0, 51, 201}

-- squareHa BMPString ::= {0, 0, 51, 202}

-- squareHp BMPString ::= {0, 0, 51, 203}

-- squareIn BMPString ::= {0, 0, 51, 204}

-- squareKk BMPString ::= {0, 0, 51, 205}

-- squareKmCapital BMPString ::= {0, 0, 51, 206}

-- squareKt BMPString ::= {0, 0, 51, 207}

-- squareLm BMPString ::= {0, 0, 51, 208}

-- squareLn BMPString ::= {0, 0, 51, 209}

-- squareLog BMPString ::= {0, 0, 51, 210}

-- squareLx BMPString ::= {0, 0, 51, 211}

-- squareMbSmall BMPString ::= {0, 0, 51, 212}

-- squareMil BMPString ::= {0, 0, 51, 213}

-- squareMol BMPString ::= {0, 0, 51, 214}

-- squarePh BMPString ::= {0, 0, 51, 215}

-- squarePm BMPString ::= {0, 0, 51, 216}

-- squarePpm BMPString ::= {0, 0, 51, 217}

-- squarePr BMPString ::= {0, 0, 51, 218}

-- squareSr BMPString ::= {0, 0, 51, 219}

-- squareSv BMPString ::= {0, 0, 51, 220}

-- squareWb BMPString ::= {0, 0, 51, 221}

-- ideographicTelegraphSymbolForDayOne BMPString ::= {0, 0, 51, 224}

-- ideographicTelegraphSymbolForDayTwo BMPString ::= {0, 0, 51, 225}

-- ideographicTelegraphSymbolForDayThree BMPString ::= {0, 0, 51, 226}

-- ideographicTelegraphSymbolForDayFour BMPString ::= {0, 0, 51, 227}

-- ideographicTelegraphSymbolForDayFive BMPString ::= {0, 0, 51, 228}

-- ideographicTelegraphSymbolForDaySix BMPString ::= {0, 0, 51, 229}

-- ideographicTelegraphSymbolForDaySeven BMPString ::= {0, 0, 51, 230}

-- ideographicTelegraphSymbolForDayEight BMPString ::= {0, 0, 51, 231}

-- ideographicTelegraphSymbolForDayNine BMPString ::= {0, 0, 51, 232}

-- ideographicTelegraphSymbolForDayTen BMPString ::= {0, 0, 51, 233}

-- ideographicTelegraphSymbolForDayEleven BMPString ::= {0, 0, 51, 234}

-- ideographicTelegraphSymbolForDayTwelve BMPString ::= {0, 0, 51, 235}

-- ideographicTelegraphSymbolForDayThirteen BMPString ::= {0, 0, 51, 236}

-- ideographicTelegraphSymbolForDayFourteen BMPString ::= {0, 0, 51, 237}

-- ideographicTelegraphSymbolForDayFifteen BMPString ::= {0, 0, 51, 238}

-- ideographicTelegraphSymbolForDaySixteen BMPString ::= {0, 0, 51, 239}

-- ideographicTelegraphSymbolForDaySeventeen BMPString ::= {0, 0, 51, 240}

-- ideographicTelegraphSymbolForDayEighteen BMPString ::= {0, 0, 51, 241}

-- ideographicTelegraphSymbolForDayNineteen BMPString ::= {0, 0, 51, 242}

-- ideographicTelegraphSymbolForDayTwenty BMPString ::= {0, 0, 51, 243}

-- ideographicTelegraphSymbolForDayTwenty-one BMPString ::= {0, 0, 51, 244}

-- ideographicTelegraphSymbolForDayTwenty-two BMPString ::= {0, 0, 51, 245}

-- ideographicTelegraphSymbolForDayTwenty-three BMPString ::= {0, 0, 51, 246}

-- ideographicTelegraphSymbolForDayTwenty-four BMPString ::= {0, 0, 51, 247}

-- ideographicTelegraphSymbolForDayTwenty-five BMPString ::= {0, 0, 51, 248}

-- ideographicTelegraphSymbolForDayTwenty-six BMPString ::= {0, 0, 51, 249}

-- ideographicTelegraphSymbolForDayTwenty-seven BMPString ::= {0, 0, 51, 250}

-- ideographicTelegraphSymbolForDayTwenty-eight BMPString ::= {0, 0, 51, 251}

-- ideographicTelegraphSymbolForDayTwenty-nine BMPString ::= {0, 0, 51, 252}

-- ideographicTelegraphSymbolForDayThirty BMPString ::= {0, 0, 51, 253}

-- ideographicTelegraphSymbolForDayThirty-one BMPString ::= {0, 0, 51, 254}

-- yiSyllableIt BMPString ::= {0, 0, 160, 0}

-- yiSyllableIx BMPString ::= {0, 0, 160, 1}

-- yiSyllableI BMPString ::= {0, 0, 160, 2}

-- yiSyllableIp BMPString ::= {0, 0, 160, 3}

-- yiSyllableIet BMPString ::= {0, 0, 160, 4}

-- yiSyllableIex BMPString ::= {0, 0, 160, 5}

-- yiSyllableIe BMPString ::= {0, 0, 160, 6}

-- yiSyllableIep BMPString ::= {0, 0, 160, 7}

-- yiSyllableAt BMPString ::= {0, 0, 160, 8}

-- yiSyllableAx BMPString ::= {0, 0, 160, 9}

-- yiSyllableA BMPString ::= {0, 0, 160, 10}

-- yiSyllableAp BMPString ::= {0, 0, 160, 11}

-- yiSyllableUox BMPString ::= {0, 0, 160, 12}

-- yiSyllableUo BMPString ::= {0, 0, 160, 13}

-- yiSyllableUop BMPString ::= {0, 0, 160, 14}

-- yiSyllableOt BMPString ::= {0, 0, 160, 15}

-- yiSyllableOx BMPString ::= {0, 0, 160, 16}

-- yiSyllableO BMPString ::= {0, 0, 160, 17}

-- yiSyllableOp BMPString ::= {0, 0, 160, 18}

-- yiSyllableEx BMPString ::= {0, 0, 160, 19}

-- yiSyllableE BMPString ::= {0, 0, 160, 20}

-- yiSyllableWu BMPString ::= {0, 0, 160, 21}

-- yiSyllableBit BMPString ::= {0, 0, 160, 22}

-- yiSyllableBix BMPString ::= {0, 0, 160, 23}

-- yiSyllableBi BMPString ::= {0, 0, 160, 24}

-- yiSyllableBip BMPString ::= {0, 0, 160, 25}

-- yiSyllableBiet BMPString ::= {0, 0, 160, 26}

-- yiSyllableBiex BMPString ::= {0, 0, 160, 27}

-- yiSyllableBie BMPString ::= {0, 0, 160, 28}

-- yiSyllableBiep BMPString ::= {0, 0, 160, 29}

-- yiSyllableBat BMPString ::= {0, 0, 160, 30}

-- yiSyllableBax BMPString ::= {0, 0, 160, 31}

-- yiSyllableBa BMPString ::= {0, 0, 160, 32}

-- yiSyllableBap BMPString ::= {0, 0, 160, 33}

-- yiSyllableBuox BMPString ::= {0, 0, 160, 34}

-- yiSyllableBuo BMPString ::= {0, 0, 160, 35}

-- yiSyllableBuop BMPString ::= {0, 0, 160, 36}

-- yiSyllableBot BMPString ::= {0, 0, 160, 37}

-- yiSyllableBox BMPString ::= {0, 0, 160, 38}

-- yiSyllableBo BMPString ::= {0, 0, 160, 39}

-- yiSyllableBop BMPString ::= {0, 0, 160, 40}

-- yiSyllableBex BMPString ::= {0, 0, 160, 41}

-- yiSyllableBe BMPString ::= {0, 0, 160, 42}

-- yiSyllableBep BMPString ::= {0, 0, 160, 43}

-- yiSyllableBut BMPString ::= {0, 0, 160, 44}

-- yiSyllableBux BMPString ::= {0, 0, 160, 45}

-- yiSyllableBu BMPString ::= {0, 0, 160, 46}

-- yiSyllableBup BMPString ::= {0, 0, 160, 47}

-- yiSyllableBurx BMPString ::= {0, 0, 160, 48}

-- yiSyllableBur BMPString ::= {0, 0, 160, 49}

-- yiSyllableByt BMPString ::= {0, 0, 160, 50}

-- yiSyllableByx BMPString ::= {0, 0, 160, 51}

-- yiSyllableBy BMPString ::= {0, 0, 160, 52}

-- yiSyllableByp BMPString ::= {0, 0, 160, 53}

-- yiSyllableByrx BMPString ::= {0, 0, 160, 54}

-- yiSyllableByr BMPString ::= {0, 0, 160, 55}

-- yiSyllablePit BMPString ::= {0, 0, 160, 56}

-- yiSyllablePix BMPString ::= {0, 0, 160, 57}

-- yiSyllablePi BMPString ::= {0, 0, 160, 58}

-- yiSyllablePip BMPString ::= {0, 0, 160, 59}

-- yiSyllablePiex BMPString ::= {0, 0, 160, 60}

-- yiSyllablePie BMPString ::= {0, 0, 160, 61}

-- yiSyllablePiep BMPString ::= {0, 0, 160, 62}

-- yiSyllablePat BMPString ::= {0, 0, 160, 63}

-- yiSyllablePax BMPString ::= {0, 0, 160, 64}

-- yiSyllablePa BMPString ::= {0, 0, 160, 65}

-- yiSyllablePap BMPString ::= {0, 0, 160, 66}

-- yiSyllablePuox BMPString ::= {0, 0, 160, 67}

-- yiSyllablePuo BMPString ::= {0, 0, 160, 68}

-- yiSyllablePuop BMPString ::= {0, 0, 160, 69}

-- yiSyllablePot BMPString ::= {0, 0, 160, 70}

-- yiSyllablePox BMPString ::= {0, 0, 160, 71}

-- yiSyllablePo BMPString ::= {0, 0, 160, 72}

-- yiSyllablePop BMPString ::= {0, 0, 160, 73}

-- yiSyllablePut BMPString ::= {0, 0, 160, 74}

-- yiSyllablePux BMPString ::= {0, 0, 160, 75}

-- yiSyllablePu BMPString ::= {0, 0, 160, 76}

-- yiSyllablePup BMPString ::= {0, 0, 160, 77}

-- yiSyllablePurx BMPString ::= {0, 0, 160, 78}

-- yiSyllablePur BMPString ::= {0, 0, 160, 79}

-- yiSyllablePyt BMPString ::= {0, 0, 160, 80}

-- yiSyllablePyx BMPString ::= {0, 0, 160, 81}

-- yiSyllablePy BMPString ::= {0, 0, 160, 82}

-- yiSyllablePyp BMPString ::= {0, 0, 160, 83}

-- yiSyllablePyrx BMPString ::= {0, 0, 160, 84}

-- yiSyllablePyr BMPString ::= {0, 0, 160, 85}

-- yiSyllableBbit BMPString ::= {0, 0, 160, 86}

-- yiSyllableBbix BMPString ::= {0, 0, 160, 87}

-- yiSyllableBbi BMPString ::= {0, 0, 160, 88}

-- yiSyllableBbip BMPString ::= {0, 0, 160, 89}

-- yiSyllableBbiet BMPString ::= {0, 0, 160, 90}

-- yiSyllableBbiex BMPString ::= {0, 0, 160, 91}

-- yiSyllableBbie BMPString ::= {0, 0, 160, 92}

-- yiSyllableBbiep BMPString ::= {0, 0, 160, 93}

-- yiSyllableBbat BMPString ::= {0, 0, 160, 94}

-- yiSyllableBbax BMPString ::= {0, 0, 160, 95}

-- yiSyllableBba BMPString ::= {0, 0, 160, 96}

-- yiSyllableBbap BMPString ::= {0, 0, 160, 97}

-- yiSyllableBbuox BMPString ::= {0, 0, 160, 98}

-- yiSyllableBbuo BMPString ::= {0, 0, 160, 99}

-- yiSyllableBbuop BMPString ::= {0, 0, 160, 100}

-- yiSyllableBbot BMPString ::= {0, 0, 160, 101}

-- yiSyllableBbox BMPString ::= {0, 0, 160, 102}

-- yiSyllableBbo BMPString ::= {0, 0, 160, 103}

-- yiSyllableBbop BMPString ::= {0, 0, 160, 104}

-- yiSyllableBbex BMPString ::= {0, 0, 160, 105}

-- yiSyllableBbe BMPString ::= {0, 0, 160, 106}

-- yiSyllableBbep BMPString ::= {0, 0, 160, 107}

-- yiSyllableBbut BMPString ::= {0, 0, 160, 108}

-- yiSyllableBbux BMPString ::= {0, 0, 160, 109}

-- yiSyllableBbu BMPString ::= {0, 0, 160, 110}

-- yiSyllableBbup BMPString ::= {0, 0, 160, 111}

-- yiSyllableBburx BMPString ::= {0, 0, 160, 112}

-- yiSyllableBbur BMPString ::= {0, 0, 160, 113}

-- yiSyllableBbyt BMPString ::= {0, 0, 160, 114}

-- yiSyllableBbyx BMPString ::= {0, 0, 160, 115}

-- yiSyllableBby BMPString ::= {0, 0, 160, 116}

-- yiSyllableBbyp BMPString ::= {0, 0, 160, 117}

-- yiSyllableNbit BMPString ::= {0, 0, 160, 118}

-- yiSyllableNbix BMPString ::= {0, 0, 160, 119}

-- yiSyllableNbi BMPString ::= {0, 0, 160, 120}

-- yiSyllableNbip BMPString ::= {0, 0, 160, 121}

-- yiSyllableNbiex BMPString ::= {0, 0, 160, 122}

-- yiSyllableNbie BMPString ::= {0, 0, 160, 123}

-- yiSyllableNbiep BMPString ::= {0, 0, 160, 124}

-- yiSyllableNbat BMPString ::= {0, 0, 160, 125}

-- yiSyllableNbax BMPString ::= {0, 0, 160, 126}

-- yiSyllableNba BMPString ::= {0, 0, 160, 127}

-- yiSyllableNbap BMPString ::= {0, 0, 160, 128}

-- yiSyllableNbot BMPString ::= {0, 0, 160, 129}

-- yiSyllableNbox BMPString ::= {0, 0, 160, 130}

-- yiSyllableNbo BMPString ::= {0, 0, 160, 131}

-- yiSyllableNbop BMPString ::= {0, 0, 160, 132}

-- yiSyllableNbut BMPString ::= {0, 0, 160, 133}

-- yiSyllableNbux BMPString ::= {0, 0, 160, 134}

-- yiSyllableNbu BMPString ::= {0, 0, 160, 135}

-- yiSyllableNbup BMPString ::= {0, 0, 160, 136}

-- yiSyllableNburx BMPString ::= {0, 0, 160, 137}

-- yiSyllableNbur BMPString ::= {0, 0, 160, 138}

-- yiSyllableNbyt BMPString ::= {0, 0, 160, 139}

-- yiSyllableNbyx BMPString ::= {0, 0, 160, 140}

-- yiSyllableNby BMPString ::= {0, 0, 160, 141}

-- yiSyllableNbyp BMPString ::= {0, 0, 160, 142}

-- yiSyllableNbyrx BMPString ::= {0, 0, 160, 143}

-- yiSyllableNbyr BMPString ::= {0, 0, 160, 144}

-- yiSyllableHmit BMPString ::= {0, 0, 160, 145}

-- yiSyllableHmix BMPString ::= {0, 0, 160, 146}

-- yiSyllableHmi BMPString ::= {0, 0, 160, 147}

-- yiSyllableHmip BMPString ::= {0, 0, 160, 148}

-- yiSyllableHmiex BMPString ::= {0, 0, 160, 149}

-- yiSyllableHmie BMPString ::= {0, 0, 160, 150}

-- yiSyllableHmiep BMPString ::= {0, 0, 160, 151}

-- yiSyllableHmat BMPString ::= {0, 0, 160, 152}

-- yiSyllableHmax BMPString ::= {0, 0, 160, 153}

-- yiSyllableHma BMPString ::= {0, 0, 160, 154}

-- yiSyllableHmap BMPString ::= {0, 0, 160, 155}

-- yiSyllableHmuox BMPString ::= {0, 0, 160, 156}

-- yiSyllableHmuo BMPString ::= {0, 0, 160, 157}

-- yiSyllableHmuop BMPString ::= {0, 0, 160, 158}

-- yiSyllableHmot BMPString ::= {0, 0, 160, 159}

-- yiSyllableHmox BMPString ::= {0, 0, 160, 160}

-- yiSyllableHmo BMPString ::= {0, 0, 160, 161}

-- yiSyllableHmop BMPString ::= {0, 0, 160, 162}

-- yiSyllableHmut BMPString ::= {0, 0, 160, 163}

-- yiSyllableHmux BMPString ::= {0, 0, 160, 164}

-- yiSyllableHmu BMPString ::= {0, 0, 160, 165}

-- yiSyllableHmup BMPString ::= {0, 0, 160, 166}

-- yiSyllableHmurx BMPString ::= {0, 0, 160, 167}

-- yiSyllableHmur BMPString ::= {0, 0, 160, 168}

-- yiSyllableHmyx BMPString ::= {0, 0, 160, 169}

-- yiSyllableHmy BMPString ::= {0, 0, 160, 170}

-- yiSyllableHmyp BMPString ::= {0, 0, 160, 171}

-- yiSyllableHmyrx BMPString ::= {0, 0, 160, 172}

-- yiSyllableHmyr BMPString ::= {0, 0, 160, 173}

-- yiSyllableMit BMPString ::= {0, 0, 160, 174}

-- yiSyllableMix BMPString ::= {0, 0, 160, 175}

-- yiSyllableMi BMPString ::= {0, 0, 160, 176}

-- yiSyllableMip BMPString ::= {0, 0, 160, 177}

-- yiSyllableMiex BMPString ::= {0, 0, 160, 178}

-- yiSyllableMie BMPString ::= {0, 0, 160, 179}

-- yiSyllableMiep BMPString ::= {0, 0, 160, 180}

-- yiSyllableMat BMPString ::= {0, 0, 160, 181}

-- yiSyllableMax BMPString ::= {0, 0, 160, 182}

-- yiSyllableMa BMPString ::= {0, 0, 160, 183}

-- yiSyllableMap BMPString ::= {0, 0, 160, 184}

-- yiSyllableMuot BMPString ::= {0, 0, 160, 185}

-- yiSyllableMuox BMPString ::= {0, 0, 160, 186}

-- yiSyllableMuo BMPString ::= {0, 0, 160, 187}

-- yiSyllableMuop BMPString ::= {0, 0, 160, 188}

-- yiSyllableMot BMPString ::= {0, 0, 160, 189}

-- yiSyllableMox BMPString ::= {0, 0, 160, 190}

-- yiSyllableMo BMPString ::= {0, 0, 160, 191}

-- yiSyllableMop BMPString ::= {0, 0, 160, 192}

-- yiSyllableMex BMPString ::= {0, 0, 160, 193}

-- yiSyllableMe BMPString ::= {0, 0, 160, 194}

-- yiSyllableMut BMPString ::= {0, 0, 160, 195}

-- yiSyllableMux BMPString ::= {0, 0, 160, 196}

-- yiSyllableMu BMPString ::= {0, 0, 160, 197}

-- yiSyllableMup BMPString ::= {0, 0, 160, 198}

-- yiSyllableMurx BMPString ::= {0, 0, 160, 199}

-- yiSyllableMur BMPString ::= {0, 0, 160, 200}

-- yiSyllableMyt BMPString ::= {0, 0, 160, 201}

-- yiSyllableMyx BMPString ::= {0, 0, 160, 202}

-- yiSyllableMy BMPString ::= {0, 0, 160, 203}

-- yiSyllableMyp BMPString ::= {0, 0, 160, 204}

-- yiSyllableFit BMPString ::= {0, 0, 160, 205}

-- yiSyllableFix BMPString ::= {0, 0, 160, 206}

-- yiSyllableFi BMPString ::= {0, 0, 160, 207}

-- yiSyllableFip BMPString ::= {0, 0, 160, 208}

-- yiSyllableFat BMPString ::= {0, 0, 160, 209}

-- yiSyllableFax BMPString ::= {0, 0, 160, 210}

-- yiSyllableFa BMPString ::= {0, 0, 160, 211}

-- yiSyllableFap BMPString ::= {0, 0, 160, 212}

-- yiSyllableFox BMPString ::= {0, 0, 160, 213}

-- yiSyllableFo BMPString ::= {0, 0, 160, 214}

-- yiSyllableFop BMPString ::= {0, 0, 160, 215}

-- yiSyllableFut BMPString ::= {0, 0, 160, 216}

-- yiSyllableFux BMPString ::= {0, 0, 160, 217}

-- yiSyllableFu BMPString ::= {0, 0, 160, 218}

-- yiSyllableFup BMPString ::= {0, 0, 160, 219}

-- yiSyllableFurx BMPString ::= {0, 0, 160, 220}

-- yiSyllableFur BMPString ::= {0, 0, 160, 221}

-- yiSyllableFyt BMPString ::= {0, 0, 160, 222}

-- yiSyllableFyx BMPString ::= {0, 0, 160, 223}

-- yiSyllableFy BMPString ::= {0, 0, 160, 224}

-- yiSyllableFyp BMPString ::= {0, 0, 160, 225}

-- yiSyllableVit BMPString ::= {0, 0, 160, 226}

-- yiSyllableVix BMPString ::= {0, 0, 160, 227}

-- yiSyllableVi BMPString ::= {0, 0, 160, 228}

-- yiSyllableVip BMPString ::= {0, 0, 160, 229}

-- yiSyllableViet BMPString ::= {0, 0, 160, 230}

-- yiSyllableViex BMPString ::= {0, 0, 160, 231}

-- yiSyllableVie BMPString ::= {0, 0, 160, 232}

-- yiSyllableViep BMPString ::= {0, 0, 160, 233}

-- yiSyllableVat BMPString ::= {0, 0, 160, 234}

-- yiSyllableVax BMPString ::= {0, 0, 160, 235}

-- yiSyllableVa BMPString ::= {0, 0, 160, 236}

-- yiSyllableVap BMPString ::= {0, 0, 160, 237}

-- yiSyllableVot BMPString ::= {0, 0, 160, 238}

-- yiSyllableVox BMPString ::= {0, 0, 160, 239}

-- yiSyllableVo BMPString ::= {0, 0, 160, 240}

-- yiSyllableVop BMPString ::= {0, 0, 160, 241}

-- yiSyllableVex BMPString ::= {0, 0, 160, 242}

-- yiSyllableVep BMPString ::= {0, 0, 160, 243}

-- yiSyllableVut BMPString ::= {0, 0, 160, 244}

-- yiSyllableVux BMPString ::= {0, 0, 160, 245}

-- yiSyllableVu BMPString ::= {0, 0, 160, 246}

-- yiSyllableVup BMPString ::= {0, 0, 160, 247}

-- yiSyllableVurx BMPString ::= {0, 0, 160, 248}

-- yiSyllableVur BMPString ::= {0, 0, 160, 249}

-- yiSyllableVyt BMPString ::= {0, 0, 160, 250}

-- yiSyllableVyx BMPString ::= {0, 0, 160, 251}

-- yiSyllableVy BMPString ::= {0, 0, 160, 252}

-- yiSyllableVyp BMPString ::= {0, 0, 160, 253}

-- yiSyllableVyrx BMPString ::= {0, 0, 160, 254}

-- yiSyllableVyr BMPString ::= {0, 0, 160, 255}

-- yiSyllableDit BMPString ::= {0, 0, 161, 0}

-- yiSyllableDix BMPString ::= {0, 0, 161, 1}

-- yiSyllableDi BMPString ::= {0, 0, 161, 2}

-- yiSyllableDip BMPString ::= {0, 0, 161, 3}

-- yiSyllableDiex BMPString ::= {0, 0, 161, 4}

-- yiSyllableDie BMPString ::= {0, 0, 161, 5}

-- yiSyllableDiep BMPString ::= {0, 0, 161, 6}

-- yiSyllableDat BMPString ::= {0, 0, 161, 7}

-- yiSyllableDax BMPString ::= {0, 0, 161, 8}

-- yiSyllableDa BMPString ::= {0, 0, 161, 9}

-- yiSyllableDap BMPString ::= {0, 0, 161, 10}

-- yiSyllableDuox BMPString ::= {0, 0, 161, 11}

-- yiSyllableDuo BMPString ::= {0, 0, 161, 12}

-- yiSyllableDot BMPString ::= {0, 0, 161, 13}

-- yiSyllableDox BMPString ::= {0, 0, 161, 14}

-- yiSyllableDo BMPString ::= {0, 0, 161, 15}

-- yiSyllableDop BMPString ::= {0, 0, 161, 16}

-- yiSyllableDex BMPString ::= {0, 0, 161, 17}

-- yiSyllableDe BMPString ::= {0, 0, 161, 18}

-- yiSyllableDep BMPString ::= {0, 0, 161, 19}

-- yiSyllableDut BMPString ::= {0, 0, 161, 20}

-- yiSyllableDux BMPString ::= {0, 0, 161, 21}

-- yiSyllableDu BMPString ::= {0, 0, 161, 22}

-- yiSyllableDup BMPString ::= {0, 0, 161, 23}

-- yiSyllableDurx BMPString ::= {0, 0, 161, 24}

-- yiSyllableDur BMPString ::= {0, 0, 161, 25}

-- yiSyllableTit BMPString ::= {0, 0, 161, 26}

-- yiSyllableTix BMPString ::= {0, 0, 161, 27}

-- yiSyllableTi BMPString ::= {0, 0, 161, 28}

-- yiSyllableTip BMPString ::= {0, 0, 161, 29}

-- yiSyllableTiex BMPString ::= {0, 0, 161, 30}

-- yiSyllableTie BMPString ::= {0, 0, 161, 31}

-- yiSyllableTiep BMPString ::= {0, 0, 161, 32}

-- yiSyllableTat BMPString ::= {0, 0, 161, 33}

-- yiSyllableTax BMPString ::= {0, 0, 161, 34}

-- yiSyllableTa BMPString ::= {0, 0, 161, 35}

-- yiSyllableTap BMPString ::= {0, 0, 161, 36}

-- yiSyllableTuot BMPString ::= {0, 0, 161, 37}

-- yiSyllableTuox BMPString ::= {0, 0, 161, 38}

-- yiSyllableTuo BMPString ::= {0, 0, 161, 39}

-- yiSyllableTuop BMPString ::= {0, 0, 161, 40}

-- yiSyllableTot BMPString ::= {0, 0, 161, 41}

-- yiSyllableTox BMPString ::= {0, 0, 161, 42}

-- yiSyllableTo BMPString ::= {0, 0, 161, 43}

-- yiSyllableTop BMPString ::= {0, 0, 161, 44}

-- yiSyllableTex BMPString ::= {0, 0, 161, 45}

-- yiSyllableTe BMPString ::= {0, 0, 161, 46}

-- yiSyllableTep BMPString ::= {0, 0, 161, 47}

-- yiSyllableTut BMPString ::= {0, 0, 161, 48}

-- yiSyllableTux BMPString ::= {0, 0, 161, 49}

-- yiSyllableTu BMPString ::= {0, 0, 161, 50}

-- yiSyllableTup BMPString ::= {0, 0, 161, 51}

-- yiSyllableTurx BMPString ::= {0, 0, 161, 52}

-- yiSyllableTur BMPString ::= {0, 0, 161, 53}

-- yiSyllableDdit BMPString ::= {0, 0, 161, 54}

-- yiSyllableDdix BMPString ::= {0, 0, 161, 55}

-- yiSyllableDdi BMPString ::= {0, 0, 161, 56}

-- yiSyllableDdip BMPString ::= {0, 0, 161, 57}

-- yiSyllableDdiex BMPString ::= {0, 0, 161, 58}

-- yiSyllableDdie BMPString ::= {0, 0, 161, 59}

-- yiSyllableDdiep BMPString ::= {0, 0, 161, 60}

-- yiSyllableDdat BMPString ::= {0, 0, 161, 61}

-- yiSyllableDdax BMPString ::= {0, 0, 161, 62}

-- yiSyllableDda BMPString ::= {0, 0, 161, 63}

-- yiSyllableDdap BMPString ::= {0, 0, 161, 64}

-- yiSyllableDduox BMPString ::= {0, 0, 161, 65}

-- yiSyllableDduo BMPString ::= {0, 0, 161, 66}

-- yiSyllableDduop BMPString ::= {0, 0, 161, 67}

-- yiSyllableDdot BMPString ::= {0, 0, 161, 68}

-- yiSyllableDdox BMPString ::= {0, 0, 161, 69}

-- yiSyllableDdo BMPString ::= {0, 0, 161, 70}

-- yiSyllableDdop BMPString ::= {0, 0, 161, 71}

-- yiSyllableDdex BMPString ::= {0, 0, 161, 72}

-- yiSyllableDde BMPString ::= {0, 0, 161, 73}

-- yiSyllableDdep BMPString ::= {0, 0, 161, 74}

-- yiSyllableDdut BMPString ::= {0, 0, 161, 75}

-- yiSyllableDdux BMPString ::= {0, 0, 161, 76}

-- yiSyllableDdu BMPString ::= {0, 0, 161, 77}

-- yiSyllableDdup BMPString ::= {0, 0, 161, 78}

-- yiSyllableDdurx BMPString ::= {0, 0, 161, 79}

-- yiSyllableDdur BMPString ::= {0, 0, 161, 80}

-- yiSyllableNdit BMPString ::= {0, 0, 161, 81}

-- yiSyllableNdix BMPString ::= {0, 0, 161, 82}

-- yiSyllableNdi BMPString ::= {0, 0, 161, 83}

-- yiSyllableNdip BMPString ::= {0, 0, 161, 84}

-- yiSyllableNdiex BMPString ::= {0, 0, 161, 85}

-- yiSyllableNdie BMPString ::= {0, 0, 161, 86}

-- yiSyllableNdat BMPString ::= {0, 0, 161, 87}

-- yiSyllableNdax BMPString ::= {0, 0, 161, 88}

-- yiSyllableNda BMPString ::= {0, 0, 161, 89}

-- yiSyllableNdap BMPString ::= {0, 0, 161, 90}

-- yiSyllableNdot BMPString ::= {0, 0, 161, 91}

-- yiSyllableNdox BMPString ::= {0, 0, 161, 92}

-- yiSyllableNdo BMPString ::= {0, 0, 161, 93}

-- yiSyllableNdop BMPString ::= {0, 0, 161, 94}

-- yiSyllableNdex BMPString ::= {0, 0, 161, 95}

-- yiSyllableNde BMPString ::= {0, 0, 161, 96}

-- yiSyllableNdep BMPString ::= {0, 0, 161, 97}

-- yiSyllableNdut BMPString ::= {0, 0, 161, 98}

-- yiSyllableNdux BMPString ::= {0, 0, 161, 99}

-- yiSyllableNdu BMPString ::= {0, 0, 161, 100}

-- yiSyllableNdup BMPString ::= {0, 0, 161, 101}

-- yiSyllableNdurx BMPString ::= {0, 0, 161, 102}

-- yiSyllableNdur BMPString ::= {0, 0, 161, 103}

-- yiSyllableHnit BMPString ::= {0, 0, 161, 104}

-- yiSyllableHnix BMPString ::= {0, 0, 161, 105}

-- yiSyllableHni BMPString ::= {0, 0, 161, 106}

-- yiSyllableHnip BMPString ::= {0, 0, 161, 107}

-- yiSyllableHniet BMPString ::= {0, 0, 161, 108}

-- yiSyllableHniex BMPString ::= {0, 0, 161, 109}

-- yiSyllableHnie BMPString ::= {0, 0, 161, 110}

-- yiSyllableHniep BMPString ::= {0, 0, 161, 111}

-- yiSyllableHnat BMPString ::= {0, 0, 161, 112}

-- yiSyllableHnax BMPString ::= {0, 0, 161, 113}

-- yiSyllableHna BMPString ::= {0, 0, 161, 114}

-- yiSyllableHnap BMPString ::= {0, 0, 161, 115}

-- yiSyllableHnuox BMPString ::= {0, 0, 161, 116}

-- yiSyllableHnuo BMPString ::= {0, 0, 161, 117}

-- yiSyllableHnot BMPString ::= {0, 0, 161, 118}

-- yiSyllableHnox BMPString ::= {0, 0, 161, 119}

-- yiSyllableHnop BMPString ::= {0, 0, 161, 120}

-- yiSyllableHnex BMPString ::= {0, 0, 161, 121}

-- yiSyllableHne BMPString ::= {0, 0, 161, 122}

-- yiSyllableHnep BMPString ::= {0, 0, 161, 123}

-- yiSyllableHnut BMPString ::= {0, 0, 161, 124}

-- yiSyllableNit BMPString ::= {0, 0, 161, 125}

-- yiSyllableNix BMPString ::= {0, 0, 161, 126}

-- yiSyllableNi BMPString ::= {0, 0, 161, 127}

-- yiSyllableNip BMPString ::= {0, 0, 161, 128}

-- yiSyllableNiex BMPString ::= {0, 0, 161, 129}

-- yiSyllableNie BMPString ::= {0, 0, 161, 130}

-- yiSyllableNiep BMPString ::= {0, 0, 161, 131}

-- yiSyllableNax BMPString ::= {0, 0, 161, 132}

-- yiSyllableNa BMPString ::= {0, 0, 161, 133}

-- yiSyllableNap BMPString ::= {0, 0, 161, 134}

-- yiSyllableNuox BMPString ::= {0, 0, 161, 135}

-- yiSyllableNuo BMPString ::= {0, 0, 161, 136}

-- yiSyllableNuop BMPString ::= {0, 0, 161, 137}

-- yiSyllableNot BMPString ::= {0, 0, 161, 138}

-- yiSyllableNox BMPString ::= {0, 0, 161, 139}

-- yiSyllableNo BMPString ::= {0, 0, 161, 140}

-- yiSyllableNop BMPString ::= {0, 0, 161, 141}

-- yiSyllableNex BMPString ::= {0, 0, 161, 142}

-- yiSyllableNe BMPString ::= {0, 0, 161, 143}

-- yiSyllableNep BMPString ::= {0, 0, 161, 144}

-- yiSyllableNut BMPString ::= {0, 0, 161, 145}

-- yiSyllableNux BMPString ::= {0, 0, 161, 146}

-- yiSyllableNu BMPString ::= {0, 0, 161, 147}

-- yiSyllableNup BMPString ::= {0, 0, 161, 148}

-- yiSyllableNurx BMPString ::= {0, 0, 161, 149}

-- yiSyllableNur BMPString ::= {0, 0, 161, 150}

-- yiSyllableHlit BMPString ::= {0, 0, 161, 151}

-- yiSyllableHlix BMPString ::= {0, 0, 161, 152}

-- yiSyllableHli BMPString ::= {0, 0, 161, 153}

-- yiSyllableHlip BMPString ::= {0, 0, 161, 154}

-- yiSyllableHliex BMPString ::= {0, 0, 161, 155}

-- yiSyllableHlie BMPString ::= {0, 0, 161, 156}

-- yiSyllableHliep BMPString ::= {0, 0, 161, 157}

-- yiSyllableHlat BMPString ::= {0, 0, 161, 158}

-- yiSyllableHlax BMPString ::= {0, 0, 161, 159}

-- yiSyllableHla BMPString ::= {0, 0, 161, 160}

-- yiSyllableHlap BMPString ::= {0, 0, 161, 161}

-- yiSyllableHluox BMPString ::= {0, 0, 161, 162}

-- yiSyllableHluo BMPString ::= {0, 0, 161, 163}

-- yiSyllableHluop BMPString ::= {0, 0, 161, 164}

-- yiSyllableHlox BMPString ::= {0, 0, 161, 165}

-- yiSyllableHlo BMPString ::= {0, 0, 161, 166}

-- yiSyllableHlop BMPString ::= {0, 0, 161, 167}

-- yiSyllableHlex BMPString ::= {0, 0, 161, 168}

-- yiSyllableHle BMPString ::= {0, 0, 161, 169}

-- yiSyllableHlep BMPString ::= {0, 0, 161, 170}

-- yiSyllableHlut BMPString ::= {0, 0, 161, 171}

-- yiSyllableHlux BMPString ::= {0, 0, 161, 172}

-- yiSyllableHlu BMPString ::= {0, 0, 161, 173}

-- yiSyllableHlup BMPString ::= {0, 0, 161, 174}

-- yiSyllableHlurx BMPString ::= {0, 0, 161, 175}

-- yiSyllableHlur BMPString ::= {0, 0, 161, 176}

-- yiSyllableHlyt BMPString ::= {0, 0, 161, 177}

-- yiSyllableHlyx BMPString ::= {0, 0, 161, 178}

-- yiSyllableHly BMPString ::= {0, 0, 161, 179}

-- yiSyllableHlyp BMPString ::= {0, 0, 161, 180}

-- yiSyllableHlyrx BMPString ::= {0, 0, 161, 181}

-- yiSyllableHlyr BMPString ::= {0, 0, 161, 182}

-- yiSyllableLit BMPString ::= {0, 0, 161, 183}

-- yiSyllableLix BMPString ::= {0, 0, 161, 184}

-- yiSyllableLi BMPString ::= {0, 0, 161, 185}

-- yiSyllableLip BMPString ::= {0, 0, 161, 186}

-- yiSyllableLiet BMPString ::= {0, 0, 161, 187}

-- yiSyllableLiex BMPString ::= {0, 0, 161, 188}

-- yiSyllableLie BMPString ::= {0, 0, 161, 189}

-- yiSyllableLiep BMPString ::= {0, 0, 161, 190}

-- yiSyllableLat BMPString ::= {0, 0, 161, 191}

-- yiSyllableLax BMPString ::= {0, 0, 161, 192}

-- yiSyllableLa BMPString ::= {0, 0, 161, 193}

-- yiSyllableLap BMPString ::= {0, 0, 161, 194}

-- yiSyllableLuot BMPString ::= {0, 0, 161, 195}

-- yiSyllableLuox BMPString ::= {0, 0, 161, 196}

-- yiSyllableLuo BMPString ::= {0, 0, 161, 197}

-- yiSyllableLuop BMPString ::= {0, 0, 161, 198}

-- yiSyllableLot BMPString ::= {0, 0, 161, 199}

-- yiSyllableLox BMPString ::= {0, 0, 161, 200}

-- yiSyllableLo BMPString ::= {0, 0, 161, 201}

-- yiSyllableLop BMPString ::= {0, 0, 161, 202}

-- yiSyllableLex BMPString ::= {0, 0, 161, 203}

-- yiSyllableLe BMPString ::= {0, 0, 161, 204}

-- yiSyllableLep BMPString ::= {0, 0, 161, 205}

-- yiSyllableLut BMPString ::= {0, 0, 161, 206}

-- yiSyllableLux BMPString ::= {0, 0, 161, 207}

-- yiSyllableLu BMPString ::= {0, 0, 161, 208}

-- yiSyllableLup BMPString ::= {0, 0, 161, 209}

-- yiSyllableLurx BMPString ::= {0, 0, 161, 210}

-- yiSyllableLur BMPString ::= {0, 0, 161, 211}

-- yiSyllableLyt BMPString ::= {0, 0, 161, 212}

-- yiSyllableLyx BMPString ::= {0, 0, 161, 213}

-- yiSyllableLy BMPString ::= {0, 0, 161, 214}

-- yiSyllableLyp BMPString ::= {0, 0, 161, 215}

-- yiSyllableLyrx BMPString ::= {0, 0, 161, 216}

-- yiSyllableLyr BMPString ::= {0, 0, 161, 217}

-- yiSyllableGit BMPString ::= {0, 0, 161, 218}

-- yiSyllableGix BMPString ::= {0, 0, 161, 219}

-- yiSyllableGi BMPString ::= {0, 0, 161, 220}

-- yiSyllableGip BMPString ::= {0, 0, 161, 221}

-- yiSyllableGiet BMPString ::= {0, 0, 161, 222}

-- yiSyllableGiex BMPString ::= {0, 0, 161, 223}

-- yiSyllableGie BMPString ::= {0, 0, 161, 224}

-- yiSyllableGiep BMPString ::= {0, 0, 161, 225}

-- yiSyllableGat BMPString ::= {0, 0, 161, 226}

-- yiSyllableGax BMPString ::= {0, 0, 161, 227}

-- yiSyllableGa BMPString ::= {0, 0, 161, 228}

-- yiSyllableGap BMPString ::= {0, 0, 161, 229}

-- yiSyllableGuot BMPString ::= {0, 0, 161, 230}

-- yiSyllableGuox BMPString ::= {0, 0, 161, 231}

-- yiSyllableGuo BMPString ::= {0, 0, 161, 232}

-- yiSyllableGuop BMPString ::= {0, 0, 161, 233}

-- yiSyllableGot BMPString ::= {0, 0, 161, 234}

-- yiSyllableGox BMPString ::= {0, 0, 161, 235}

-- yiSyllableGo BMPString ::= {0, 0, 161, 236}

-- yiSyllableGop BMPString ::= {0, 0, 161, 237}

-- yiSyllableGet BMPString ::= {0, 0, 161, 238}

-- yiSyllableGex BMPString ::= {0, 0, 161, 239}

-- yiSyllableGe BMPString ::= {0, 0, 161, 240}

-- yiSyllableGep BMPString ::= {0, 0, 161, 241}

-- yiSyllableGut BMPString ::= {0, 0, 161, 242}

-- yiSyllableGux BMPString ::= {0, 0, 161, 243}

-- yiSyllableGu BMPString ::= {0, 0, 161, 244}

-- yiSyllableGup BMPString ::= {0, 0, 161, 245}

-- yiSyllableGurx BMPString ::= {0, 0, 161, 246}

-- yiSyllableGur BMPString ::= {0, 0, 161, 247}

-- yiSyllableKit BMPString ::= {0, 0, 161, 248}

-- yiSyllableKix BMPString ::= {0, 0, 161, 249}

-- yiSyllableKi BMPString ::= {0, 0, 161, 250}

-- yiSyllableKip BMPString ::= {0, 0, 161, 251}

-- yiSyllableKiex BMPString ::= {0, 0, 161, 252}

-- yiSyllableKie BMPString ::= {0, 0, 161, 253}

-- yiSyllableKiep BMPString ::= {0, 0, 161, 254}

-- yiSyllableKat BMPString ::= {0, 0, 161, 255}

-- yiSyllableKax BMPString ::= {0, 0, 162, 0}

-- yiSyllableKa BMPString ::= {0, 0, 162, 1}

-- yiSyllableKap BMPString ::= {0, 0, 162, 2}

-- yiSyllableKuox BMPString ::= {0, 0, 162, 3}

-- yiSyllableKuo BMPString ::= {0, 0, 162, 4}

-- yiSyllableKuop BMPString ::= {0, 0, 162, 5}

-- yiSyllableKot BMPString ::= {0, 0, 162, 6}

-- yiSyllableKox BMPString ::= {0, 0, 162, 7}

-- yiSyllableKo BMPString ::= {0, 0, 162, 8}

-- yiSyllableKop BMPString ::= {0, 0, 162, 9}

-- yiSyllableKet BMPString ::= {0, 0, 162, 10}

-- yiSyllableKex BMPString ::= {0, 0, 162, 11}

-- yiSyllableKe BMPString ::= {0, 0, 162, 12}

-- yiSyllableKep BMPString ::= {0, 0, 162, 13}

-- yiSyllableKut BMPString ::= {0, 0, 162, 14}

-- yiSyllableKux BMPString ::= {0, 0, 162, 15}

-- yiSyllableKu BMPString ::= {0, 0, 162, 16}

-- yiSyllableKup BMPString ::= {0, 0, 162, 17}

-- yiSyllableKurx BMPString ::= {0, 0, 162, 18}

-- yiSyllableKur BMPString ::= {0, 0, 162, 19}

-- yiSyllableGgit BMPString ::= {0, 0, 162, 20}

-- yiSyllableGgix BMPString ::= {0, 0, 162, 21}

-- yiSyllableGgi BMPString ::= {0, 0, 162, 22}

-- yiSyllableGgiex BMPString ::= {0, 0, 162, 23}

-- yiSyllableGgie BMPString ::= {0, 0, 162, 24}

-- yiSyllableGgiep BMPString ::= {0, 0, 162, 25}

-- yiSyllableGgat BMPString ::= {0, 0, 162, 26}

-- yiSyllableGgax BMPString ::= {0, 0, 162, 27}

-- yiSyllableGga BMPString ::= {0, 0, 162, 28}

-- yiSyllableGgap BMPString ::= {0, 0, 162, 29}

-- yiSyllableGguot BMPString ::= {0, 0, 162, 30}

-- yiSyllableGguox BMPString ::= {0, 0, 162, 31}

-- yiSyllableGguo BMPString ::= {0, 0, 162, 32}

-- yiSyllableGguop BMPString ::= {0, 0, 162, 33}

-- yiSyllableGgot BMPString ::= {0, 0, 162, 34}

-- yiSyllableGgox BMPString ::= {0, 0, 162, 35}

-- yiSyllableGgo BMPString ::= {0, 0, 162, 36}

-- yiSyllableGgop BMPString ::= {0, 0, 162, 37}

-- yiSyllableGget BMPString ::= {0, 0, 162, 38}

-- yiSyllableGgex BMPString ::= {0, 0, 162, 39}

-- yiSyllableGge BMPString ::= {0, 0, 162, 40}

-- yiSyllableGgep BMPString ::= {0, 0, 162, 41}

-- yiSyllableGgut BMPString ::= {0, 0, 162, 42}

-- yiSyllableGgux BMPString ::= {0, 0, 162, 43}

-- yiSyllableGgu BMPString ::= {0, 0, 162, 44}

-- yiSyllableGgup BMPString ::= {0, 0, 162, 45}

-- yiSyllableGgurx BMPString ::= {0, 0, 162, 46}

-- yiSyllableGgur BMPString ::= {0, 0, 162, 47}

-- yiSyllableMgiex BMPString ::= {0, 0, 162, 48}

-- yiSyllableMgie BMPString ::= {0, 0, 162, 49}

-- yiSyllableMgat BMPString ::= {0, 0, 162, 50}

-- yiSyllableMgax BMPString ::= {0, 0, 162, 51}

-- yiSyllableMga BMPString ::= {0, 0, 162, 52}

-- yiSyllableMgap BMPString ::= {0, 0, 162, 53}

-- yiSyllableMguox BMPString ::= {0, 0, 162, 54}

-- yiSyllableMguo BMPString ::= {0, 0, 162, 55}

-- yiSyllableMguop BMPString ::= {0, 0, 162, 56}

-- yiSyllableMgot BMPString ::= {0, 0, 162, 57}

-- yiSyllableMgox BMPString ::= {0, 0, 162, 58}

-- yiSyllableMgo BMPString ::= {0, 0, 162, 59}

-- yiSyllableMgop BMPString ::= {0, 0, 162, 60}

-- yiSyllableMgex BMPString ::= {0, 0, 162, 61}

-- yiSyllableMge BMPString ::= {0, 0, 162, 62}

-- yiSyllableMgep BMPString ::= {0, 0, 162, 63}

-- yiSyllableMgut BMPString ::= {0, 0, 162, 64}

-- yiSyllableMgux BMPString ::= {0, 0, 162, 65}

-- yiSyllableMgu BMPString ::= {0, 0, 162, 66}

-- yiSyllableMgup BMPString ::= {0, 0, 162, 67}

-- yiSyllableMgurx BMPString ::= {0, 0, 162, 68}

-- yiSyllableMgur BMPString ::= {0, 0, 162, 69}

-- yiSyllableHxit BMPString ::= {0, 0, 162, 70}

-- yiSyllableHxix BMPString ::= {0, 0, 162, 71}

-- yiSyllableHxi BMPString ::= {0, 0, 162, 72}

-- yiSyllableHxip BMPString ::= {0, 0, 162, 73}

-- yiSyllableHxiet BMPString ::= {0, 0, 162, 74}

-- yiSyllableHxiex BMPString ::= {0, 0, 162, 75}

-- yiSyllableHxie BMPString ::= {0, 0, 162, 76}

-- yiSyllableHxiep BMPString ::= {0, 0, 162, 77}

-- yiSyllableHxat BMPString ::= {0, 0, 162, 78}

-- yiSyllableHxax BMPString ::= {0, 0, 162, 79}

-- yiSyllableHxa BMPString ::= {0, 0, 162, 80}

-- yiSyllableHxap BMPString ::= {0, 0, 162, 81}

-- yiSyllableHxuot BMPString ::= {0, 0, 162, 82}

-- yiSyllableHxuox BMPString ::= {0, 0, 162, 83}

-- yiSyllableHxuo BMPString ::= {0, 0, 162, 84}

-- yiSyllableHxuop BMPString ::= {0, 0, 162, 85}

-- yiSyllableHxot BMPString ::= {0, 0, 162, 86}

-- yiSyllableHxox BMPString ::= {0, 0, 162, 87}

-- yiSyllableHxo BMPString ::= {0, 0, 162, 88}

-- yiSyllableHxop BMPString ::= {0, 0, 162, 89}

-- yiSyllableHxex BMPString ::= {0, 0, 162, 90}

-- yiSyllableHxe BMPString ::= {0, 0, 162, 91}

-- yiSyllableHxep BMPString ::= {0, 0, 162, 92}

-- yiSyllableNgiex BMPString ::= {0, 0, 162, 93}

-- yiSyllableNgie BMPString ::= {0, 0, 162, 94}

-- yiSyllableNgiep BMPString ::= {0, 0, 162, 95}

-- yiSyllableNgat BMPString ::= {0, 0, 162, 96}

-- yiSyllableNgax BMPString ::= {0, 0, 162, 97}

-- yiSyllableNga BMPString ::= {0, 0, 162, 98}

-- yiSyllableNgap BMPString ::= {0, 0, 162, 99}

-- yiSyllableNguot BMPString ::= {0, 0, 162, 100}

-- yiSyllableNguox BMPString ::= {0, 0, 162, 101}

-- yiSyllableNguo BMPString ::= {0, 0, 162, 102}

-- yiSyllableNgot BMPString ::= {0, 0, 162, 103}

-- yiSyllableNgox BMPString ::= {0, 0, 162, 104}

-- yiSyllableNgo BMPString ::= {0, 0, 162, 105}

-- yiSyllableNgop BMPString ::= {0, 0, 162, 106}

-- yiSyllableNgex BMPString ::= {0, 0, 162, 107}

-- yiSyllableNge BMPString ::= {0, 0, 162, 108}

-- yiSyllableNgep BMPString ::= {0, 0, 162, 109}

-- yiSyllableHit BMPString ::= {0, 0, 162, 110}

-- yiSyllableHiex BMPString ::= {0, 0, 162, 111}

-- yiSyllableHie BMPString ::= {0, 0, 162, 112}

-- yiSyllableHat BMPString ::= {0, 0, 162, 113}

-- yiSyllableHax BMPString ::= {0, 0, 162, 114}

-- yiSyllableHa BMPString ::= {0, 0, 162, 115}

-- yiSyllableHap BMPString ::= {0, 0, 162, 116}

-- yiSyllableHuot BMPString ::= {0, 0, 162, 117}

-- yiSyllableHuox BMPString ::= {0, 0, 162, 118}

-- yiSyllableHuo BMPString ::= {0, 0, 162, 119}

-- yiSyllableHuop BMPString ::= {0, 0, 162, 120}

-- yiSyllableHot BMPString ::= {0, 0, 162, 121}

-- yiSyllableHox BMPString ::= {0, 0, 162, 122}

-- yiSyllableHo BMPString ::= {0, 0, 162, 123}

-- yiSyllableHop BMPString ::= {0, 0, 162, 124}

-- yiSyllableHex BMPString ::= {0, 0, 162, 125}

-- yiSyllableHe BMPString ::= {0, 0, 162, 126}

-- yiSyllableHep BMPString ::= {0, 0, 162, 127}

-- yiSyllableWat BMPString ::= {0, 0, 162, 128}

-- yiSyllableWax BMPString ::= {0, 0, 162, 129}

-- yiSyllableWa BMPString ::= {0, 0, 162, 130}

-- yiSyllableWap BMPString ::= {0, 0, 162, 131}

-- yiSyllableWuox BMPString ::= {0, 0, 162, 132}

-- yiSyllableWuo BMPString ::= {0, 0, 162, 133}

-- yiSyllableWuop BMPString ::= {0, 0, 162, 134}

-- yiSyllableWox BMPString ::= {0, 0, 162, 135}

-- yiSyllableWo BMPString ::= {0, 0, 162, 136}

-- yiSyllableWop BMPString ::= {0, 0, 162, 137}

-- yiSyllableWex BMPString ::= {0, 0, 162, 138}

-- yiSyllableWe BMPString ::= {0, 0, 162, 139}

-- yiSyllableWep BMPString ::= {0, 0, 162, 140}

-- yiSyllableZit BMPString ::= {0, 0, 162, 141}

-- yiSyllableZix BMPString ::= {0, 0, 162, 142}

-- yiSyllableZi BMPString ::= {0, 0, 162, 143}

-- yiSyllableZip BMPString ::= {0, 0, 162, 144}

-- yiSyllableZiex BMPString ::= {0, 0, 162, 145}

-- yiSyllableZie BMPString ::= {0, 0, 162, 146}

-- yiSyllableZiep BMPString ::= {0, 0, 162, 147}

-- yiSyllableZat BMPString ::= {0, 0, 162, 148}

-- yiSyllableZax BMPString ::= {0, 0, 162, 149}

-- yiSyllableZa BMPString ::= {0, 0, 162, 150}

-- yiSyllableZap BMPString ::= {0, 0, 162, 151}

-- yiSyllableZuox BMPString ::= {0, 0, 162, 152}

-- yiSyllableZuo BMPString ::= {0, 0, 162, 153}

-- yiSyllableZuop BMPString ::= {0, 0, 162, 154}

-- yiSyllableZot BMPString ::= {0, 0, 162, 155}

-- yiSyllableZox BMPString ::= {0, 0, 162, 156}

-- yiSyllableZo BMPString ::= {0, 0, 162, 157}

-- yiSyllableZop BMPString ::= {0, 0, 162, 158}

-- yiSyllableZex BMPString ::= {0, 0, 162, 159}

-- yiSyllableZe BMPString ::= {0, 0, 162, 160}

-- yiSyllableZep BMPString ::= {0, 0, 162, 161}

-- yiSyllableZut BMPString ::= {0, 0, 162, 162}

-- yiSyllableZux BMPString ::= {0, 0, 162, 163}

-- yiSyllableZu BMPString ::= {0, 0, 162, 164}

-- yiSyllableZup BMPString ::= {0, 0, 162, 165}

-- yiSyllableZurx BMPString ::= {0, 0, 162, 166}

-- yiSyllableZur BMPString ::= {0, 0, 162, 167}

-- yiSyllableZyt BMPString ::= {0, 0, 162, 168}

-- yiSyllableZyx BMPString ::= {0, 0, 162, 169}

-- yiSyllableZy BMPString ::= {0, 0, 162, 170}

-- yiSyllableZyp BMPString ::= {0, 0, 162, 171}

-- yiSyllableZyrx BMPString ::= {0, 0, 162, 172}

-- yiSyllableZyr BMPString ::= {0, 0, 162, 173}

-- yiSyllableCit BMPString ::= {0, 0, 162, 174}

-- yiSyllableCix BMPString ::= {0, 0, 162, 175}

-- yiSyllableCi BMPString ::= {0, 0, 162, 176}

-- yiSyllableCip BMPString ::= {0, 0, 162, 177}

-- yiSyllableCiet BMPString ::= {0, 0, 162, 178}

-- yiSyllableCiex BMPString ::= {0, 0, 162, 179}

-- yiSyllableCie BMPString ::= {0, 0, 162, 180}

-- yiSyllableCiep BMPString ::= {0, 0, 162, 181}

-- yiSyllableCat BMPString ::= {0, 0, 162, 182}

-- yiSyllableCax BMPString ::= {0, 0, 162, 183}

-- yiSyllableCa BMPString ::= {0, 0, 162, 184}

-- yiSyllableCap BMPString ::= {0, 0, 162, 185}

-- yiSyllableCuox BMPString ::= {0, 0, 162, 186}

-- yiSyllableCuo BMPString ::= {0, 0, 162, 187}

-- yiSyllableCuop BMPString ::= {0, 0, 162, 188}

-- yiSyllableCot BMPString ::= {0, 0, 162, 189}

-- yiSyllableCox BMPString ::= {0, 0, 162, 190}

-- yiSyllableCo BMPString ::= {0, 0, 162, 191}

-- yiSyllableCop BMPString ::= {0, 0, 162, 192}

-- yiSyllableCex BMPString ::= {0, 0, 162, 193}

-- yiSyllableCe BMPString ::= {0, 0, 162, 194}

-- yiSyllableCep BMPString ::= {0, 0, 162, 195}

-- yiSyllableCut BMPString ::= {0, 0, 162, 196}

-- yiSyllableCux BMPString ::= {0, 0, 162, 197}

-- yiSyllableCu BMPString ::= {0, 0, 162, 198}

-- yiSyllableCup BMPString ::= {0, 0, 162, 199}

-- yiSyllableCurx BMPString ::= {0, 0, 162, 200}

-- yiSyllableCur BMPString ::= {0, 0, 162, 201}

-- yiSyllableCyt BMPString ::= {0, 0, 162, 202}

-- yiSyllableCyx BMPString ::= {0, 0, 162, 203}

-- yiSyllableCy BMPString ::= {0, 0, 162, 204}

-- yiSyllableCyp BMPString ::= {0, 0, 162, 205}

-- yiSyllableCyrx BMPString ::= {0, 0, 162, 206}

-- yiSyllableCyr BMPString ::= {0, 0, 162, 207}

-- yiSyllableZzit BMPString ::= {0, 0, 162, 208}

-- yiSyllableZzix BMPString ::= {0, 0, 162, 209}

-- yiSyllableZzi BMPString ::= {0, 0, 162, 210}

-- yiSyllableZzip BMPString ::= {0, 0, 162, 211}

-- yiSyllableZziet BMPString ::= {0, 0, 162, 212}

-- yiSyllableZziex BMPString ::= {0, 0, 162, 213}

-- yiSyllableZzie BMPString ::= {0, 0, 162, 214}

-- yiSyllableZziep BMPString ::= {0, 0, 162, 215}

-- yiSyllableZzat BMPString ::= {0, 0, 162, 216}

-- yiSyllableZzax BMPString ::= {0, 0, 162, 217}

-- yiSyllableZza BMPString ::= {0, 0, 162, 218}

-- yiSyllableZzap BMPString ::= {0, 0, 162, 219}

-- yiSyllableZzox BMPString ::= {0, 0, 162, 220}

-- yiSyllableZzo BMPString ::= {0, 0, 162, 221}

-- yiSyllableZzop BMPString ::= {0, 0, 162, 222}

-- yiSyllableZzex BMPString ::= {0, 0, 162, 223}

-- yiSyllableZze BMPString ::= {0, 0, 162, 224}

-- yiSyllableZzep BMPString ::= {0, 0, 162, 225}

-- yiSyllableZzux BMPString ::= {0, 0, 162, 226}

-- yiSyllableZzu BMPString ::= {0, 0, 162, 227}

-- yiSyllableZzup BMPString ::= {0, 0, 162, 228}

-- yiSyllableZzurx BMPString ::= {0, 0, 162, 229}

-- yiSyllableZzur BMPString ::= {0, 0, 162, 230}

-- yiSyllableZzyt BMPString ::= {0, 0, 162, 231}

-- yiSyllableZzyx BMPString ::= {0, 0, 162, 232}

-- yiSyllableZzy BMPString ::= {0, 0, 162, 233}

-- yiSyllableZzyp BMPString ::= {0, 0, 162, 234}

-- yiSyllableZzyrx BMPString ::= {0, 0, 162, 235}

-- yiSyllableZzyr BMPString ::= {0, 0, 162, 236}

-- yiSyllableNzit BMPString ::= {0, 0, 162, 237}

-- yiSyllableNzix BMPString ::= {0, 0, 162, 238}

-- yiSyllableNzi BMPString ::= {0, 0, 162, 239}

-- yiSyllableNzip BMPString ::= {0, 0, 162, 240}

-- yiSyllableNziex BMPString ::= {0, 0, 162, 241}

-- yiSyllableNzie BMPString ::= {0, 0, 162, 242}

-- yiSyllableNziep BMPString ::= {0, 0, 162, 243}

-- yiSyllableNzat BMPString ::= {0, 0, 162, 244}

-- yiSyllableNzax BMPString ::= {0, 0, 162, 245}

-- yiSyllableNza BMPString ::= {0, 0, 162, 246}

-- yiSyllableNzap BMPString ::= {0, 0, 162, 247}

-- yiSyllableNzuox BMPString ::= {0, 0, 162, 248}

-- yiSyllableNzuo BMPString ::= {0, 0, 162, 249}

-- yiSyllableNzox BMPString ::= {0, 0, 162, 250}

-- yiSyllableNzop BMPString ::= {0, 0, 162, 251}

-- yiSyllableNzex BMPString ::= {0, 0, 162, 252}

-- yiSyllableNze BMPString ::= {0, 0, 162, 253}

-- yiSyllableNzux BMPString ::= {0, 0, 162, 254}

-- yiSyllableNzu BMPString ::= {0, 0, 162, 255}

-- yiSyllableNzup BMPString ::= {0, 0, 163, 0}

-- yiSyllableNzurx BMPString ::= {0, 0, 163, 1}

-- yiSyllableNzur BMPString ::= {0, 0, 163, 2}

-- yiSyllableNzyt BMPString ::= {0, 0, 163, 3}

-- yiSyllableNzyx BMPString ::= {0, 0, 163, 4}

-- yiSyllableNzy BMPString ::= {0, 0, 163, 5}

-- yiSyllableNzyp BMPString ::= {0, 0, 163, 6}

-- yiSyllableNzyrx BMPString ::= {0, 0, 163, 7}

-- yiSyllableNzyr BMPString ::= {0, 0, 163, 8}

-- yiSyllableSit BMPString ::= {0, 0, 163, 9}

-- yiSyllableSix BMPString ::= {0, 0, 163, 10}

-- yiSyllableSi BMPString ::= {0, 0, 163, 11}

-- yiSyllableSip BMPString ::= {0, 0, 163, 12}

-- yiSyllableSiex BMPString ::= {0, 0, 163, 13}

-- yiSyllableSie BMPString ::= {0, 0, 163, 14}

-- yiSyllableSiep BMPString ::= {0, 0, 163, 15}

-- yiSyllableSat BMPString ::= {0, 0, 163, 16}

-- yiSyllableSax BMPString ::= {0, 0, 163, 17}

-- yiSyllableSa BMPString ::= {0, 0, 163, 18}

-- yiSyllableSap BMPString ::= {0, 0, 163, 19}

-- yiSyllableSuox BMPString ::= {0, 0, 163, 20}

-- yiSyllableSuo BMPString ::= {0, 0, 163, 21}

-- yiSyllableSuop BMPString ::= {0, 0, 163, 22}

-- yiSyllableSot BMPString ::= {0, 0, 163, 23}

-- yiSyllableSox BMPString ::= {0, 0, 163, 24}

-- yiSyllableSo BMPString ::= {0, 0, 163, 25}

-- yiSyllableSop BMPString ::= {0, 0, 163, 26}

-- yiSyllableSex BMPString ::= {0, 0, 163, 27}

-- yiSyllableSe BMPString ::= {0, 0, 163, 28}

-- yiSyllableSep BMPString ::= {0, 0, 163, 29}

-- yiSyllableSut BMPString ::= {0, 0, 163, 30}

-- yiSyllableSux BMPString ::= {0, 0, 163, 31}

-- yiSyllableSu BMPString ::= {0, 0, 163, 32}

-- yiSyllableSup BMPString ::= {0, 0, 163, 33}

-- yiSyllableSurx BMPString ::= {0, 0, 163, 34}

-- yiSyllableSur BMPString ::= {0, 0, 163, 35}

-- yiSyllableSyt BMPString ::= {0, 0, 163, 36}

-- yiSyllableSyx BMPString ::= {0, 0, 163, 37}

-- yiSyllableSy BMPString ::= {0, 0, 163, 38}

-- yiSyllableSyp BMPString ::= {0, 0, 163, 39}

-- yiSyllableSyrx BMPString ::= {0, 0, 163, 40}

-- yiSyllableSyr BMPString ::= {0, 0, 163, 41}

-- yiSyllableSsit BMPString ::= {0, 0, 163, 42}

-- yiSyllableSsix BMPString ::= {0, 0, 163, 43}

-- yiSyllableSsi BMPString ::= {0, 0, 163, 44}

-- yiSyllableSsip BMPString ::= {0, 0, 163, 45}

-- yiSyllableSsiex BMPString ::= {0, 0, 163, 46}

-- yiSyllableSsie BMPString ::= {0, 0, 163, 47}

-- yiSyllableSsiep BMPString ::= {0, 0, 163, 48}

-- yiSyllableSsat BMPString ::= {0, 0, 163, 49}

-- yiSyllableSsax BMPString ::= {0, 0, 163, 50}

-- yiSyllableSsa BMPString ::= {0, 0, 163, 51}

-- yiSyllableSsap BMPString ::= {0, 0, 163, 52}

-- yiSyllableSsot BMPString ::= {0, 0, 163, 53}

-- yiSyllableSsox BMPString ::= {0, 0, 163, 54}

-- yiSyllableSso BMPString ::= {0, 0, 163, 55}

-- yiSyllableSsop BMPString ::= {0, 0, 163, 56}

-- yiSyllableSsex BMPString ::= {0, 0, 163, 57}

-- yiSyllableSse BMPString ::= {0, 0, 163, 58}

-- yiSyllableSsep BMPString ::= {0, 0, 163, 59}

-- yiSyllableSsut BMPString ::= {0, 0, 163, 60}

-- yiSyllableSsux BMPString ::= {0, 0, 163, 61}

-- yiSyllableSsu BMPString ::= {0, 0, 163, 62}

-- yiSyllableSsup BMPString ::= {0, 0, 163, 63}

-- yiSyllableSsyt BMPString ::= {0, 0, 163, 64}

-- yiSyllableSsyx BMPString ::= {0, 0, 163, 65}

-- yiSyllableSsy BMPString ::= {0, 0, 163, 66}

-- yiSyllableSsyp BMPString ::= {0, 0, 163, 67}

-- yiSyllableSsyrx BMPString ::= {0, 0, 163, 68}

-- yiSyllableSsyr BMPString ::= {0, 0, 163, 69}

-- yiSyllableZhat BMPString ::= {0, 0, 163, 70}

-- yiSyllableZhax BMPString ::= {0, 0, 163, 71}

-- yiSyllableZha BMPString ::= {0, 0, 163, 72}

-- yiSyllableZhap BMPString ::= {0, 0, 163, 73}

-- yiSyllableZhuox BMPString ::= {0, 0, 163, 74}

-- yiSyllableZhuo BMPString ::= {0, 0, 163, 75}

-- yiSyllableZhuop BMPString ::= {0, 0, 163, 76}

-- yiSyllableZhot BMPString ::= {0, 0, 163, 77}

-- yiSyllableZhox BMPString ::= {0, 0, 163, 78}

-- yiSyllableZho BMPString ::= {0, 0, 163, 79}

-- yiSyllableZhop BMPString ::= {0, 0, 163, 80}

-- yiSyllableZhet BMPString ::= {0, 0, 163, 81}

-- yiSyllableZhex BMPString ::= {0, 0, 163, 82}

-- yiSyllableZhe BMPString ::= {0, 0, 163, 83}

-- yiSyllableZhep BMPString ::= {0, 0, 163, 84}

-- yiSyllableZhut BMPString ::= {0, 0, 163, 85}

-- yiSyllableZhux BMPString ::= {0, 0, 163, 86}

-- yiSyllableZhu BMPString ::= {0, 0, 163, 87}

-- yiSyllableZhup BMPString ::= {0, 0, 163, 88}

-- yiSyllableZhurx BMPString ::= {0, 0, 163, 89}

-- yiSyllableZhur BMPString ::= {0, 0, 163, 90}

-- yiSyllableZhyt BMPString ::= {0, 0, 163, 91}

-- yiSyllableZhyx BMPString ::= {0, 0, 163, 92}

-- yiSyllableZhy BMPString ::= {0, 0, 163, 93}

-- yiSyllableZhyp BMPString ::= {0, 0, 163, 94}

-- yiSyllableZhyrx BMPString ::= {0, 0, 163, 95}

-- yiSyllableZhyr BMPString ::= {0, 0, 163, 96}

-- yiSyllableChat BMPString ::= {0, 0, 163, 97}

-- yiSyllableChax BMPString ::= {0, 0, 163, 98}

-- yiSyllableCha BMPString ::= {0, 0, 163, 99}

-- yiSyllableChap BMPString ::= {0, 0, 163, 100}

-- yiSyllableChuot BMPString ::= {0, 0, 163, 101}

-- yiSyllableChuox BMPString ::= {0, 0, 163, 102}

-- yiSyllableChuo BMPString ::= {0, 0, 163, 103}

-- yiSyllableChuop BMPString ::= {0, 0, 163, 104}

-- yiSyllableChot BMPString ::= {0, 0, 163, 105}

-- yiSyllableChox BMPString ::= {0, 0, 163, 106}

-- yiSyllableCho BMPString ::= {0, 0, 163, 107}

-- yiSyllableChop BMPString ::= {0, 0, 163, 108}

-- yiSyllableChet BMPString ::= {0, 0, 163, 109}

-- yiSyllableChex BMPString ::= {0, 0, 163, 110}

-- yiSyllableChe BMPString ::= {0, 0, 163, 111}

-- yiSyllableChep BMPString ::= {0, 0, 163, 112}

-- yiSyllableChux BMPString ::= {0, 0, 163, 113}

-- yiSyllableChu BMPString ::= {0, 0, 163, 114}

-- yiSyllableChup BMPString ::= {0, 0, 163, 115}

-- yiSyllableChurx BMPString ::= {0, 0, 163, 116}

-- yiSyllableChur BMPString ::= {0, 0, 163, 117}

-- yiSyllableChyt BMPString ::= {0, 0, 163, 118}

-- yiSyllableChyx BMPString ::= {0, 0, 163, 119}

-- yiSyllableChy BMPString ::= {0, 0, 163, 120}

-- yiSyllableChyp BMPString ::= {0, 0, 163, 121}

-- yiSyllableChyrx BMPString ::= {0, 0, 163, 122}

-- yiSyllableChyr BMPString ::= {0, 0, 163, 123}

-- yiSyllableRrax BMPString ::= {0, 0, 163, 124}

-- yiSyllableRra BMPString ::= {0, 0, 163, 125}

-- yiSyllableRruox BMPString ::= {0, 0, 163, 126}

-- yiSyllableRruo BMPString ::= {0, 0, 163, 127}

-- yiSyllableRrot BMPString ::= {0, 0, 163, 128}

-- yiSyllableRrox BMPString ::= {0, 0, 163, 129}

-- yiSyllableRro BMPString ::= {0, 0, 163, 130}

-- yiSyllableRrop BMPString ::= {0, 0, 163, 131}

-- yiSyllableRret BMPString ::= {0, 0, 163, 132}

-- yiSyllableRrex BMPString ::= {0, 0, 163, 133}

-- yiSyllableRre BMPString ::= {0, 0, 163, 134}

-- yiSyllableRrep BMPString ::= {0, 0, 163, 135}

-- yiSyllableRrut BMPString ::= {0, 0, 163, 136}

-- yiSyllableRrux BMPString ::= {0, 0, 163, 137}

-- yiSyllableRru BMPString ::= {0, 0, 163, 138}

-- yiSyllableRrup BMPString ::= {0, 0, 163, 139}

-- yiSyllableRrurx BMPString ::= {0, 0, 163, 140}

-- yiSyllableRrur BMPString ::= {0, 0, 163, 141}

-- yiSyllableRryt BMPString ::= {0, 0, 163, 142}

-- yiSyllableRryx BMPString ::= {0, 0, 163, 143}

-- yiSyllableRry BMPString ::= {0, 0, 163, 144}

-- yiSyllableRryp BMPString ::= {0, 0, 163, 145}

-- yiSyllableRryrx BMPString ::= {0, 0, 163, 146}

-- yiSyllableRryr BMPString ::= {0, 0, 163, 147}

-- yiSyllableNrat BMPString ::= {0, 0, 163, 148}

-- yiSyllableNrax BMPString ::= {0, 0, 163, 149}

-- yiSyllableNra BMPString ::= {0, 0, 163, 150}

-- yiSyllableNrap BMPString ::= {0, 0, 163, 151}

-- yiSyllableNrox BMPString ::= {0, 0, 163, 152}

-- yiSyllableNro BMPString ::= {0, 0, 163, 153}

-- yiSyllableNrop BMPString ::= {0, 0, 163, 154}

-- yiSyllableNret BMPString ::= {0, 0, 163, 155}

-- yiSyllableNrex BMPString ::= {0, 0, 163, 156}

-- yiSyllableNre BMPString ::= {0, 0, 163, 157}

-- yiSyllableNrep BMPString ::= {0, 0, 163, 158}

-- yiSyllableNrut BMPString ::= {0, 0, 163, 159}

-- yiSyllableNrux BMPString ::= {0, 0, 163, 160}

-- yiSyllableNru BMPString ::= {0, 0, 163, 161}

-- yiSyllableNrup BMPString ::= {0, 0, 163, 162}

-- yiSyllableNrurx BMPString ::= {0, 0, 163, 163}

-- yiSyllableNrur BMPString ::= {0, 0, 163, 164}

-- yiSyllableNryt BMPString ::= {0, 0, 163, 165}

-- yiSyllableNryx BMPString ::= {0, 0, 163, 166}

-- yiSyllableNry BMPString ::= {0, 0, 163, 167}

-- yiSyllableNryp BMPString ::= {0, 0, 163, 168}

-- yiSyllableNryrx BMPString ::= {0, 0, 163, 169}

-- yiSyllableNryr BMPString ::= {0, 0, 163, 170}

-- yiSyllableShat BMPString ::= {0, 0, 163, 171}

-- yiSyllableShax BMPString ::= {0, 0, 163, 172}

-- yiSyllableSha BMPString ::= {0, 0, 163, 173}

-- yiSyllableShap BMPString ::= {0, 0, 163, 174}

-- yiSyllableShuox BMPString ::= {0, 0, 163, 175}

-- yiSyllableShuo BMPString ::= {0, 0, 163, 176}

-- yiSyllableShuop BMPString ::= {0, 0, 163, 177}

-- yiSyllableShot BMPString ::= {0, 0, 163, 178}

-- yiSyllableShox BMPString ::= {0, 0, 163, 179}

-- yiSyllableSho BMPString ::= {0, 0, 163, 180}

-- yiSyllableShop BMPString ::= {0, 0, 163, 181}

-- yiSyllableShet BMPString ::= {0, 0, 163, 182}

-- yiSyllableShex BMPString ::= {0, 0, 163, 183}

-- yiSyllableShe BMPString ::= {0, 0, 163, 184}

-- yiSyllableShep BMPString ::= {0, 0, 163, 185}

-- yiSyllableShut BMPString ::= {0, 0, 163, 186}

-- yiSyllableShux BMPString ::= {0, 0, 163, 187}

-- yiSyllableShu BMPString ::= {0, 0, 163, 188}

-- yiSyllableShup BMPString ::= {0, 0, 163, 189}

-- yiSyllableShurx BMPString ::= {0, 0, 163, 190}

-- yiSyllableShur BMPString ::= {0, 0, 163, 191}

-- yiSyllableShyt BMPString ::= {0, 0, 163, 192}

-- yiSyllableShyx BMPString ::= {0, 0, 163, 193}

-- yiSyllableShy BMPString ::= {0, 0, 163, 194}

-- yiSyllableShyp BMPString ::= {0, 0, 163, 195}

-- yiSyllableShyrx BMPString ::= {0, 0, 163, 196}

-- yiSyllableShyr BMPString ::= {0, 0, 163, 197}

-- yiSyllableRat BMPString ::= {0, 0, 163, 198}

-- yiSyllableRax BMPString ::= {0, 0, 163, 199}

-- yiSyllableRa BMPString ::= {0, 0, 163, 200}

-- yiSyllableRap BMPString ::= {0, 0, 163, 201}

-- yiSyllableRuox BMPString ::= {0, 0, 163, 202}

-- yiSyllableRuo BMPString ::= {0, 0, 163, 203}

-- yiSyllableRuop BMPString ::= {0, 0, 163, 204}

-- yiSyllableRot BMPString ::= {0, 0, 163, 205}

-- yiSyllableRox BMPString ::= {0, 0, 163, 206}

-- yiSyllableRo BMPString ::= {0, 0, 163, 207}

-- yiSyllableRop BMPString ::= {0, 0, 163, 208}

-- yiSyllableRex BMPString ::= {0, 0, 163, 209}

-- yiSyllableRe BMPString ::= {0, 0, 163, 210}

-- yiSyllableRep BMPString ::= {0, 0, 163, 211}

-- yiSyllableRut BMPString ::= {0, 0, 163, 212}

-- yiSyllableRux BMPString ::= {0, 0, 163, 213}

-- yiSyllableRu BMPString ::= {0, 0, 163, 214}

-- yiSyllableRup BMPString ::= {0, 0, 163, 215}

-- yiSyllableRurx BMPString ::= {0, 0, 163, 216}

-- yiSyllableRur BMPString ::= {0, 0, 163, 217}

-- yiSyllableRyt BMPString ::= {0, 0, 163, 218}

-- yiSyllableRyx BMPString ::= {0, 0, 163, 219}

-- yiSyllableRy BMPString ::= {0, 0, 163, 220}

-- yiSyllableRyp BMPString ::= {0, 0, 163, 221}

-- yiSyllableRyrx BMPString ::= {0, 0, 163, 222}

-- yiSyllableRyr BMPString ::= {0, 0, 163, 223}

-- yiSyllableJit BMPString ::= {0, 0, 163, 224}

-- yiSyllableJix BMPString ::= {0, 0, 163, 225}

-- yiSyllableJi BMPString ::= {0, 0, 163, 226}

-- yiSyllableJip BMPString ::= {0, 0, 163, 227}

-- yiSyllableJiet BMPString ::= {0, 0, 163, 228}

-- yiSyllableJiex BMPString ::= {0, 0, 163, 229}

-- yiSyllableJie BMPString ::= {0, 0, 163, 230}

-- yiSyllableJiep BMPString ::= {0, 0, 163, 231}

-- yiSyllableJuot BMPString ::= {0, 0, 163, 232}

-- yiSyllableJuox BMPString ::= {0, 0, 163, 233}

-- yiSyllableJuo BMPString ::= {0, 0, 163, 234}

-- yiSyllableJuop BMPString ::= {0, 0, 163, 235}

-- yiSyllableJot BMPString ::= {0, 0, 163, 236}

-- yiSyllableJox BMPString ::= {0, 0, 163, 237}

-- yiSyllableJo BMPString ::= {0, 0, 163, 238}

-- yiSyllableJop BMPString ::= {0, 0, 163, 239}

-- yiSyllableJut BMPString ::= {0, 0, 163, 240}

-- yiSyllableJux BMPString ::= {0, 0, 163, 241}

-- yiSyllableJu BMPString ::= {0, 0, 163, 242}

-- yiSyllableJup BMPString ::= {0, 0, 163, 243}

-- yiSyllableJurx BMPString ::= {0, 0, 163, 244}

-- yiSyllableJur BMPString ::= {0, 0, 163, 245}

-- yiSyllableJyt BMPString ::= {0, 0, 163, 246}

-- yiSyllableJyx BMPString ::= {0, 0, 163, 247}

-- yiSyllableJy BMPString ::= {0, 0, 163, 248}

-- yiSyllableJyp BMPString ::= {0, 0, 163, 249}

-- yiSyllableJyrx BMPString ::= {0, 0, 163, 250}

-- yiSyllableJyr BMPString ::= {0, 0, 163, 251}

-- yiSyllableQit BMPString ::= {0, 0, 163, 252}

-- yiSyllableQix BMPString ::= {0, 0, 163, 253}

-- yiSyllableQi BMPString ::= {0, 0, 163, 254}

-- yiSyllableQip BMPString ::= {0, 0, 163, 255}

-- yiSyllableQiet BMPString ::= {0, 0, 164, 0}

-- yiSyllableQiex BMPString ::= {0, 0, 164, 1}

-- yiSyllableQie BMPString ::= {0, 0, 164, 2}

-- yiSyllableQiep BMPString ::= {0, 0, 164, 3}

-- yiSyllableQuot BMPString ::= {0, 0, 164, 4}

-- yiSyllableQuox BMPString ::= {0, 0, 164, 5}

-- yiSyllableQuo BMPString ::= {0, 0, 164, 6}

-- yiSyllableQuop BMPString ::= {0, 0, 164, 7}

-- yiSyllableQot BMPString ::= {0, 0, 164, 8}

-- yiSyllableQox BMPString ::= {0, 0, 164, 9}

-- yiSyllableQo BMPString ::= {0, 0, 164, 10}

-- yiSyllableQop BMPString ::= {0, 0, 164, 11}

-- yiSyllableQut BMPString ::= {0, 0, 164, 12}

-- yiSyllableQux BMPString ::= {0, 0, 164, 13}

-- yiSyllableQu BMPString ::= {0, 0, 164, 14}

-- yiSyllableQup BMPString ::= {0, 0, 164, 15}

-- yiSyllableQurx BMPString ::= {0, 0, 164, 16}

-- yiSyllableQur BMPString ::= {0, 0, 164, 17}

-- yiSyllableQyt BMPString ::= {0, 0, 164, 18}

-- yiSyllableQyx BMPString ::= {0, 0, 164, 19}

-- yiSyllableQy BMPString ::= {0, 0, 164, 20}

-- yiSyllableQyp BMPString ::= {0, 0, 164, 21}

-- yiSyllableQyrx BMPString ::= {0, 0, 164, 22}

-- yiSyllableQyr BMPString ::= {0, 0, 164, 23}

-- yiSyllableJjit BMPString ::= {0, 0, 164, 24}

-- yiSyllableJjix BMPString ::= {0, 0, 164, 25}

-- yiSyllableJji BMPString ::= {0, 0, 164, 26}

-- yiSyllableJjip BMPString ::= {0, 0, 164, 27}

-- yiSyllableJjiet BMPString ::= {0, 0, 164, 28}

-- yiSyllableJjiex BMPString ::= {0, 0, 164, 29}

-- yiSyllableJjie BMPString ::= {0, 0, 164, 30}

-- yiSyllableJjiep BMPString ::= {0, 0, 164, 31}

-- yiSyllableJjuox BMPString ::= {0, 0, 164, 32}

-- yiSyllableJjuo BMPString ::= {0, 0, 164, 33}

-- yiSyllableJjuop BMPString ::= {0, 0, 164, 34}

-- yiSyllableJjot BMPString ::= {0, 0, 164, 35}

-- yiSyllableJjox BMPString ::= {0, 0, 164, 36}

-- yiSyllableJjo BMPString ::= {0, 0, 164, 37}

-- yiSyllableJjop BMPString ::= {0, 0, 164, 38}

-- yiSyllableJjut BMPString ::= {0, 0, 164, 39}

-- yiSyllableJjux BMPString ::= {0, 0, 164, 40}

-- yiSyllableJju BMPString ::= {0, 0, 164, 41}

-- yiSyllableJjup BMPString ::= {0, 0, 164, 42}

-- yiSyllableJjurx BMPString ::= {0, 0, 164, 43}

-- yiSyllableJjur BMPString ::= {0, 0, 164, 44}

-- yiSyllableJjyt BMPString ::= {0, 0, 164, 45}

-- yiSyllableJjyx BMPString ::= {0, 0, 164, 46}

-- yiSyllableJjy BMPString ::= {0, 0, 164, 47}

-- yiSyllableJjyp BMPString ::= {0, 0, 164, 48}

-- yiSyllableNjit BMPString ::= {0, 0, 164, 49}

-- yiSyllableNjix BMPString ::= {0, 0, 164, 50}

-- yiSyllableNji BMPString ::= {0, 0, 164, 51}

-- yiSyllableNjip BMPString ::= {0, 0, 164, 52}

-- yiSyllableNjiet BMPString ::= {0, 0, 164, 53}

-- yiSyllableNjiex BMPString ::= {0, 0, 164, 54}

-- yiSyllableNjie BMPString ::= {0, 0, 164, 55}

-- yiSyllableNjiep BMPString ::= {0, 0, 164, 56}

-- yiSyllableNjuox BMPString ::= {0, 0, 164, 57}

-- yiSyllableNjuo BMPString ::= {0, 0, 164, 58}

-- yiSyllableNjot BMPString ::= {0, 0, 164, 59}

-- yiSyllableNjox BMPString ::= {0, 0, 164, 60}

-- yiSyllableNjo BMPString ::= {0, 0, 164, 61}

-- yiSyllableNjop BMPString ::= {0, 0, 164, 62}

-- yiSyllableNjux BMPString ::= {0, 0, 164, 63}

-- yiSyllableNju BMPString ::= {0, 0, 164, 64}

-- yiSyllableNjup BMPString ::= {0, 0, 164, 65}

-- yiSyllableNjurx BMPString ::= {0, 0, 164, 66}

-- yiSyllableNjur BMPString ::= {0, 0, 164, 67}

-- yiSyllableNjyt BMPString ::= {0, 0, 164, 68}

-- yiSyllableNjyx BMPString ::= {0, 0, 164, 69}

-- yiSyllableNjy BMPString ::= {0, 0, 164, 70}

-- yiSyllableNjyp BMPString ::= {0, 0, 164, 71}

-- yiSyllableNjyrx BMPString ::= {0, 0, 164, 72}

-- yiSyllableNjyr BMPString ::= {0, 0, 164, 73}

-- yiSyllableNyit BMPString ::= {0, 0, 164, 74}

-- yiSyllableNyix BMPString ::= {0, 0, 164, 75}

-- yiSyllableNyi BMPString ::= {0, 0, 164, 76}

-- yiSyllableNyip BMPString ::= {0, 0, 164, 77}

-- yiSyllableNyiet BMPString ::= {0, 0, 164, 78}

-- yiSyllableNyiex BMPString ::= {0, 0, 164, 79}

-- yiSyllableNyie BMPString ::= {0, 0, 164, 80}

-- yiSyllableNyiep BMPString ::= {0, 0, 164, 81}

-- yiSyllableNyuox BMPString ::= {0, 0, 164, 82}

-- yiSyllableNyuo BMPString ::= {0, 0, 164, 83}

-- yiSyllableNyuop BMPString ::= {0, 0, 164, 84}

-- yiSyllableNyot BMPString ::= {0, 0, 164, 85}

-- yiSyllableNyox BMPString ::= {0, 0, 164, 86}

-- yiSyllableNyo BMPString ::= {0, 0, 164, 87}

-- yiSyllableNyop BMPString ::= {0, 0, 164, 88}

-- yiSyllableNyut BMPString ::= {0, 0, 164, 89}

-- yiSyllableNyux BMPString ::= {0, 0, 164, 90}

-- yiSyllableNyu BMPString ::= {0, 0, 164, 91}

-- yiSyllableNyup BMPString ::= {0, 0, 164, 92}

-- yiSyllableXit BMPString ::= {0, 0, 164, 93}

-- yiSyllableXix BMPString ::= {0, 0, 164, 94}

-- yiSyllableXi BMPString ::= {0, 0, 164, 95}

-- yiSyllableXip BMPString ::= {0, 0, 164, 96}

-- yiSyllableXiet BMPString ::= {0, 0, 164, 97}

-- yiSyllableXiex BMPString ::= {0, 0, 164, 98}

-- yiSyllableXie BMPString ::= {0, 0, 164, 99}

-- yiSyllableXiep BMPString ::= {0, 0, 164, 100}

-- yiSyllableXuox BMPString ::= {0, 0, 164, 101}

-- yiSyllableXuo BMPString ::= {0, 0, 164, 102}

-- yiSyllableXot BMPString ::= {0, 0, 164, 103}

-- yiSyllableXox BMPString ::= {0, 0, 164, 104}

-- yiSyllableXo BMPString ::= {0, 0, 164, 105}

-- yiSyllableXop BMPString ::= {0, 0, 164, 106}

-- yiSyllableXyt BMPString ::= {0, 0, 164, 107}

-- yiSyllableXyx BMPString ::= {0, 0, 164, 108}

-- yiSyllableXy BMPString ::= {0, 0, 164, 109}

-- yiSyllableXyp BMPString ::= {0, 0, 164, 110}

-- yiSyllableXyrx BMPString ::= {0, 0, 164, 111}

-- yiSyllableXyr BMPString ::= {0, 0, 164, 112}

-- yiSyllableYit BMPString ::= {0, 0, 164, 113}

-- yiSyllableYix BMPString ::= {0, 0, 164, 114}

-- yiSyllableYi BMPString ::= {0, 0, 164, 115}

-- yiSyllableYip BMPString ::= {0, 0, 164, 116}

-- yiSyllableYiet BMPString ::= {0, 0, 164, 117}

-- yiSyllableYiex BMPString ::= {0, 0, 164, 118}

-- yiSyllableYie BMPString ::= {0, 0, 164, 119}

-- yiSyllableYiep BMPString ::= {0, 0, 164, 120}

-- yiSyllableYuot BMPString ::= {0, 0, 164, 121}

-- yiSyllableYuox BMPString ::= {0, 0, 164, 122}

-- yiSyllableYuo BMPString ::= {0, 0, 164, 123}

-- yiSyllableYuop BMPString ::= {0, 0, 164, 124}

-- yiSyllableYot BMPString ::= {0, 0, 164, 125}

-- yiSyllableYox BMPString ::= {0, 0, 164, 126}

-- yiSyllableYo BMPString ::= {0, 0, 164, 127}

-- yiSyllableYop BMPString ::= {0, 0, 164, 128}

-- yiSyllableYut BMPString ::= {0, 0, 164, 129}

-- yiSyllableYux BMPString ::= {0, 0, 164, 130}

-- yiSyllableYu BMPString ::= {0, 0, 164, 131}

-- yiSyllableYup BMPString ::= {0, 0, 164, 132}

-- yiSyllableYurx BMPString ::= {0, 0, 164, 133}

-- yiSyllableYur BMPString ::= {0, 0, 164, 134}

-- yiSyllableYyt BMPString ::= {0, 0, 164, 135}

-- yiSyllableYyx BMPString ::= {0, 0, 164, 136}

-- yiSyllableYy BMPString ::= {0, 0, 164, 137}

-- yiSyllableYyp BMPString ::= {0, 0, 164, 138}

-- yiSyllableYyrx BMPString ::= {0, 0, 164, 139}

-- yiSyllableYyr BMPString ::= {0, 0, 164, 140}

-- yiRadicalQot BMPString ::= {0, 0, 164, 144}

-- yiRadicalLi BMPString ::= {0, 0, 164, 145}

-- yiRadicalKit BMPString ::= {0, 0, 164, 146}

-- yiRadicalNyip BMPString ::= {0, 0, 164, 147}

-- yiRadicalCyp BMPString ::= {0, 0, 164, 148}

-- yiRadicalSsi BMPString ::= {0, 0, 164, 149}

-- yiRadicalGgop BMPString ::= {0, 0, 164, 150}

-- yiRadicalGep BMPString ::= {0, 0, 164, 151}

-- yiRadicalMi BMPString ::= {0, 0, 164, 152}

-- yiRadicalHxit BMPString ::= {0, 0, 164, 153}

-- yiRadicalLyr BMPString ::= {0, 0, 164, 154}

-- yiRadicalBbut BMPString ::= {0, 0, 164, 155}

-- yiRadicalMop BMPString ::= {0, 0, 164, 156}

-- yiRadicalYo BMPString ::= {0, 0, 164, 157}

-- yiRadicalPut BMPString ::= {0, 0, 164, 158}

-- yiRadicalHxuo BMPString ::= {0, 0, 164, 159}

-- yiRadicalTat BMPString ::= {0, 0, 164, 160}

-- yiRadicalGa BMPString ::= {0, 0, 164, 161}

-- yiRadicalZup BMPString ::= {0, 0, 164, 162}

-- yiRadicalCyt BMPString ::= {0, 0, 164, 163}

-- yiRadicalDdur BMPString ::= {0, 0, 164, 164}

-- yiRadicalBur BMPString ::= {0, 0, 164, 165}

-- yiRadicalGguo BMPString ::= {0, 0, 164, 166}

-- yiRadicalNyop BMPString ::= {0, 0, 164, 167}

-- yiRadicalTu BMPString ::= {0, 0, 164, 168}

-- yiRadicalOp BMPString ::= {0, 0, 164, 169}

-- yiRadicalJjut BMPString ::= {0, 0, 164, 170}

-- yiRadicalZot BMPString ::= {0, 0, 164, 171}

-- yiRadicalPyt BMPString ::= {0, 0, 164, 172}

-- yiRadicalHmo BMPString ::= {0, 0, 164, 173}

-- yiRadicalYit BMPString ::= {0, 0, 164, 174}

-- yiRadicalVur BMPString ::= {0, 0, 164, 175}

-- yiRadicalShy BMPString ::= {0, 0, 164, 176}

-- yiRadicalVep BMPString ::= {0, 0, 164, 177}

-- yiRadicalZa BMPString ::= {0, 0, 164, 178}

-- yiRadicalJo BMPString ::= {0, 0, 164, 179}

-- yiRadicalNzup BMPString ::= {0, 0, 164, 180}

-- yiRadicalJjy BMPString ::= {0, 0, 164, 181}

-- yiRadicalGot BMPString ::= {0, 0, 164, 182}

-- yiRadicalJjie BMPString ::= {0, 0, 164, 183}

-- yiRadicalWo BMPString ::= {0, 0, 164, 184}

-- yiRadicalDu BMPString ::= {0, 0, 164, 185}

-- yiRadicalShur BMPString ::= {0, 0, 164, 186}

-- yiRadicalLie BMPString ::= {0, 0, 164, 187}

-- yiRadicalCy BMPString ::= {0, 0, 164, 188}

-- yiRadicalCuop BMPString ::= {0, 0, 164, 189}

-- yiRadicalCip BMPString ::= {0, 0, 164, 190}

-- yiRadicalHxop BMPString ::= {0, 0, 164, 191}

-- yiRadicalShat BMPString ::= {0, 0, 164, 192}

-- yiRadicalZur BMPString ::= {0, 0, 164, 193}

-- yiRadicalShop BMPString ::= {0, 0, 164, 194}

-- yiRadicalChe BMPString ::= {0, 0, 164, 195}

-- yiRadicalZziet BMPString ::= {0, 0, 164, 196}

-- yiRadicalNbie BMPString ::= {0, 0, 164, 197}

-- yiRadicalKe BMPString ::= {0, 0, 164, 198}

-- cjkCompatibilityIdeograph-f900 BMPString ::= {0, 0, 249, 0}

-- cjkCompatibilityIdeograph-f901 BMPString ::= {0, 0, 249, 1}

-- cjkCompatibilityIdeograph-f902 BMPString ::= {0, 0, 249, 2}

-- cjkCompatibilityIdeograph-f903 BMPString ::= {0, 0, 249, 3}

-- cjkCompatibilityIdeograph-f904 BMPString ::= {0, 0, 249, 4}

-- cjkCompatibilityIdeograph-f905 BMPString ::= {0, 0, 249, 5}

-- cjkCompatibilityIdeograph-f906 BMPString ::= {0, 0, 249, 6}

-- cjkCompatibilityIdeograph-f907 BMPString ::= {0, 0, 249, 7}

-- cjkCompatibilityIdeograph-f908 BMPString ::= {0, 0, 249, 8}

-- cjkCompatibilityIdeograph-f909 BMPString ::= {0, 0, 249, 9}

-- cjkCompatibilityIdeograph-f90a BMPString ::= {0, 0, 249, 10}

-- cjkCompatibilityIdeograph-f90b BMPString ::= {0, 0, 249, 11}

-- cjkCompatibilityIdeograph-f90c BMPString ::= {0, 0, 249, 12}

-- cjkCompatibilityIdeograph-f90d BMPString ::= {0, 0, 249, 13}

-- cjkCompatibilityIdeograph-f90e BMPString ::= {0, 0, 249, 14}

-- cjkCompatibilityIdeograph-f90f BMPString ::= {0, 0, 249, 15}

-- cjkCompatibilityIdeograph-f910 BMPString ::= {0, 0, 249, 16}

-- cjkCompatibilityIdeograph-f911 BMPString ::= {0, 0, 249, 17}

-- cjkCompatibilityIdeograph-f912 BMPString ::= {0, 0, 249, 18}

-- cjkCompatibilityIdeograph-f913 BMPString ::= {0, 0, 249, 19}

-- cjkCompatibilityIdeograph-f914 BMPString ::= {0, 0, 249, 20}

-- cjkCompatibilityIdeograph-f915 BMPString ::= {0, 0, 249, 21}

-- cjkCompatibilityIdeograph-f916 BMPString ::= {0, 0, 249, 22}

-- cjkCompatibilityIdeograph-f917 BMPString ::= {0, 0, 249, 23}

-- cjkCompatibilityIdeograph-f918 BMPString ::= {0, 0, 249, 24}

-- cjkCompatibilityIdeograph-f919 BMPString ::= {0, 0, 249, 25}

-- cjkCompatibilityIdeograph-f91a BMPString ::= {0, 0, 249, 26}

-- cjkCompatibilityIdeograph-f91b BMPString ::= {0, 0, 249, 27}

-- cjkCompatibilityIdeograph-f91c BMPString ::= {0, 0, 249, 28}

-- cjkCompatibilityIdeograph-f91d BMPString ::= {0, 0, 249, 29}

-- cjkCompatibilityIdeograph-f91e BMPString ::= {0, 0, 249, 30}

-- cjkCompatibilityIdeograph-f91f BMPString ::= {0, 0, 249, 31}

-- cjkCompatibilityIdeograph-f920 BMPString ::= {0, 0, 249, 32}

-- cjkCompatibilityIdeograph-f921 BMPString ::= {0, 0, 249, 33}

-- cjkCompatibilityIdeograph-f922 BMPString ::= {0, 0, 249, 34}

-- cjkCompatibilityIdeograph-f923 BMPString ::= {0, 0, 249, 35}

-- cjkCompatibilityIdeograph-f924 BMPString ::= {0, 0, 249, 36}

-- cjkCompatibilityIdeograph-f925 BMPString ::= {0, 0, 249, 37}

-- cjkCompatibilityIdeograph-f926 BMPString ::= {0, 0, 249, 38}

-- cjkCompatibilityIdeograph-f927 BMPString ::= {0, 0, 249, 39}

-- cjkCompatibilityIdeograph-f928 BMPString ::= {0, 0, 249, 40}

-- cjkCompatibilityIdeograph-f929 BMPString ::= {0, 0, 249, 41}

-- cjkCompatibilityIdeograph-f92a BMPString ::= {0, 0, 249, 42}

-- cjkCompatibilityIdeograph-f92b BMPString ::= {0, 0, 249, 43}

-- cjkCompatibilityIdeograph-f92c BMPString ::= {0, 0, 249, 44}

-- cjkCompatibilityIdeograph-f92d BMPString ::= {0, 0, 249, 45}

-- cjkCompatibilityIdeograph-f92e BMPString ::= {0, 0, 249, 46}

-- cjkCompatibilityIdeograph-f92f BMPString ::= {0, 0, 249, 47}

-- cjkCompatibilityIdeograph-f930 BMPString ::= {0, 0, 249, 48}

-- cjkCompatibilityIdeograph-f931 BMPString ::= {0, 0, 249, 49}

-- cjkCompatibilityIdeograph-f932 BMPString ::= {0, 0, 249, 50}

-- cjkCompatibilityIdeograph-f933 BMPString ::= {0, 0, 249, 51}

-- cjkCompatibilityIdeograph-f934 BMPString ::= {0, 0, 249, 52}

-- cjkCompatibilityIdeograph-f935 BMPString ::= {0, 0, 249, 53}

-- cjkCompatibilityIdeograph-f936 BMPString ::= {0, 0, 249, 54}

-- cjkCompatibilityIdeograph-f937 BMPString ::= {0, 0, 249, 55}

-- cjkCompatibilityIdeograph-f938 BMPString ::= {0, 0, 249, 56}

-- cjkCompatibilityIdeograph-f939 BMPString ::= {0, 0, 249, 57}

-- cjkCompatibilityIdeograph-f93a BMPString ::= {0, 0, 249, 58}

-- cjkCompatibilityIdeograph-f93b BMPString ::= {0, 0, 249, 59}

-- cjkCompatibilityIdeograph-f93c BMPString ::= {0, 0, 249, 60}

-- cjkCompatibilityIdeograph-f93d BMPString ::= {0, 0, 249, 61}

-- cjkCompatibilityIdeograph-f93e BMPString ::= {0, 0, 249, 62}

-- cjkCompatibilityIdeograph-f93f BMPString ::= {0, 0, 249, 63}

-- cjkCompatibilityIdeograph-f940 BMPString ::= {0, 0, 249, 64}

-- cjkCompatibilityIdeograph-f941 BMPString ::= {0, 0, 249, 65}

-- cjkCompatibilityIdeograph-f942 BMPString ::= {0, 0, 249, 66}

-- cjkCompatibilityIdeograph-f943 BMPString ::= {0, 0, 249, 67}

-- cjkCompatibilityIdeograph-f944 BMPString ::= {0, 0, 249, 68}

-- cjkCompatibilityIdeograph-f945 BMPString ::= {0, 0, 249, 69}

-- cjkCompatibilityIdeograph-f946 BMPString ::= {0, 0, 249, 70}

-- cjkCompatibilityIdeograph-f947 BMPString ::= {0, 0, 249, 71}

-- cjkCompatibilityIdeograph-f948 BMPString ::= {0, 0, 249, 72}

-- cjkCompatibilityIdeograph-f949 BMPString ::= {0, 0, 249, 73}

-- cjkCompatibilityIdeograph-f94a BMPString ::= {0, 0, 249, 74}

-- cjkCompatibilityIdeograph-f94b BMPString ::= {0, 0, 249, 75}

-- cjkCompatibilityIdeograph-f94c BMPString ::= {0, 0, 249, 76}

-- cjkCompatibilityIdeograph-f94d BMPString ::= {0, 0, 249, 77}

-- cjkCompatibilityIdeograph-f94e BMPString ::= {0, 0, 249, 78}

-- cjkCompatibilityIdeograph-f94f BMPString ::= {0, 0, 249, 79}

-- cjkCompatibilityIdeograph-f950 BMPString ::= {0, 0, 249, 80}

-- cjkCompatibilityIdeograph-f951 BMPString ::= {0, 0, 249, 81}

-- cjkCompatibilityIdeograph-f952 BMPString ::= {0, 0, 249, 82}

-- cjkCompatibilityIdeograph-f953 BMPString ::= {0, 0, 249, 83}

-- cjkCompatibilityIdeograph-f954 BMPString ::= {0, 0, 249, 84}

-- cjkCompatibilityIdeograph-f955 BMPString ::= {0, 0, 249, 85}

-- cjkCompatibilityIdeograph-f956 BMPString ::= {0, 0, 249, 86}

-- cjkCompatibilityIdeograph-f957 BMPString ::= {0, 0, 249, 87}

-- cjkCompatibilityIdeograph-f958 BMPString ::= {0, 0, 249, 88}

-- cjkCompatibilityIdeograph-f959 BMPString ::= {0, 0, 249, 89}

-- cjkCompatibilityIdeograph-f95a BMPString ::= {0, 0, 249, 90}

-- cjkCompatibilityIdeograph-f95b BMPString ::= {0, 0, 249, 91}

-- cjkCompatibilityIdeograph-f95c BMPString ::= {0, 0, 249, 92}

-- cjkCompatibilityIdeograph-f95d BMPString ::= {0, 0, 249, 93}

-- cjkCompatibilityIdeograph-f95e BMPString ::= {0, 0, 249, 94}

-- cjkCompatibilityIdeograph-f95f BMPString ::= {0, 0, 249, 95}

-- cjkCompatibilityIdeograph-f960 BMPString ::= {0, 0, 249, 96}

-- cjkCompatibilityIdeograph-f961 BMPString ::= {0, 0, 249, 97}

-- cjkCompatibilityIdeograph-f962 BMPString ::= {0, 0, 249, 98}

-- cjkCompatibilityIdeograph-f963 BMPString ::= {0, 0, 249, 99}

-- cjkCompatibilityIdeograph-f964 BMPString ::= {0, 0, 249, 100}

-- cjkCompatibilityIdeograph-f965 BMPString ::= {0, 0, 249, 101}

-- cjkCompatibilityIdeograph-f966 BMPString ::= {0, 0, 249, 102}

-- cjkCompatibilityIdeograph-f967 BMPString ::= {0, 0, 249, 103}

-- cjkCompatibilityIdeograph-f968 BMPString ::= {0, 0, 249, 104}

-- cjkCompatibilityIdeograph-f969 BMPString ::= {0, 0, 249, 105}

-- cjkCompatibilityIdeograph-f96a BMPString ::= {0, 0, 249, 106}

-- cjkCompatibilityIdeograph-f96b BMPString ::= {0, 0, 249, 107}

-- cjkCompatibilityIdeograph-f96c BMPString ::= {0, 0, 249, 108}

-- cjkCompatibilityIdeograph-f96d BMPString ::= {0, 0, 249, 109}

-- cjkCompatibilityIdeograph-f96e BMPString ::= {0, 0, 249, 110}

-- cjkCompatibilityIdeograph-f96f BMPString ::= {0, 0, 249, 111}

-- cjkCompatibilityIdeograph-f970 BMPString ::= {0, 0, 249, 112}

-- cjkCompatibilityIdeograph-f971 BMPString ::= {0, 0, 249, 113}

-- cjkCompatibilityIdeograph-f972 BMPString ::= {0, 0, 249, 114}

-- cjkCompatibilityIdeograph-f973 BMPString ::= {0, 0, 249, 115}

-- cjkCompatibilityIdeograph-f974 BMPString ::= {0, 0, 249, 116}

-- cjkCompatibilityIdeograph-f975 BMPString ::= {0, 0, 249, 117}

-- cjkCompatibilityIdeograph-f976 BMPString ::= {0, 0, 249, 118}

-- cjkCompatibilityIdeograph-f977 BMPString ::= {0, 0, 249, 119}

-- cjkCompatibilityIdeograph-f978 BMPString ::= {0, 0, 249, 120}

-- cjkCompatibilityIdeograph-f979 BMPString ::= {0, 0, 249, 121}

-- cjkCompatibilityIdeograph-f97a BMPString ::= {0, 0, 249, 122}

-- cjkCompatibilityIdeograph-f97b BMPString ::= {0, 0, 249, 123}

-- cjkCompatibilityIdeograph-f97c BMPString ::= {0, 0, 249, 124}

-- cjkCompatibilityIdeograph-f97d BMPString ::= {0, 0, 249, 125}

-- cjkCompatibilityIdeograph-f97e BMPString ::= {0, 0, 249, 126}

-- cjkCompatibilityIdeograph-f97f BMPString ::= {0, 0, 249, 127}

-- cjkCompatibilityIdeograph-f980 BMPString ::= {0, 0, 249, 128}

-- cjkCompatibilityIdeograph-f981 BMPString ::= {0, 0, 249, 129}

-- cjkCompatibilityIdeograph-f982 BMPString ::= {0, 0, 249, 130}

-- cjkCompatibilityIdeograph-f983 BMPString ::= {0, 0, 249, 131}

-- cjkCompatibilityIdeograph-f984 BMPString ::= {0, 0, 249, 132}

-- cjkCompatibilityIdeograph-f985 BMPString ::= {0, 0, 249, 133}

-- cjkCompatibilityIdeograph-f986 BMPString ::= {0, 0, 249, 134}

-- cjkCompatibilityIdeograph-f987 BMPString ::= {0, 0, 249, 135}

-- cjkCompatibilityIdeograph-f988 BMPString ::= {0, 0, 249, 136}

-- cjkCompatibilityIdeograph-f989 BMPString ::= {0, 0, 249, 137}

-- cjkCompatibilityIdeograph-f98a BMPString ::= {0, 0, 249, 138}

-- cjkCompatibilityIdeograph-f98b BMPString ::= {0, 0, 249, 139}

-- cjkCompatibilityIdeograph-f98c BMPString ::= {0, 0, 249, 140}

-- cjkCompatibilityIdeograph-f98d BMPString ::= {0, 0, 249, 141}

-- cjkCompatibilityIdeograph-f98e BMPString ::= {0, 0, 249, 142}

-- cjkCompatibilityIdeograph-f98f BMPString ::= {0, 0, 249, 143}

-- cjkCompatibilityIdeograph-f990 BMPString ::= {0, 0, 249, 144}

-- cjkCompatibilityIdeograph-f991 BMPString ::= {0, 0, 249, 145}

-- cjkCompatibilityIdeograph-f992 BMPString ::= {0, 0, 249, 146}

-- cjkCompatibilityIdeograph-f993 BMPString ::= {0, 0, 249, 147}

-- cjkCompatibilityIdeograph-f994 BMPString ::= {0, 0, 249, 148}

-- cjkCompatibilityIdeograph-f995 BMPString ::= {0, 0, 249, 149}

-- cjkCompatibilityIdeograph-f996 BMPString ::= {0, 0, 249, 150}

-- cjkCompatibilityIdeograph-f997 BMPString ::= {0, 0, 249, 151}

-- cjkCompatibilityIdeograph-f998 BMPString ::= {0, 0, 249, 152}

-- cjkCompatibilityIdeograph-f999 BMPString ::= {0, 0, 249, 153}

-- cjkCompatibilityIdeograph-f99a BMPString ::= {0, 0, 249, 154}

-- cjkCompatibilityIdeograph-f99b BMPString ::= {0, 0, 249, 155}

-- cjkCompatibilityIdeograph-f99c BMPString ::= {0, 0, 249, 156}

-- cjkCompatibilityIdeograph-f99d BMPString ::= {0, 0, 249, 157}

-- cjkCompatibilityIdeograph-f99e BMPString ::= {0, 0, 249, 158}

-- cjkCompatibilityIdeograph-f99f BMPString ::= {0, 0, 249, 159}

-- cjkCompatibilityIdeograph-f9a0 BMPString ::= {0, 0, 249, 160}

-- cjkCompatibilityIdeograph-f9a1 BMPString ::= {0, 0, 249, 161}

-- cjkCompatibilityIdeograph-f9a2 BMPString ::= {0, 0, 249, 162}

-- cjkCompatibilityIdeograph-f9a3 BMPString ::= {0, 0, 249, 163}

-- cjkCompatibilityIdeograph-f9a4 BMPString ::= {0, 0, 249, 164}

-- cjkCompatibilityIdeograph-f9a5 BMPString ::= {0, 0, 249, 165}

-- cjkCompatibilityIdeograph-f9a6 BMPString ::= {0, 0, 249, 166}

-- cjkCompatibilityIdeograph-f9a7 BMPString ::= {0, 0, 249, 167}

-- cjkCompatibilityIdeograph-f9a8 BMPString ::= {0, 0, 249, 168}

-- cjkCompatibilityIdeograph-f9a9 BMPString ::= {0, 0, 249, 169}

-- cjkCompatibilityIdeograph-f9aa BMPString ::= {0, 0, 249, 170}

-- cjkCompatibilityIdeograph-f9ab BMPString ::= {0, 0, 249, 171}

-- cjkCompatibilityIdeograph-f9ac BMPString ::= {0, 0, 249, 172}

-- cjkCompatibilityIdeograph-f9ad BMPString ::= {0, 0, 249, 173}

-- cjkCompatibilityIdeograph-f9ae BMPString ::= {0, 0, 249, 174}

-- cjkCompatibilityIdeograph-f9af BMPString ::= {0, 0, 249, 175}

-- cjkCompatibilityIdeograph-f9b0 BMPString ::= {0, 0, 249, 176}

-- cjkCompatibilityIdeograph-f9b1 BMPString ::= {0, 0, 249, 177}

-- cjkCompatibilityIdeograph-f9b2 BMPString ::= {0, 0, 249, 178}

-- cjkCompatibilityIdeograph-f9b3 BMPString ::= {0, 0, 249, 179}

-- cjkCompatibilityIdeograph-f9b4 BMPString ::= {0, 0, 249, 180}

-- cjkCompatibilityIdeograph-f9b5 BMPString ::= {0, 0, 249, 181}

-- cjkCompatibilityIdeograph-f9b6 BMPString ::= {0, 0, 249, 182}

-- cjkCompatibilityIdeograph-f9b7 BMPString ::= {0, 0, 249, 183}

-- cjkCompatibilityIdeograph-f9b8 BMPString ::= {0, 0, 249, 184}

-- cjkCompatibilityIdeograph-f9b9 BMPString ::= {0, 0, 249, 185}

-- cjkCompatibilityIdeograph-f9ba BMPString ::= {0, 0, 249, 186}

-- cjkCompatibilityIdeograph-f9bb BMPString ::= {0, 0, 249, 187}

-- cjkCompatibilityIdeograph-f9bc BMPString ::= {0, 0, 249, 188}

-- cjkCompatibilityIdeograph-f9bd BMPString ::= {0, 0, 249, 189}

-- cjkCompatibilityIdeograph-f9be BMPString ::= {0, 0, 249, 190}

-- cjkCompatibilityIdeograph-f9bf BMPString ::= {0, 0, 249, 191}

-- cjkCompatibilityIdeograph-f9c0 BMPString ::= {0, 0, 249, 192}

-- cjkCompatibilityIdeograph-f9c1 BMPString ::= {0, 0, 249, 193}

-- cjkCompatibilityIdeograph-f9c2 BMPString ::= {0, 0, 249, 194}

-- cjkCompatibilityIdeograph-f9c3 BMPString ::= {0, 0, 249, 195}

-- cjkCompatibilityIdeograph-f9c4 BMPString ::= {0, 0, 249, 196}

-- cjkCompatibilityIdeograph-f9c5 BMPString ::= {0, 0, 249, 197}

-- cjkCompatibilityIdeograph-f9c6 BMPString ::= {0, 0, 249, 198}

-- cjkCompatibilityIdeograph-f9c7 BMPString ::= {0, 0, 249, 199}

-- cjkCompatibilityIdeograph-f9c8 BMPString ::= {0, 0, 249, 200}

-- cjkCompatibilityIdeograph-f9c9 BMPString ::= {0, 0, 249, 201}

-- cjkCompatibilityIdeograph-f9ca BMPString ::= {0, 0, 249, 202}

-- cjkCompatibilityIdeograph-f9cb BMPString ::= {0, 0, 249, 203}

-- cjkCompatibilityIdeograph-f9cc BMPString ::= {0, 0, 249, 204}

-- cjkCompatibilityIdeograph-f9cd BMPString ::= {0, 0, 249, 205}

-- cjkCompatibilityIdeograph-f9ce BMPString ::= {0, 0, 249, 206}

-- cjkCompatibilityIdeograph-f9cf BMPString ::= {0, 0, 249, 207}

-- cjkCompatibilityIdeograph-f9d0 BMPString ::= {0, 0, 249, 208}

-- cjkCompatibilityIdeograph-f9d1 BMPString ::= {0, 0, 249, 209}

-- cjkCompatibilityIdeograph-f9d2 BMPString ::= {0, 0, 249, 210}

-- cjkCompatibilityIdeograph-f9d3 BMPString ::= {0, 0, 249, 211}

-- cjkCompatibilityIdeograph-f9d4 BMPString ::= {0, 0, 249, 212}

-- cjkCompatibilityIdeograph-f9d5 BMPString ::= {0, 0, 249, 213}

-- cjkCompatibilityIdeograph-f9d6 BMPString ::= {0, 0, 249, 214}

-- cjkCompatibilityIdeograph-f9d7 BMPString ::= {0, 0, 249, 215}

-- cjkCompatibilityIdeograph-f9d8 BMPString ::= {0, 0, 249, 216}

-- cjkCompatibilityIdeograph-f9d9 BMPString ::= {0, 0, 249, 217}

-- cjkCompatibilityIdeograph-f9da BMPString ::= {0, 0, 249, 218}

-- cjkCompatibilityIdeograph-f9db BMPString ::= {0, 0, 249, 219}

-- cjkCompatibilityIdeograph-f9dc BMPString ::= {0, 0, 249, 220}

-- cjkCompatibilityIdeograph-f9dd BMPString ::= {0, 0, 249, 221}

-- cjkCompatibilityIdeograph-f9de BMPString ::= {0, 0, 249, 222}

-- cjkCompatibilityIdeograph-f9df BMPString ::= {0, 0, 249, 223}

-- cjkCompatibilityIdeograph-f9e0 BMPString ::= {0, 0, 249, 224}

-- cjkCompatibilityIdeograph-f9e1 BMPString ::= {0, 0, 249, 225}

-- cjkCompatibilityIdeograph-f9e2 BMPString ::= {0, 0, 249, 226}

-- cjkCompatibilityIdeograph-f9e3 BMPString ::= {0, 0, 249, 227}

-- cjkCompatibilityIdeograph-f9e4 BMPString ::= {0, 0, 249, 228}

-- cjkCompatibilityIdeograph-f9e5 BMPString ::= {0, 0, 249, 229}

-- cjkCompatibilityIdeograph-f9e6 BMPString ::= {0, 0, 249, 230}

-- cjkCompatibilityIdeograph-f9e7 BMPString ::= {0, 0, 249, 231}

-- cjkCompatibilityIdeograph-f9e8 BMPString ::= {0, 0, 249, 232}

-- cjkCompatibilityIdeograph-f9e9 BMPString ::= {0, 0, 249, 233}

-- cjkCompatibilityIdeograph-f9ea BMPString ::= {0, 0, 249, 234}

-- cjkCompatibilityIdeograph-f9eb BMPString ::= {0, 0, 249, 235}

-- cjkCompatibilityIdeograph-f9ec BMPString ::= {0, 0, 249, 236}

-- cjkCompatibilityIdeograph-f9ed BMPString ::= {0, 0, 249, 237}

-- cjkCompatibilityIdeograph-f9ee BMPString ::= {0, 0, 249, 238}

-- cjkCompatibilityIdeograph-f9ef BMPString ::= {0, 0, 249, 239}

-- cjkCompatibilityIdeograph-f9f0 BMPString ::= {0, 0, 249, 240}

-- cjkCompatibilityIdeograph-f9f1 BMPString ::= {0, 0, 249, 241}

-- cjkCompatibilityIdeograph-f9f2 BMPString ::= {0, 0, 249, 242}

-- cjkCompatibilityIdeograph-f9f3 BMPString ::= {0, 0, 249, 243}

-- cjkCompatibilityIdeograph-f9f4 BMPString ::= {0, 0, 249, 244}

-- cjkCompatibilityIdeograph-f9f5 BMPString ::= {0, 0, 249, 245}

-- cjkCompatibilityIdeograph-f9f6 BMPString ::= {0, 0, 249, 246}

-- cjkCompatibilityIdeograph-f9f7 BMPString ::= {0, 0, 249, 247}

-- cjkCompatibilityIdeograph-f9f8 BMPString ::= {0, 0, 249, 248}

-- cjkCompatibilityIdeograph-f9f9 BMPString ::= {0, 0, 249, 249}

-- cjkCompatibilityIdeograph-f9fa BMPString ::= {0, 0, 249, 250}

-- cjkCompatibilityIdeograph-f9fb BMPString ::= {0, 0, 249, 251}

-- cjkCompatibilityIdeograph-f9fc BMPString ::= {0, 0, 249, 252}

-- cjkCompatibilityIdeograph-f9fd BMPString ::= {0, 0, 249, 253}

-- cjkCompatibilityIdeograph-f9fe BMPString ::= {0, 0, 249, 254}

-- cjkCompatibilityIdeograph-f9ff BMPString ::= {0, 0, 249, 255}

-- cjkCompatibilityIdeograph-fa00 BMPString ::= {0, 0, 250, 0}

-- cjkCompatibilityIdeograph-fa01 BMPString ::= {0, 0, 250, 1}

-- cjkCompatibilityIdeograph-fa02 BMPString ::= {0, 0, 250, 2}

-- cjkCompatibilityIdeograph-fa03 BMPString ::= {0, 0, 250, 3}

-- cjkCompatibilityIdeograph-fa04 BMPString ::= {0, 0, 250, 4}

-- cjkCompatibilityIdeograph-fa05 BMPString ::= {0, 0, 250, 5}

-- cjkCompatibilityIdeograph-fa06 BMPString ::= {0, 0, 250, 6}

-- cjkCompatibilityIdeograph-fa07 BMPString ::= {0, 0, 250, 7}

-- cjkCompatibilityIdeograph-fa08 BMPString ::= {0, 0, 250, 8}

-- cjkCompatibilityIdeograph-fa09 BMPString ::= {0, 0, 250, 9}

-- cjkCompatibilityIdeograph-fa0a BMPString ::= {0, 0, 250, 10}

-- cjkCompatibilityIdeograph-fa0b BMPString ::= {0, 0, 250, 11}

-- cjkCompatibilityIdeograph-fa0c BMPString ::= {0, 0, 250, 12}

-- cjkCompatibilityIdeograph-fa0d BMPString ::= {0, 0, 250, 13}

-- cjkCompatibilityIdeograph-fa0e BMPString ::= {0, 0, 250, 14}

-- cjkCompatibilityIdeograph-fa0f BMPString ::= {0, 0, 250, 15}

-- cjkCompatibilityIdeograph-fa10 BMPString ::= {0, 0, 250, 16}

-- cjkCompatibilityIdeograph-fa11 BMPString ::= {0, 0, 250, 17}

-- cjkCompatibilityIdeograph-fa12 BMPString ::= {0, 0, 250, 18}

-- cjkCompatibilityIdeograph-fa13 BMPString ::= {0, 0, 250, 19}

-- cjkCompatibilityIdeograph-fa14 BMPString ::= {0, 0, 250, 20}

-- cjkCompatibilityIdeograph-fa15 BMPString ::= {0, 0, 250, 21}

-- cjkCompatibilityIdeograph-fa16 BMPString ::= {0, 0, 250, 22}

-- cjkCompatibilityIdeograph-fa17 BMPString ::= {0, 0, 250, 23}

-- cjkCompatibilityIdeograph-fa18 BMPString ::= {0, 0, 250, 24}

-- cjkCompatibilityIdeograph-fa19 BMPString ::= {0, 0, 250, 25}

-- cjkCompatibilityIdeograph-fa1a BMPString ::= {0, 0, 250, 26}

-- cjkCompatibilityIdeograph-fa1b BMPString ::= {0, 0, 250, 27}

-- cjkCompatibilityIdeograph-fa1c BMPString ::= {0, 0, 250, 28}

-- cjkCompatibilityIdeograph-fa1d BMPString ::= {0, 0, 250, 29}

-- cjkCompatibilityIdeograph-fa1e BMPString ::= {0, 0, 250, 30}

-- cjkCompatibilityIdeograph-fa1f BMPString ::= {0, 0, 250, 31}

-- cjkCompatibilityIdeograph-fa20 BMPString ::= {0, 0, 250, 32}

-- cjkCompatibilityIdeograph-fa21 BMPString ::= {0, 0, 250, 33}

-- cjkCompatibilityIdeograph-fa22 BMPString ::= {0, 0, 250, 34}

-- cjkCompatibilityIdeograph-fa23 BMPString ::= {0, 0, 250, 35}

-- cjkCompatibilityIdeograph-fa24 BMPString ::= {0, 0, 250, 36}

-- cjkCompatibilityIdeograph-fa25 BMPString ::= {0, 0, 250, 37}

-- cjkCompatibilityIdeograph-fa26 BMPString ::= {0, 0, 250, 38}

-- cjkCompatibilityIdeograph-fa27 BMPString ::= {0, 0, 250, 39}

-- cjkCompatibilityIdeograph-fa28 BMPString ::= {0, 0, 250, 40}

-- cjkCompatibilityIdeograph-fa29 BMPString ::= {0, 0, 250, 41}

-- cjkCompatibilityIdeograph-fa2a BMPString ::= {0, 0, 250, 42}

-- cjkCompatibilityIdeograph-fa2b BMPString ::= {0, 0, 250, 43}

-- cjkCompatibilityIdeograph-fa2c BMPString ::= {0, 0, 250, 44}

-- cjkCompatibilityIdeograph-fa2d BMPString ::= {0, 0, 250, 45}

-- cjkCompatibilityIdeograph-fa30 BMPString ::= {0, 0, 250, 48}

-- cjkCompatibilityIdeograph-fa31 BMPString ::= {0, 0, 250, 49}

-- cjkCompatibilityIdeograph-fa32 BMPString ::= {0, 0, 250, 50}

-- cjkCompatibilityIdeograph-fa33 BMPString ::= {0, 0, 250, 51}

-- cjkCompatibilityIdeograph-fa34 BMPString ::= {0, 0, 250, 52}

-- cjkCompatibilityIdeograph-fa35 BMPString ::= {0, 0, 250, 53}

-- cjkCompatibilityIdeograph-fa36 BMPString ::= {0, 0, 250, 54}

-- cjkCompatibilityIdeograph-fa37 BMPString ::= {0, 0, 250, 55}

-- cjkCompatibilityIdeograph-fa38 BMPString ::= {0, 0, 250, 56}

-- cjkCompatibilityIdeograph-fa39 BMPString ::= {0, 0, 250, 57}

-- cjkCompatibilityIdeograph-fa3a BMPString ::= {0, 0, 250, 58}

-- cjkCompatibilityIdeograph-fa3b BMPString ::= {0, 0, 250, 59}

-- cjkCompatibilityIdeograph-fa3c BMPString ::= {0, 0, 250, 60}

-- cjkCompatibilityIdeograph-fa3d BMPString ::= {0, 0, 250, 61}

-- cjkCompatibilityIdeograph-fa3e BMPString ::= {0, 0, 250, 62}

-- cjkCompatibilityIdeograph-fa3f BMPString ::= {0, 0, 250, 63}

-- cjkCompatibilityIdeograph-fa40 BMPString ::= {0, 0, 250, 64}

-- cjkCompatibilityIdeograph-fa41 BMPString ::= {0, 0, 250, 65}

-- cjkCompatibilityIdeograph-fa42 BMPString ::= {0, 0, 250, 66}

-- cjkCompatibilityIdeograph-fa43 BMPString ::= {0, 0, 250, 67}

-- cjkCompatibilityIdeograph-fa44 BMPString ::= {0, 0, 250, 68}

-- cjkCompatibilityIdeograph-fa45 BMPString ::= {0, 0, 250, 69}

-- cjkCompatibilityIdeograph-fa46 BMPString ::= {0, 0, 250, 70}

-- cjkCompatibilityIdeograph-fa47 BMPString ::= {0, 0, 250, 71}

-- cjkCompatibilityIdeograph-fa48 BMPString ::= {0, 0, 250, 72}

-- cjkCompatibilityIdeograph-fa49 BMPString ::= {0, 0, 250, 73}

-- cjkCompatibilityIdeograph-fa4a BMPString ::= {0, 0, 250, 74}

-- cjkCompatibilityIdeograph-fa4b BMPString ::= {0, 0, 250, 75}

-- cjkCompatibilityIdeograph-fa4c BMPString ::= {0, 0, 250, 76}

-- cjkCompatibilityIdeograph-fa4d BMPString ::= {0, 0, 250, 77}

-- cjkCompatibilityIdeograph-fa4e BMPString ::= {0, 0, 250, 78}

-- cjkCompatibilityIdeograph-fa4f BMPString ::= {0, 0, 250, 79}

-- cjkCompatibilityIdeograph-fa50 BMPString ::= {0, 0, 250, 80}

-- cjkCompatibilityIdeograph-fa51 BMPString ::= {0, 0, 250, 81}

-- cjkCompatibilityIdeograph-fa52 BMPString ::= {0, 0, 250, 82}

-- cjkCompatibilityIdeograph-fa53 BMPString ::= {0, 0, 250, 83}

-- cjkCompatibilityIdeograph-fa54 BMPString ::= {0, 0, 250, 84}

-- cjkCompatibilityIdeograph-fa55 BMPString ::= {0, 0, 250, 85}

-- cjkCompatibilityIdeograph-fa56 BMPString ::= {0, 0, 250, 86}

-- cjkCompatibilityIdeograph-fa57 BMPString ::= {0, 0, 250, 87}

-- cjkCompatibilityIdeograph-fa58 BMPString ::= {0, 0, 250, 88}

-- cjkCompatibilityIdeograph-fa59 BMPString ::= {0, 0, 250, 89}

-- cjkCompatibilityIdeograph-fa5a BMPString ::= {0, 0, 250, 90}

-- cjkCompatibilityIdeograph-fa5b BMPString ::= {0, 0, 250, 91}

-- cjkCompatibilityIdeograph-fa5c BMPString ::= {0, 0, 250, 92}

-- cjkCompatibilityIdeograph-fa5d BMPString ::= {0, 0, 250, 93}

-- cjkCompatibilityIdeograph-fa5e BMPString ::= {0, 0, 250, 94}

-- cjkCompatibilityIdeograph-fa5f BMPString ::= {0, 0, 250, 95}

-- cjkCompatibilityIdeograph-fa60 BMPString ::= {0, 0, 250, 96}

-- cjkCompatibilityIdeograph-fa61 BMPString ::= {0, 0, 250, 97}

-- cjkCompatibilityIdeograph-fa62 BMPString ::= {0, 0, 250, 98}

-- cjkCompatibilityIdeograph-fa63 BMPString ::= {0, 0, 250, 99}

-- cjkCompatibilityIdeograph-fa64 BMPString ::= {0, 0, 250, 100}

-- cjkCompatibilityIdeograph-fa65 BMPString ::= {0, 0, 250, 101}

-- cjkCompatibilityIdeograph-fa66 BMPString ::= {0, 0, 250, 102}

-- cjkCompatibilityIdeograph-fa67 BMPString ::= {0, 0, 250, 103}

-- cjkCompatibilityIdeograph-fa68 BMPString ::= {0, 0, 250, 104}

-- cjkCompatibilityIdeograph-fa69 BMPString ::= {0, 0, 250, 105}

-- cjkCompatibilityIdeograph-fa6a BMPString ::= {0, 0, 250, 106}

-- latinSmallLigatureFf BMPString ::= {0, 0, 251, 0}

-- latinSmallLigatureFi BMPString ::= {0, 0, 251, 1}

-- latinSmallLigatureFl BMPString ::= {0, 0, 251, 2}

-- latinSmallLigatureFfi BMPString ::= {0, 0, 251, 3}

-- latinSmallLigatureFfl BMPString ::= {0, 0, 251, 4}

-- latinSmallLigatureLongST BMPString ::= {0, 0, 251, 5}

-- latinSmallLigatureSt BMPString ::= {0, 0, 251, 6}

-- armenianSmallLigatureMenNow BMPString ::= {0, 0, 251, 19}

-- armenianSmallLigatureMenEch BMPString ::= {0, 0, 251, 20}

-- armenianSmallLigatureMenIni BMPString ::= {0, 0, 251, 21}

-- armenianSmallLigatureVewNow BMPString ::= {0, 0, 251, 22}

-- armenianSmallLigatureMenXeh BMPString ::= {0, 0, 251, 23}

-- hebrewLetterYodWithHiriq BMPString ::= {0, 0, 251, 29}

-- hebrewPointJudeo-spanishVarika BMPString ::= {0, 0, 251, 30}

-- hebrewLigatureYiddishYodYodPatah BMPString ::= {0, 0, 251, 31}

-- hebrewLetterAlternativeAyin BMPString ::= {0, 0, 251, 32}

-- hebrewLetterWideAlef BMPString ::= {0, 0, 251, 33}

-- hebrewLetterWideDalet BMPString ::= {0, 0, 251, 34}

-- hebrewLetterWideHe BMPString ::= {0, 0, 251, 35}

-- hebrewLetterWideKaf BMPString ::= {0, 0, 251, 36}

-- hebrewLetterWideLamed BMPString ::= {0, 0, 251, 37}

-- hebrewLetterWideFinalMem BMPString ::= {0, 0, 251, 38}

-- hebrewLetterWideResh BMPString ::= {0, 0, 251, 39}

-- hebrewLetterWideTav BMPString ::= {0, 0, 251, 40}

-- hebrewLetterAlternativePlusSign BMPString ::= {0, 0, 251, 41}

-- hebrewLetterShinWithShinDot BMPString ::= {0, 0, 251, 42}

-- hebrewLetterShinWithSinDot BMPString ::= {0, 0, 251, 43}

-- hebrewLetterShinWithDageshAndShinDot BMPString ::= {0, 0, 251, 44}

-- hebrewLetterShinWithDageshAndSinDot BMPString ::= {0, 0, 251, 45}

-- hebrewLetterAlefWithPatah BMPString ::= {0, 0, 251, 46}

-- hebrewLetterAlefWithQamats BMPString ::= {0, 0, 251, 47}

-- hebrewLetterAlefWithMapiq BMPString ::= {0, 0, 251, 48}

-- hebrewLetterBetWithDagesh BMPString ::= {0, 0, 251, 49}

-- hebrewLetterGimelWithDagesh BMPString ::= {0, 0, 251, 50}

-- hebrewLetterDaletWithDagesh BMPString ::= {0, 0, 251, 51}

-- hebrewLetterHeWithMapiq BMPString ::= {0, 0, 251, 52}

-- hebrewLetterVavWithDagesh BMPString ::= {0, 0, 251, 53}

-- hebrewLetterZayinWithDagesh BMPString ::= {0, 0, 251, 54}

-- hebrewLetterTetWithDagesh BMPString ::= {0, 0, 251, 56}

-- hebrewLetterYodWithDagesh BMPString ::= {0, 0, 251, 57}

-- hebrewLetterFinalKafWithDagesh BMPString ::= {0, 0, 251, 58}

-- hebrewLetterKafWithDagesh BMPString ::= {0, 0, 251, 59}

-- hebrewLetterLamedWithDagesh BMPString ::= {0, 0, 251, 60}

-- hebrewLetterMemWithDagesh BMPString ::= {0, 0, 251, 62}

-- hebrewLetterNunWithDagesh BMPString ::= {0, 0, 251, 64}

-- hebrewLetterSamekhWithDagesh BMPString ::= {0, 0, 251, 65}

-- hebrewLetterFinalPeWithDagesh BMPString ::= {0, 0, 251, 67}

-- hebrewLetterPeWithDagesh BMPString ::= {0, 0, 251, 68}

-- hebrewLetterTsadiWithDagesh BMPString ::= {0, 0, 251, 70}

-- hebrewLetterQofWithDagesh BMPString ::= {0, 0, 251, 71}

-- hebrewLetterReshWithDagesh BMPString ::= {0, 0, 251, 72}

-- hebrewLetterShinWithDagesh BMPString ::= {0, 0, 251, 73}

-- hebrewLetterTavWithDagesh BMPString ::= {0, 0, 251, 74}

-- hebrewLetterVavWithHolam BMPString ::= {0, 0, 251, 75}

-- hebrewLetterBetWithRafe BMPString ::= {0, 0, 251, 76}

-- hebrewLetterKafWithRafe BMPString ::= {0, 0, 251, 77}

-- hebrewLetterPeWithRafe BMPString ::= {0, 0, 251, 78}

-- hebrewLigatureAlefLamed BMPString ::= {0, 0, 251, 79}

-- arabicLetterAlefWaslaIsolatedForm BMPString ::= {0, 0, 251, 80}

-- arabicLetterAlefWaslaFinalForm BMPString ::= {0, 0, 251, 81}

-- arabicLetterBeehIsolatedForm BMPString ::= {0, 0, 251, 82}

-- arabicLetterBeehFinalForm BMPString ::= {0, 0, 251, 83}

-- arabicLetterBeehInitialForm BMPString ::= {0, 0, 251, 84}

-- arabicLetterBeehMedialForm BMPString ::= {0, 0, 251, 85}

-- arabicLetterPehIsolatedForm BMPString ::= {0, 0, 251, 86}

-- arabicLetterPehFinalForm BMPString ::= {0, 0, 251, 87}

-- arabicLetterPehInitialForm BMPString ::= {0, 0, 251, 88}

-- arabicLetterPehMedialForm BMPString ::= {0, 0, 251, 89}

-- arabicLetterBehehIsolatedForm BMPString ::= {0, 0, 251, 90}

-- arabicLetterBehehFinalForm BMPString ::= {0, 0, 251, 91}

-- arabicLetterBehehInitialForm BMPString ::= {0, 0, 251, 92}

-- arabicLetterBehehMedialForm BMPString ::= {0, 0, 251, 93}

-- arabicLetterTtehehIsolatedForm BMPString ::= {0, 0, 251, 94}

-- arabicLetterTtehehFinalForm BMPString ::= {0, 0, 251, 95}

-- arabicLetterTtehehInitialForm BMPString ::= {0, 0, 251, 96}

-- arabicLetterTtehehMedialForm BMPString ::= {0, 0, 251, 97}

-- arabicLetterTehehIsolatedForm BMPString ::= {0, 0, 251, 98}

-- arabicLetterTehehFinalForm BMPString ::= {0, 0, 251, 99}

-- arabicLetterTehehInitialForm BMPString ::= {0, 0, 251, 100}

-- arabicLetterTehehMedialForm BMPString ::= {0, 0, 251, 101}

-- arabicLetterTtehIsolatedForm BMPString ::= {0, 0, 251, 102}

-- arabicLetterTtehFinalForm BMPString ::= {0, 0, 251, 103}

-- arabicLetterTtehInitialForm BMPString ::= {0, 0, 251, 104}

-- arabicLetterTtehMedialForm BMPString ::= {0, 0, 251, 105}

-- arabicLetterVehIsolatedForm BMPString ::= {0, 0, 251, 106}

-- arabicLetterVehFinalForm BMPString ::= {0, 0, 251, 107}

-- arabicLetterVehInitialForm BMPString ::= {0, 0, 251, 108}

-- arabicLetterVehMedialForm BMPString ::= {0, 0, 251, 109}

-- arabicLetterPehehIsolatedForm BMPString ::= {0, 0, 251, 110}

-- arabicLetterPehehFinalForm BMPString ::= {0, 0, 251, 111}

-- arabicLetterPehehInitialForm BMPString ::= {0, 0, 251, 112}

-- arabicLetterPehehMedialForm BMPString ::= {0, 0, 251, 113}

-- arabicLetterDyehIsolatedForm BMPString ::= {0, 0, 251, 114}

-- arabicLetterDyehFinalForm BMPString ::= {0, 0, 251, 115}

-- arabicLetterDyehInitialForm BMPString ::= {0, 0, 251, 116}

-- arabicLetterDyehMedialForm BMPString ::= {0, 0, 251, 117}

-- arabicLetterNyehIsolatedForm BMPString ::= {0, 0, 251, 118}

-- arabicLetterNyehFinalForm BMPString ::= {0, 0, 251, 119}

-- arabicLetterNyehInitialForm BMPString ::= {0, 0, 251, 120}

-- arabicLetterNyehMedialForm BMPString ::= {0, 0, 251, 121}

-- arabicLetterTchehIsolatedForm BMPString ::= {0, 0, 251, 122}

-- arabicLetterTchehFinalForm BMPString ::= {0, 0, 251, 123}

-- arabicLetterTchehInitialForm BMPString ::= {0, 0, 251, 124}

-- arabicLetterTchehMedialForm BMPString ::= {0, 0, 251, 125}

-- arabicLetterTchehehIsolatedForm BMPString ::= {0, 0, 251, 126}

-- arabicLetterTchehehFinalForm BMPString ::= {0, 0, 251, 127}

-- arabicLetterTchehehInitialForm BMPString ::= {0, 0, 251, 128}

-- arabicLetterTchehehMedialForm BMPString ::= {0, 0, 251, 129}

-- arabicLetterDdahalIsolatedForm BMPString ::= {0, 0, 251, 130}

-- arabicLetterDdahalFinalForm BMPString ::= {0, 0, 251, 131}

-- arabicLetterDahalIsolatedForm BMPString ::= {0, 0, 251, 132}

-- arabicLetterDahalFinalForm BMPString ::= {0, 0, 251, 133}

-- arabicLetterDulIsolatedForm BMPString ::= {0, 0, 251, 134}

-- arabicLetterDulFinalForm BMPString ::= {0, 0, 251, 135}

-- arabicLetterDdalIsolatedForm BMPString ::= {0, 0, 251, 136}

-- arabicLetterDdalFinalForm BMPString ::= {0, 0, 251, 137}

-- arabicLetterJehIsolatedForm BMPString ::= {0, 0, 251, 138}

-- arabicLetterJehFinalForm BMPString ::= {0, 0, 251, 139}

-- arabicLetterRrehIsolatedForm BMPString ::= {0, 0, 251, 140}

-- arabicLetterRrehFinalForm BMPString ::= {0, 0, 251, 141}

-- arabicLetterKehehIsolatedForm BMPString ::= {0, 0, 251, 142}

-- arabicLetterKehehFinalForm BMPString ::= {0, 0, 251, 143}

-- arabicLetterKehehInitialForm BMPString ::= {0, 0, 251, 144}

-- arabicLetterKehehMedialForm BMPString ::= {0, 0, 251, 145}

-- arabicLetterGafIsolatedForm BMPString ::= {0, 0, 251, 146}

-- arabicLetterGafFinalForm BMPString ::= {0, 0, 251, 147}

-- arabicLetterGafInitialForm BMPString ::= {0, 0, 251, 148}

-- arabicLetterGafMedialForm BMPString ::= {0, 0, 251, 149}

-- arabicLetterGuehIsolatedForm BMPString ::= {0, 0, 251, 150}

-- arabicLetterGuehFinalForm BMPString ::= {0, 0, 251, 151}

-- arabicLetterGuehInitialForm BMPString ::= {0, 0, 251, 152}

-- arabicLetterGuehMedialForm BMPString ::= {0, 0, 251, 153}

-- arabicLetterNgoehIsolatedForm BMPString ::= {0, 0, 251, 154}

-- arabicLetterNgoehFinalForm BMPString ::= {0, 0, 251, 155}

-- arabicLetterNgoehInitialForm BMPString ::= {0, 0, 251, 156}

-- arabicLetterNgoehMedialForm BMPString ::= {0, 0, 251, 157}

-- arabicLetterNoonGhunnaIsolatedForm BMPString ::= {0, 0, 251, 158}

-- arabicLetterNoonGhunnaFinalForm BMPString ::= {0, 0, 251, 159}

-- arabicLetterRnoonIsolatedForm BMPString ::= {0, 0, 251, 160}

-- arabicLetterRnoonFinalForm BMPString ::= {0, 0, 251, 161}

-- arabicLetterRnoonInitialForm BMPString ::= {0, 0, 251, 162}

-- arabicLetterRnoonMedialForm BMPString ::= {0, 0, 251, 163}

-- arabicLetterHehWithYehAboveIsolatedForm BMPString ::= {0, 0, 251, 164}

-- arabicLetterHehWithYehAboveFinalForm BMPString ::= {0, 0, 251, 165}

-- arabicLetterHehGoalIsolatedForm BMPString ::= {0, 0, 251, 166}

-- arabicLetterHehGoalFinalForm BMPString ::= {0, 0, 251, 167}

-- arabicLetterHehGoalInitialForm BMPString ::= {0, 0, 251, 168}

-- arabicLetterHehGoalMedialForm BMPString ::= {0, 0, 251, 169}

-- arabicLetterHehDoachashmeeIsolatedForm BMPString ::= {0, 0, 251, 170}

-- arabicLetterHehDoachashmeeFinalForm BMPString ::= {0, 0, 251, 171}

-- arabicLetterHehDoachashmeeInitialForm BMPString ::= {0, 0, 251, 172}

-- arabicLetterHehDoachashmeeMedialForm BMPString ::= {0, 0, 251, 173}

-- arabicLetterYehBarreeIsolatedForm BMPString ::= {0, 0, 251, 174}

-- arabicLetterYehBarreeFinalForm BMPString ::= {0, 0, 251, 175}

-- arabicLetterYehBarreeWithHamzaAboveIsolatedForm BMPString ::= {0, 0, 251, 176}

-- arabicLetterYehBarreeWithHamzaAboveFinalForm BMPString ::= {0, 0, 251, 177}

-- arabicLetterNgIsolatedForm BMPString ::= {0, 0, 251, 211}

-- arabicLetterNgFinalForm BMPString ::= {0, 0, 251, 212}

-- arabicLetterNgInitialForm BMPString ::= {0, 0, 251, 213}

-- arabicLetterNgMedialForm BMPString ::= {0, 0, 251, 214}

-- arabicLetterUIsolatedForm BMPString ::= {0, 0, 251, 215}

-- arabicLetterUFinalForm BMPString ::= {0, 0, 251, 216}

-- arabicLetterOeIsolatedForm BMPString ::= {0, 0, 251, 217}

-- arabicLetterOeFinalForm BMPString ::= {0, 0, 251, 218}

-- arabicLetterYuIsolatedForm BMPString ::= {0, 0, 251, 219}

-- arabicLetterYuFinalForm BMPString ::= {0, 0, 251, 220}

-- arabicLetterUWithHamzaAboveIsolatedForm BMPString ::= {0, 0, 251, 221}

-- arabicLetterVeIsolatedForm BMPString ::= {0, 0, 251, 222}

-- arabicLetterVeFinalForm BMPString ::= {0, 0, 251, 223}

-- arabicLetterKirghizOeIsolatedForm BMPString ::= {0, 0, 251, 224}

-- arabicLetterKirghizOeFinalForm BMPString ::= {0, 0, 251, 225}

-- arabicLetterKirghizYuIsolatedForm BMPString ::= {0, 0, 251, 226}

-- arabicLetterKirghizYuFinalForm BMPString ::= {0, 0, 251, 227}

-- arabicLetterEIsolatedForm BMPString ::= {0, 0, 251, 228}

-- arabicLetterEFinalForm BMPString ::= {0, 0, 251, 229}

-- arabicLetterEInitialForm BMPString ::= {0, 0, 251, 230}

-- arabicLetterEMedialForm BMPString ::= {0, 0, 251, 231}

-- arabicLetterUighurKazakhKirghizAlefMaksuraInitialForm BMPString ::=
--   {0, 0, 251, 232}

-- arabicLetterUighurKazakhKirghizAlefMaksuraMedialForm BMPString ::=
--   {0, 0, 251, 233}

-- arabicLigatureYehWithHamzaAboveWithAlefIsolatedForm BMPString ::=
--   {0, 0, 251, 234}

-- arabicLigatureYehWithHamzaAboveWithAlefFinalForm BMPString ::= {0, 0, 251, 235}

-- arabicLigatureYehWithHamzaAboveWithAeIsolatedForm BMPString ::=
--   {0, 0, 251, 236}

-- arabicLigatureYehWithHamzaAboveWithAeFinalForm BMPString ::= {0, 0, 251, 237}

-- arabicLigatureYehWithHamzaAboveWithWawIsolatedForm BMPString ::=
--   {0, 0, 251, 238}

-- arabicLigatureYehWithHamzaAboveWithWawFinalForm BMPString ::= {0, 0, 251, 239}

-- arabicLigatureYehWithHamzaAboveWithUIsolatedForm BMPString ::= {0, 0, 251, 240}

-- arabicLigatureYehWithHamzaAboveWithUFinalForm BMPString ::= {0, 0, 251, 241}

-- arabicLigatureYehWithHamzaAboveWithOeIsolatedForm BMPString ::=
--   {0, 0, 251, 242}

-- arabicLigatureYehWithHamzaAboveWithOeFinalForm BMPString ::= {0, 0, 251, 243}

-- arabicLigatureYehWithHamzaAboveWithYuIsolatedForm BMPString ::=
--   {0, 0, 251, 244}

-- arabicLigatureYehWithHamzaAboveWithYuFinalForm BMPString ::= {0, 0, 251, 245}

-- arabicLigatureYehWithHamzaAboveWithEIsolatedForm BMPString ::= {0, 0, 251, 246}

-- arabicLigatureYehWithHamzaAboveWithEFinalForm BMPString ::= {0, 0, 251, 247}

-- arabicLigatureYehWithHamzaAboveWithEInitialForm BMPString ::= {0, 0, 251, 248}

-- arabicLigatureUighurKirghizYehWithHamzaAboveWithAlefMaksuraIsolatedForm
--   BMPString ::=
--   {0, 0, 251, 249}

-- arabicLigatureUighurKirghizYehWithHamzaAboveWithAlefMaksuraFinalForm
--   BMPString ::=
--   {0, 0, 251, 250}

-- arabicLigatureUighurKirghizYehWithHamzaAboveWithAlefMaksuraInitialForm
--   BMPString ::=
--   {0, 0, 251, 251}

-- arabicLetterFarsiYehIsolatedForm BMPString ::= {0, 0, 251, 252}

-- arabicLetterFarsiYehFinalForm BMPString ::= {0, 0, 251, 253}

-- arabicLetterFarsiYehInitialForm BMPString ::= {0, 0, 251, 254}

-- arabicLetterFarsiYehMedialForm BMPString ::= {0, 0, 251, 255}

-- arabicLigatureYehWithHamzaAboveWithJeemIsolatedForm BMPString ::=
--   {0, 0, 252, 0}

-- arabicLigatureYehWithHamzaAboveWithHahIsolatedForm BMPString ::= {0, 0, 252, 1}

-- arabicLigatureYehWithHamzaAboveWithMeemIsolatedForm BMPString ::=
--   {0, 0, 252, 2}

-- arabicLigatureYehWithHamzaAboveWithAlefMaksuraIsolatedForm BMPString ::=
--   {0, 0, 252, 3}

-- arabicLigatureYehWithHamzaAboveWithYehIsolatedForm BMPString ::= {0, 0, 252, 4}

-- arabicLigatureBehWithJeemIsolatedForm BMPString ::= {0, 0, 252, 5}

-- arabicLigatureBehWithHahIsolatedForm BMPString ::= {0, 0, 252, 6}

-- arabicLigatureBehWithKhahIsolatedForm BMPString ::= {0, 0, 252, 7}

-- arabicLigatureBehWithMeemIsolatedForm BMPString ::= {0, 0, 252, 8}

-- arabicLigatureBehWithAlefMaksuraIsolatedForm BMPString ::= {0, 0, 252, 9}

-- arabicLigatureBehWithYehIsolatedForm BMPString ::= {0, 0, 252, 10}

-- arabicLigatureTehWithJeemIsolatedForm BMPString ::= {0, 0, 252, 11}

-- arabicLigatureTehWithHahIsolatedForm BMPString ::= {0, 0, 252, 12}

-- arabicLigatureTehWithKhahIsolatedForm BMPString ::= {0, 0, 252, 13}

-- arabicLigatureTehWithMeemIsolatedForm BMPString ::= {0, 0, 252, 14}

-- arabicLigatureTehWithAlefMaksuraIsolatedForm BMPString ::= {0, 0, 252, 15}

-- arabicLigatureTehWithYehIsolatedForm BMPString ::= {0, 0, 252, 16}

-- arabicLigatureThehWithJeemIsolatedForm BMPString ::= {0, 0, 252, 17}

-- arabicLigatureThehWithMeemIsolatedForm BMPString ::= {0, 0, 252, 18}

-- arabicLigatureThehWithAlefMaksuraIsolatedForm BMPString ::= {0, 0, 252, 19}

-- arabicLigatureThehWithYehIsolatedForm BMPString ::= {0, 0, 252, 20}

-- arabicLigatureJeemWithHahIsolatedForm BMPString ::= {0, 0, 252, 21}

-- arabicLigatureJeemWithMeemIsolatedForm BMPString ::= {0, 0, 252, 22}

-- arabicLigatureHahWithJeemIsolatedForm BMPString ::= {0, 0, 252, 23}

-- arabicLigatureHahWithMeemIsolatedForm BMPString ::= {0, 0, 252, 24}

-- arabicLigatureKhahWithJeemIsolatedForm BMPString ::= {0, 0, 252, 25}

-- arabicLigatureKhahWithHahIsolatedForm BMPString ::= {0, 0, 252, 26}

-- arabicLigatureKhahWithMeemIsolatedForm BMPString ::= {0, 0, 252, 27}

-- arabicLigatureSeenWithJeemIsolatedForm BMPString ::= {0, 0, 252, 28}

-- arabicLigatureSeenWithHahIsolatedForm BMPString ::= {0, 0, 252, 29}

-- arabicLigatureSeenWithKhahIsolatedForm BMPString ::= {0, 0, 252, 30}

-- arabicLigatureSeenWithMeemIsolatedForm BMPString ::= {0, 0, 252, 31}

-- arabicLigatureSadWithHahIsolatedForm BMPString ::= {0, 0, 252, 32}

-- arabicLigatureSadWithMeemIsolatedForm BMPString ::= {0, 0, 252, 33}

-- arabicLigatureDadWithJeemIsolatedForm BMPString ::= {0, 0, 252, 34}

-- arabicLigatureDadWithHahIsolatedForm BMPString ::= {0, 0, 252, 35}

-- arabicLigatureDadWithKhahIsolatedForm BMPString ::= {0, 0, 252, 36}

-- arabicLigatureDadWithMeemIsolatedForm BMPString ::= {0, 0, 252, 37}

-- arabicLigatureTahWithHahIsolatedForm BMPString ::= {0, 0, 252, 38}

-- arabicLigatureTahWithMeemIsolatedForm BMPString ::= {0, 0, 252, 39}

-- arabicLigatureZahWithMeemIsolatedForm BMPString ::= {0, 0, 252, 40}

-- arabicLigatureAinWithJeemIsolatedForm BMPString ::= {0, 0, 252, 41}

-- arabicLigatureAinWithMeemIsolatedForm BMPString ::= {0, 0, 252, 42}

-- arabicLigatureGhainWithJeemIsolatedForm BMPString ::= {0, 0, 252, 43}

-- arabicLigatureGhainWithMeemIsolatedForm BMPString ::= {0, 0, 252, 44}

-- arabicLigatureFehWithJeemIsolatedForm BMPString ::= {0, 0, 252, 45}

-- arabicLigatureFehWithHahIsolatedForm BMPString ::= {0, 0, 252, 46}

-- arabicLigatureFehWithKhahIsolatedForm BMPString ::= {0, 0, 252, 47}

-- arabicLigatureFehWithMeemIsolatedForm BMPString ::= {0, 0, 252, 48}

-- arabicLigatureFehWithAlefMaksuraIsolatedForm BMPString ::= {0, 0, 252, 49}

-- arabicLigatureFehWithYehIsolatedForm BMPString ::= {0, 0, 252, 50}

-- arabicLigatureQafWithHahIsolatedForm BMPString ::= {0, 0, 252, 51}

-- arabicLigatureQafWithMeemIsolatedForm BMPString ::= {0, 0, 252, 52}

-- arabicLigatureQafWithAlefMaksuraIsolatedForm BMPString ::= {0, 0, 252, 53}

-- arabicLigatureQafWithYehIsolatedForm BMPString ::= {0, 0, 252, 54}

-- arabicLigatureKafWithAlefIsolatedForm BMPString ::= {0, 0, 252, 55}

-- arabicLigatureKafWithJeemIsolatedForm BMPString ::= {0, 0, 252, 56}

-- arabicLigatureKafWithHahIsolatedForm BMPString ::= {0, 0, 252, 57}

-- arabicLigatureKafWithKhahIsolatedForm BMPString ::= {0, 0, 252, 58}

-- arabicLigatureKafWithLamIsolatedForm BMPString ::= {0, 0, 252, 59}

-- arabicLigatureKafWithMeemIsolatedForm BMPString ::= {0, 0, 252, 60}

-- arabicLigatureKafWithAlefMaksuraIsolatedForm BMPString ::= {0, 0, 252, 61}

-- arabicLigatureKafWithYehIsolatedForm BMPString ::= {0, 0, 252, 62}

-- arabicLigatureLamWithJeemIsolatedForm BMPString ::= {0, 0, 252, 63}

-- arabicLigatureLamWithHahIsolatedForm BMPString ::= {0, 0, 252, 64}

-- arabicLigatureLamWithKhahIsolatedForm BMPString ::= {0, 0, 252, 65}

-- arabicLigatureLamWithMeemIsolatedForm BMPString ::= {0, 0, 252, 66}

-- arabicLigatureLamWithAlefMaksuraIsolatedForm BMPString ::= {0, 0, 252, 67}

-- arabicLigatureLamWithYehIsolatedForm BMPString ::= {0, 0, 252, 68}

-- arabicLigatureMeemWithJeemIsolatedForm BMPString ::= {0, 0, 252, 69}

-- arabicLigatureMeemWithHahIsolatedForm BMPString ::= {0, 0, 252, 70}

-- arabicLigatureMeemWithKhahIsolatedForm BMPString ::= {0, 0, 252, 71}

-- arabicLigatureMeemWithMeemIsolatedForm BMPString ::= {0, 0, 252, 72}

-- arabicLigatureMeemWithAlefMaksuraIsolatedForm BMPString ::= {0, 0, 252, 73}

-- arabicLigatureMeemWithYehIsolatedForm BMPString ::= {0, 0, 252, 74}

-- arabicLigatureNoonWithJeemIsolatedForm BMPString ::= {0, 0, 252, 75}

-- arabicLigatureNoonWithHahIsolatedForm BMPString ::= {0, 0, 252, 76}

-- arabicLigatureNoonWithKhahIsolatedForm BMPString ::= {0, 0, 252, 77}

-- arabicLigatureNoonWithMeemIsolatedForm BMPString ::= {0, 0, 252, 78}

-- arabicLigatureNoonWithAlefMaksuraIsolatedForm BMPString ::= {0, 0, 252, 79}

-- arabicLigatureNoonWithYehIsolatedForm BMPString ::= {0, 0, 252, 80}

-- arabicLigatureHehWithJeemIsolatedForm BMPString ::= {0, 0, 252, 81}

-- arabicLigatureHehWithMeemIsolatedForm BMPString ::= {0, 0, 252, 82}

-- arabicLigatureHehWithAlefMaksuraIsolatedForm BMPString ::= {0, 0, 252, 83}

-- arabicLigatureHehWithYehIsolatedForm BMPString ::= {0, 0, 252, 84}

-- arabicLigatureYehWithJeemIsolatedForm BMPString ::= {0, 0, 252, 85}

-- arabicLigatureYehWithHahIsolatedForm BMPString ::= {0, 0, 252, 86}

-- arabicLigatureYehWithKhahIsolatedForm BMPString ::= {0, 0, 252, 87}

-- arabicLigatureYehWithMeemIsolatedForm BMPString ::= {0, 0, 252, 88}

-- arabicLigatureYehWithAlefMaksuraIsolatedForm BMPString ::= {0, 0, 252, 89}

-- arabicLigatureYehWithYehIsolatedForm BMPString ::= {0, 0, 252, 90}

-- arabicLigatureThalWithSuperscriptAlefIsolatedForm BMPString ::= {0, 0, 252, 91}

-- arabicLigatureRehWithSuperscriptAlefIsolatedForm BMPString ::= {0, 0, 252, 92}

-- arabicLigatureAlefMaksuraWithSuperscriptAlefIsolatedForm BMPString ::=
--   {0, 0, 252, 93}

-- arabicLigatureShaddaWithDammatanIsolatedForm BMPString ::= {0, 0, 252, 94}

-- arabicLigatureShaddaWithKasratanIsolatedForm BMPString ::= {0, 0, 252, 95}

-- arabicLigatureShaddaWithFathaIsolatedForm BMPString ::= {0, 0, 252, 96}

-- arabicLigatureShaddaWithDammaIsolatedForm BMPString ::= {0, 0, 252, 97}

-- arabicLigatureShaddaWithKasraIsolatedForm BMPString ::= {0, 0, 252, 98}

-- arabicLigatureShaddaWithSuperscriptAlefIsolatedForm BMPString ::=
--   {0, 0, 252, 99}

-- arabicLigatureYehWithHamzaAboveWithRehFinalForm BMPString ::= {0, 0, 252, 100}

-- arabicLigatureYehWithHamzaAboveWithZainFinalForm BMPString ::= {0, 0, 252, 101}

-- arabicLigatureYehWithHamzaAboveWithMeemFinalForm BMPString ::= {0, 0, 252, 102}

-- arabicLigatureYehWithHamzaAboveWithNoonFinalForm BMPString ::= {0, 0, 252, 103}

-- arabicLigatureYehWithHamzaAboveWithAlefMaksuraFinalForm BMPString ::=
--   {0, 0, 252, 104}

-- arabicLigatureYehWithHamzaAboveWithYehFinalForm BMPString ::= {0, 0, 252, 105}

-- arabicLigatureBehWithRehFinalForm BMPString ::= {0, 0, 252, 106}

-- arabicLigatureBehWithZainFinalForm BMPString ::= {0, 0, 252, 107}

-- arabicLigatureBehWithMeemFinalForm BMPString ::= {0, 0, 252, 108}

-- arabicLigatureBehWithNoonFinalForm BMPString ::= {0, 0, 252, 109}

-- arabicLigatureBehWithAlefMaksuraFinalForm BMPString ::= {0, 0, 252, 110}

-- arabicLigatureBehWithYehFinalForm BMPString ::= {0, 0, 252, 111}

-- arabicLigatureTehWithRehFinalForm BMPString ::= {0, 0, 252, 112}

-- arabicLigatureTehWithZainFinalForm BMPString ::= {0, 0, 252, 113}

-- arabicLigatureTehWithMeemFinalForm BMPString ::= {0, 0, 252, 114}

-- arabicLigatureTehWithNoonFinalForm BMPString ::= {0, 0, 252, 115}

-- arabicLigatureTehWithAlefMaksuraFinalForm BMPString ::= {0, 0, 252, 116}

-- arabicLigatureTehWithYehFinalForm BMPString ::= {0, 0, 252, 117}

-- arabicLigatureThehWithRehFinalForm BMPString ::= {0, 0, 252, 118}

-- arabicLigatureThehWithZainFinalForm BMPString ::= {0, 0, 252, 119}

-- arabicLigatureThehWithMeemFinalForm BMPString ::= {0, 0, 252, 120}

-- arabicLigatureThehWithNoonFinalForm BMPString ::= {0, 0, 252, 121}

-- arabicLigatureThehWithAlefMaksuraFinalForm BMPString ::= {0, 0, 252, 122}

-- arabicLigatureThehWithYehFinalForm BMPString ::= {0, 0, 252, 123}

-- arabicLigatureFehWithAlefMaksuraFinalForm BMPString ::= {0, 0, 252, 124}

-- arabicLigatureFehWithYehFinalForm BMPString ::= {0, 0, 252, 125}

-- arabicLigatureQafWithAlefMaksuraFinalForm BMPString ::= {0, 0, 252, 126}

-- arabicLigatureQafWithYehFinalForm BMPString ::= {0, 0, 252, 127}

-- arabicLigatureKafWithAlefFinalForm BMPString ::= {0, 0, 252, 128}

-- arabicLigatureKafWithLamFinalForm BMPString ::= {0, 0, 252, 129}

-- arabicLigatureKafWithMeemFinalForm BMPString ::= {0, 0, 252, 130}

-- arabicLigatureKafWithAlefMaksuraFinalForm BMPString ::= {0, 0, 252, 131}

-- arabicLigatureKafWithYehFinalForm BMPString ::= {0, 0, 252, 132}

-- arabicLigatureLamWithMeemFinalForm BMPString ::= {0, 0, 252, 133}

-- arabicLigatureLamWithAlefMaksuraFinalForm BMPString ::= {0, 0, 252, 134}

-- arabicLigatureLamWithYehFinalForm BMPString ::= {0, 0, 252, 135}

-- arabicLigatureMeemWithAlefFinalForm BMPString ::= {0, 0, 252, 136}

-- arabicLigatureMeemWithMeemFinalForm BMPString ::= {0, 0, 252, 137}

-- arabicLigatureNoonWithRehFinalForm BMPString ::= {0, 0, 252, 138}

-- arabicLigatureNoonWithZainFinalForm BMPString ::= {0, 0, 252, 139}

-- arabicLigatureNoonWithMeemFinalForm BMPString ::= {0, 0, 252, 140}

-- arabicLigatureNoonWithNoonFinalForm BMPString ::= {0, 0, 252, 141}

-- arabicLigatureNoonWithAlefMaksuraFinalForm BMPString ::= {0, 0, 252, 142}

-- arabicLigatureNoonWithYehFinalForm BMPString ::= {0, 0, 252, 143}

-- arabicLigatureAlefMaksuraWithSuperscriptAlefFinalForm BMPString ::=
--   {0, 0, 252, 144}

-- arabicLigatureYehWithRehFinalForm BMPString ::= {0, 0, 252, 145}

-- arabicLigatureYehWithZainFinalForm BMPString ::= {0, 0, 252, 146}

-- arabicLigatureYehWithMeemFinalForm BMPString ::= {0, 0, 252, 147}

-- arabicLigatureYehWithNoonFinalForm BMPString ::= {0, 0, 252, 148}

-- arabicLigatureYehWithAlefMaksuraFinalForm BMPString ::= {0, 0, 252, 149}

-- arabicLigatureYehWithYehFinalForm BMPString ::= {0, 0, 252, 150}

-- arabicLigatureYehWithHamzaAboveWithJeemInitialForm BMPString ::=
--   {0, 0, 252, 151}

-- arabicLigatureYehWithHamzaAboveWithHahInitialForm BMPString ::=
--   {0, 0, 252, 152}

-- arabicLigatureYehWithHamzaAboveWithKhahInitialForm BMPString ::=
--   {0, 0, 252, 153}

-- arabicLigatureYehWithHamzaAboveWithMeemInitialForm BMPString ::=
--   {0, 0, 252, 154}

-- arabicLigatureYehWithHamzaAboveWithHehInitialForm BMPString ::=
--   {0, 0, 252, 155}

-- arabicLigatureBehWithJeemInitialForm BMPString ::= {0, 0, 252, 156}

-- arabicLigatureBehWithHahInitialForm BMPString ::= {0, 0, 252, 157}

-- arabicLigatureBehWithKhahInitialForm BMPString ::= {0, 0, 252, 158}

-- arabicLigatureBehWithMeemInitialForm BMPString ::= {0, 0, 252, 159}

-- arabicLigatureBehWithHehInitialForm BMPString ::= {0, 0, 252, 160}

-- arabicLigatureTehWithJeemInitialForm BMPString ::= {0, 0, 252, 161}

-- arabicLigatureTehWithHahInitialForm BMPString ::= {0, 0, 252, 162}

-- arabicLigatureTehWithKhahInitialForm BMPString ::= {0, 0, 252, 163}

-- arabicLigatureTehWithMeemInitialForm BMPString ::= {0, 0, 252, 164}

-- arabicLigatureTehWithHehInitialForm BMPString ::= {0, 0, 252, 165}

-- arabicLigatureThehWithMeemInitialForm BMPString ::= {0, 0, 252, 166}

-- arabicLigatureJeemWithHahInitialForm BMPString ::= {0, 0, 252, 167}

-- arabicLigatureJeemWithMeemInitialForm BMPString ::= {0, 0, 252, 168}

-- arabicLigatureHahWithJeemInitialForm BMPString ::= {0, 0, 252, 169}

-- arabicLigatureHahWithMeemInitialForm BMPString ::= {0, 0, 252, 170}

-- arabicLigatureKhahWithJeemInitialForm BMPString ::= {0, 0, 252, 171}

-- arabicLigatureKhahWithMeemInitialForm BMPString ::= {0, 0, 252, 172}

-- arabicLigatureSeenWithJeemInitialForm BMPString ::= {0, 0, 252, 173}

-- arabicLigatureSeenWithHahInitialForm BMPString ::= {0, 0, 252, 174}

-- arabicLigatureSeenWithKhahInitialForm BMPString ::= {0, 0, 252, 175}

-- arabicLigatureSeenWithMeemInitialForm BMPString ::= {0, 0, 252, 176}

-- arabicLigatureSadWithHahInitialForm BMPString ::= {0, 0, 252, 177}

-- arabicLigatureSadWithKhahInitialForm BMPString ::= {0, 0, 252, 178}

-- arabicLigatureSadWithMeemInitialForm BMPString ::= {0, 0, 252, 179}

-- arabicLigatureDadWithJeemInitialForm BMPString ::= {0, 0, 252, 180}

-- arabicLigatureDadWithHahInitialForm BMPString ::= {0, 0, 252, 181}

-- arabicLigatureDadWithKhahInitialForm BMPString ::= {0, 0, 252, 182}

-- arabicLigatureDadWithMeemInitialForm BMPString ::= {0, 0, 252, 183}

-- arabicLigatureTahWithHahInitialForm BMPString ::= {0, 0, 252, 184}

-- arabicLigatureZahWithMeemInitialForm BMPString ::= {0, 0, 252, 185}

-- arabicLigatureAinWithJeemInitialForm BMPString ::= {0, 0, 252, 186}

-- arabicLigatureAinWithMeemInitialForm BMPString ::= {0, 0, 252, 187}

-- arabicLigatureGhainWithJeemInitialForm BMPString ::= {0, 0, 252, 188}

-- arabicLigatureGhainWithMeemInitialForm BMPString ::= {0, 0, 252, 189}

-- arabicLigatureFehWithJeemInitialForm BMPString ::= {0, 0, 252, 190}

-- arabicLigatureFehWithHahInitialForm BMPString ::= {0, 0, 252, 191}

-- arabicLigatureFehWithKhahInitialForm BMPString ::= {0, 0, 252, 192}

-- arabicLigatureFehWithMeemInitialForm BMPString ::= {0, 0, 252, 193}

-- arabicLigatureQafWithHahInitialForm BMPString ::= {0, 0, 252, 194}

-- arabicLigatureQafWithMeemInitialForm BMPString ::= {0, 0, 252, 195}

-- arabicLigatureKafWithJeemInitialForm BMPString ::= {0, 0, 252, 196}

-- arabicLigatureKafWithHahInitialForm BMPString ::= {0, 0, 252, 197}

-- arabicLigatureKafWithKhahInitialForm BMPString ::= {0, 0, 252, 198}

-- arabicLigatureKafWithLamInitialForm BMPString ::= {0, 0, 252, 199}

-- arabicLigatureKafWithMeemInitialForm BMPString ::= {0, 0, 252, 200}

-- arabicLigatureLamWithJeemInitialForm BMPString ::= {0, 0, 252, 201}

-- arabicLigatureLamWithHahInitialForm BMPString ::= {0, 0, 252, 202}

-- arabicLigatureLamWithKhahInitialForm BMPString ::= {0, 0, 252, 203}

-- arabicLigatureLamWithMeemInitialForm BMPString ::= {0, 0, 252, 204}

-- arabicLigatureLamWithHehInitialForm BMPString ::= {0, 0, 252, 205}

-- arabicLigatureMeemWithJeemInitialForm BMPString ::= {0, 0, 252, 206}

-- arabicLigatureMeemWithHahInitialForm BMPString ::= {0, 0, 252, 207}

-- arabicLigatureMeemWithKhahInitialForm BMPString ::= {0, 0, 252, 208}

-- arabicLigatureMeemWithMeemInitialForm BMPString ::= {0, 0, 252, 209}

-- arabicLigatureNoonWithJeemInitialForm BMPString ::= {0, 0, 252, 210}

-- arabicLigatureNoonWithHahInitialForm BMPString ::= {0, 0, 252, 211}

-- arabicLigatureNoonWithKhahInitialForm BMPString ::= {0, 0, 252, 212}

-- arabicLigatureNoonWithMeemInitialForm BMPString ::= {0, 0, 252, 213}

-- arabicLigatureNoonWithHehInitialForm BMPString ::= {0, 0, 252, 214}

-- arabicLigatureHehWithJeemInitialForm BMPString ::= {0, 0, 252, 215}

-- arabicLigatureHehWithMeemInitialForm BMPString ::= {0, 0, 252, 216}

-- arabicLigatureHehWithSuperscriptAlefInitialForm BMPString ::= {0, 0, 252, 217}

-- arabicLigatureYehWithJeemInitialForm BMPString ::= {0, 0, 252, 218}

-- arabicLigatureYehWithHahInitialForm BMPString ::= {0, 0, 252, 219}

-- arabicLigatureYehWithKhahInitialForm BMPString ::= {0, 0, 252, 220}

-- arabicLigatureYehWithMeemInitialForm BMPString ::= {0, 0, 252, 221}

-- arabicLigatureYehWithHehInitialForm BMPString ::= {0, 0, 252, 222}

-- arabicLigatureYehWithHamzaAboveWithMeemMedialForm BMPString ::=
--   {0, 0, 252, 223}

-- arabicLigatureYehWithHamzaAboveWithHehMedialForm BMPString ::= {0, 0, 252, 224}

-- arabicLigatureBehWithMeemMedialForm BMPString ::= {0, 0, 252, 225}

-- arabicLigatureBehWithHehMedialForm BMPString ::= {0, 0, 252, 226}

-- arabicLigatureTehWithMeemMedialForm BMPString ::= {0, 0, 252, 227}

-- arabicLigatureTehWithHehMedialForm BMPString ::= {0, 0, 252, 228}

-- arabicLigatureThehWithMeemMedialForm BMPString ::= {0, 0, 252, 229}

-- arabicLigatureThehWithHehMedialForm BMPString ::= {0, 0, 252, 230}

-- arabicLigatureSeenWithMeemMedialForm BMPString ::= {0, 0, 252, 231}

-- arabicLigatureSeenWithHehMedialForm BMPString ::= {0, 0, 252, 232}

-- arabicLigatureSheenWithMeemMedialForm BMPString ::= {0, 0, 252, 233}

-- arabicLigatureSheenWithHehMedialForm BMPString ::= {0, 0, 252, 234}

-- arabicLigatureKafWithLamMedialForm BMPString ::= {0, 0, 252, 235}

-- arabicLigatureKafWithMeemMedialForm BMPString ::= {0, 0, 252, 236}

-- arabicLigatureLamWithMeemMedialForm BMPString ::= {0, 0, 252, 237}

-- arabicLigatureNoonWithMeemMedialForm BMPString ::= {0, 0, 252, 238}

-- arabicLigatureNoonWithHehMedialForm BMPString ::= {0, 0, 252, 239}

-- arabicLigatureYehWithMeemMedialForm BMPString ::= {0, 0, 252, 240}

-- arabicLigatureYehWithHehMedialForm BMPString ::= {0, 0, 252, 241}

-- arabicLigatureShaddaWithFathaMedialForm BMPString ::= {0, 0, 252, 242}

-- arabicLigatureShaddaWithDammaMedialForm BMPString ::= {0, 0, 252, 243}

-- arabicLigatureShaddaWithKasraMedialForm BMPString ::= {0, 0, 252, 244}

-- arabicLigatureTahWithAlefMaksuraIsolatedForm BMPString ::= {0, 0, 252, 245}

-- arabicLigatureTahWithYehIsolatedForm BMPString ::= {0, 0, 252, 246}

-- arabicLigatureAinWithAlefMaksuraIsolatedForm BMPString ::= {0, 0, 252, 247}

-- arabicLigatureAinWithYehIsolatedForm BMPString ::= {0, 0, 252, 248}

-- arabicLigatureGhainWithAlefMaksuraIsolatedForm BMPString ::= {0, 0, 252, 249}

-- arabicLigatureGhainWithYehIsolatedForm BMPString ::= {0, 0, 252, 250}

-- arabicLigatureSeenWithAlefMaksuraIsolatedForm BMPString ::= {0, 0, 252, 251}

-- arabicLigatureSeenWithYehIsolatedForm BMPString ::= {0, 0, 252, 252}

-- arabicLigatureSheenWithAlefMaksuraIsolatedForm BMPString ::= {0, 0, 252, 253}

-- arabicLigatureSheenWithYehIsolatedForm BMPString ::= {0, 0, 252, 254}

-- arabicLigatureHahWithAlefMaksuraIsolatedForm BMPString ::= {0, 0, 252, 255}

-- arabicLigatureHahWithYehIsolatedForm BMPString ::= {0, 0, 253, 0}

-- arabicLigatureJeemWithAlefMaksuraIsolatedForm BMPString ::= {0, 0, 253, 1}

-- arabicLigatureJeemWithYehIsolatedForm BMPString ::= {0, 0, 253, 2}

-- arabicLigatureKhahWithAlefMaksuraIsolatedForm BMPString ::= {0, 0, 253, 3}

-- arabicLigatureKhahWithYehIsolatedForm BMPString ::= {0, 0, 253, 4}

-- arabicLigatureSadWithAlefMaksuraIsolatedForm BMPString ::= {0, 0, 253, 5}

-- arabicLigatureSadWithYehIsolatedForm BMPString ::= {0, 0, 253, 6}

-- arabicLigatureDadWithAlefMaksuraIsolatedForm BMPString ::= {0, 0, 253, 7}

-- arabicLigatureDadWithYehIsolatedForm BMPString ::= {0, 0, 253, 8}

-- arabicLigatureSheenWithJeemIsolatedForm BMPString ::= {0, 0, 253, 9}

-- arabicLigatureSheenWithHahIsolatedForm BMPString ::= {0, 0, 253, 10}

-- arabicLigatureSheenWithKhahIsolatedForm BMPString ::= {0, 0, 253, 11}

-- arabicLigatureSheenWithMeemIsolatedForm BMPString ::= {0, 0, 253, 12}

-- arabicLigatureSheenWithRehIsolatedForm BMPString ::= {0, 0, 253, 13}

-- arabicLigatureSeenWithRehIsolatedForm BMPString ::= {0, 0, 253, 14}

-- arabicLigatureSadWithRehIsolatedForm BMPString ::= {0, 0, 253, 15}

-- arabicLigatureDadWithRehIsolatedForm BMPString ::= {0, 0, 253, 16}

-- arabicLigatureTahWithAlefMaksuraFinalForm BMPString ::= {0, 0, 253, 17}

-- arabicLigatureTahWithYehFinalForm BMPString ::= {0, 0, 253, 18}

-- arabicLigatureAinWithAlefMaksuraFinalForm BMPString ::= {0, 0, 253, 19}

-- arabicLigatureAinWithYehFinalForm BMPString ::= {0, 0, 253, 20}

-- arabicLigatureGhainWithAlefMaksuraFinalForm BMPString ::= {0, 0, 253, 21}

-- arabicLigatureGhainWithYehFinalForm BMPString ::= {0, 0, 253, 22}

-- arabicLigatureSeenWithAlefMaksuraFinalForm BMPString ::= {0, 0, 253, 23}

-- arabicLigatureSeenWithYehFinalForm BMPString ::= {0, 0, 253, 24}

-- arabicLigatureSheenWithAlefMaksuraFinalForm BMPString ::= {0, 0, 253, 25}

-- arabicLigatureSheenWithYehFinalForm BMPString ::= {0, 0, 253, 26}

-- arabicLigatureHahWithAlefMaksuraFinalForm BMPString ::= {0, 0, 253, 27}

-- arabicLigatureHahWithYehFinalForm BMPString ::= {0, 0, 253, 28}

-- arabicLigatureJeemWithAlefMaksuraFinalForm BMPString ::= {0, 0, 253, 29}

-- arabicLigatureJeemWithYehFinalForm BMPString ::= {0, 0, 253, 30}

-- arabicLigatureKhahWithAlefMaksuraFinalForm BMPString ::= {0, 0, 253, 31}

-- arabicLigatureKhahWithYehFinalForm BMPString ::= {0, 0, 253, 32}

-- arabicLigatureSadWithAlefMaksuraFinalForm BMPString ::= {0, 0, 253, 33}

-- arabicLigatureSadWithYehFinalForm BMPString ::= {0, 0, 253, 34}

-- arabicLigatureDadWithAlefMaksuraFinalForm BMPString ::= {0, 0, 253, 35}

-- arabicLigatureDadWithYehFinalForm BMPString ::= {0, 0, 253, 36}

-- arabicLigatureSheenWithJeemFinalForm BMPString ::= {0, 0, 253, 37}

-- arabicLigatureSheenWithHahFinalForm BMPString ::= {0, 0, 253, 38}

-- arabicLigatureSheenWithKhahFinalForm BMPString ::= {0, 0, 253, 39}

-- arabicLigatureSheenWithMeemFinalForm BMPString ::= {0, 0, 253, 40}

-- arabicLigatureSheenWithRehFinalForm BMPString ::= {0, 0, 253, 41}

-- arabicLigatureSeenWithRehFinalForm BMPString ::= {0, 0, 253, 42}

-- arabicLigatureSadWithRehFinalForm BMPString ::= {0, 0, 253, 43}

-- arabicLigatureDadWithRehFinalForm BMPString ::= {0, 0, 253, 44}

-- arabicLigatureSheenWithJeemInitialForm BMPString ::= {0, 0, 253, 45}

-- arabicLigatureSheenWithHahInitialForm BMPString ::= {0, 0, 253, 46}

-- arabicLigatureSheenWithKhahInitialForm BMPString ::= {0, 0, 253, 47}

-- arabicLigatureSheenWithMeemInitialForm BMPString ::= {0, 0, 253, 48}

-- arabicLigatureSeenWithHehInitialForm BMPString ::= {0, 0, 253, 49}

-- arabicLigatureSheenWithHehInitialForm BMPString ::= {0, 0, 253, 50}

-- arabicLigatureTahWithMeemInitialForm BMPString ::= {0, 0, 253, 51}

-- arabicLigatureSeenWithJeemMedialForm BMPString ::= {0, 0, 253, 52}

-- arabicLigatureSeenWithHahMedialForm BMPString ::= {0, 0, 253, 53}

-- arabicLigatureSeenWithKhahMedialForm BMPString ::= {0, 0, 253, 54}

-- arabicLigatureSheenWithJeemMedialForm BMPString ::= {0, 0, 253, 55}

-- arabicLigatureSheenWithHahMedialForm BMPString ::= {0, 0, 253, 56}

-- arabicLigatureSheenWithKhahMedialForm BMPString ::= {0, 0, 253, 57}

-- arabicLigatureTahWithMeemMedialForm BMPString ::= {0, 0, 253, 58}

-- arabicLigatureZahWithMeemMedialForm BMPString ::= {0, 0, 253, 59}

-- arabicLigatureAlefWithFathatanFinalForm BMPString ::= {0, 0, 253, 60}

-- arabicLigatureAlefWithFathatanIsolatedForm BMPString ::= {0, 0, 253, 61}

-- ornateLeftParenthesis BMPString ::= {0, 0, 253, 62}

-- ornateRightParenthesis BMPString ::= {0, 0, 253, 63}

-- arabicLigatureTehWithJeemWithMeemInitialForm BMPString ::= {0, 0, 253, 80}

-- arabicLigatureTehWithHahWithJeemFinalForm BMPString ::= {0, 0, 253, 81}

-- arabicLigatureTehWithHahWithJeemInitialForm BMPString ::= {0, 0, 253, 82}

-- arabicLigatureTehWithHahWithMeemInitialForm BMPString ::= {0, 0, 253, 83}

-- arabicLigatureTehWithKhahWithMeemInitialForm BMPString ::= {0, 0, 253, 84}

-- arabicLigatureTehWithMeemWithJeemInitialForm BMPString ::= {0, 0, 253, 85}

-- arabicLigatureTehWithMeemWithHahInitialForm BMPString ::= {0, 0, 253, 86}

-- arabicLigatureTehWithMeemWithKhahInitialForm BMPString ::= {0, 0, 253, 87}

-- arabicLigatureJeemWithMeemWithHahFinalForm BMPString ::= {0, 0, 253, 88}

-- arabicLigatureJeemWithMeemWithHahInitialForm BMPString ::= {0, 0, 253, 89}

-- arabicLigatureHahWithMeemWithYehFinalForm BMPString ::= {0, 0, 253, 90}

-- arabicLigatureHahWithMeemWithAlefMaksuraFinalForm BMPString ::= {0, 0, 253, 91}

-- arabicLigatureSeenWithHahWithJeemInitialForm BMPString ::= {0, 0, 253, 92}

-- arabicLigatureSeenWithJeemWithHahInitialForm BMPString ::= {0, 0, 253, 93}

-- arabicLigatureSeenWithJeemWithAlefMaksuraFinalForm BMPString ::=
--   {0, 0, 253, 94}

-- arabicLigatureSeenWithMeemWithHahFinalForm BMPString ::= {0, 0, 253, 95}

-- arabicLigatureSeenWithMeemWithHahInitialForm BMPString ::= {0, 0, 253, 96}

-- arabicLigatureSeenWithMeemWithJeemInitialForm BMPString ::= {0, 0, 253, 97}

-- arabicLigatureSeenWithMeemWithMeemFinalForm BMPString ::= {0, 0, 253, 98}

-- arabicLigatureSeenWithMeemWithMeemInitialForm BMPString ::= {0, 0, 253, 99}

-- arabicLigatureSadWithHahWithHahFinalForm BMPString ::= {0, 0, 253, 100}

-- arabicLigatureSadWithHahWithHahInitialForm BMPString ::= {0, 0, 253, 101}

-- arabicLigatureSadWithMeemWithMeemFinalForm BMPString ::= {0, 0, 253, 102}

-- arabicLigatureSheenWithHahWithMeemFinalForm BMPString ::= {0, 0, 253, 103}

-- arabicLigatureSheenWithHahWithMeemInitialForm BMPString ::= {0, 0, 253, 104}

-- arabicLigatureSheenWithJeemWithYehFinalForm BMPString ::= {0, 0, 253, 105}

-- arabicLigatureSheenWithMeemWithKhahFinalForm BMPString ::= {0, 0, 253, 106}

-- arabicLigatureSheenWithMeemWithKhahInitialForm BMPString ::= {0, 0, 253, 107}

-- arabicLigatureSheenWithMeemWithMeemFinalForm BMPString ::= {0, 0, 253, 108}

-- arabicLigatureSheenWithMeemWithMeemInitialForm BMPString ::= {0, 0, 253, 109}

-- arabicLigatureDadWithHahWithAlefMaksuraFinalForm BMPString ::= {0, 0, 253, 110}

-- arabicLigatureDadWithKhahWithMeemFinalForm BMPString ::= {0, 0, 253, 111}

-- arabicLigatureDadWithKhahWithMeemInitialForm BMPString ::= {0, 0, 253, 112}

-- arabicLigatureTahWithMeemWithHahFinalForm BMPString ::= {0, 0, 253, 113}

-- arabicLigatureTahWithMeemWithHahInitialForm BMPString ::= {0, 0, 253, 114}

-- arabicLigatureTahWithMeemWithMeemInitialForm BMPString ::= {0, 0, 253, 115}

-- arabicLigatureTahWithMeemWithYehFinalForm BMPString ::= {0, 0, 253, 116}

-- arabicLigatureAinWithJeemWithMeemFinalForm BMPString ::= {0, 0, 253, 117}

-- arabicLigatureAinWithMeemWithMeemFinalForm BMPString ::= {0, 0, 253, 118}

-- arabicLigatureAinWithMeemWithMeemInitialForm BMPString ::= {0, 0, 253, 119}

-- arabicLigatureAinWithMeemWithAlefMaksuraFinalForm BMPString ::=
--   {0, 0, 253, 120}

-- arabicLigatureGhainWithMeemWithMeemFinalForm BMPString ::= {0, 0, 253, 121}

-- arabicLigatureGhainWithMeemWithYehFinalForm BMPString ::= {0, 0, 253, 122}

-- arabicLigatureGhainWithMeemWithAlefMaksuraFinalForm BMPString ::=
--   {0, 0, 253, 123}

-- arabicLigatureFehWithKhahWithMeemFinalForm BMPString ::= {0, 0, 253, 124}

-- arabicLigatureFehWithKhahWithMeemInitialForm BMPString ::= {0, 0, 253, 125}

-- arabicLigatureQafWithMeemWithHahFinalForm BMPString ::= {0, 0, 253, 126}

-- arabicLigatureQafWithMeemWithMeemFinalForm BMPString ::= {0, 0, 253, 127}

-- arabicLigatureLamWithHahWithMeemFinalForm BMPString ::= {0, 0, 253, 128}

-- arabicLigatureLamWithHahWithYehFinalForm BMPString ::= {0, 0, 253, 129}

-- arabicLigatureLamWithHahWithAlefMaksuraFinalForm BMPString ::= {0, 0, 253, 130}

-- arabicLigatureLamWithJeemWithJeemInitialForm BMPString ::= {0, 0, 253, 131}

-- arabicLigatureLamWithJeemWithJeemFinalForm BMPString ::= {0, 0, 253, 132}

-- arabicLigatureLamWithKhahWithMeemFinalForm BMPString ::= {0, 0, 253, 133}

-- arabicLigatureLamWithKhahWithMeemInitialForm BMPString ::= {0, 0, 253, 134}

-- arabicLigatureLamWithMeemWithHahFinalForm BMPString ::= {0, 0, 253, 135}

-- arabicLigatureLamWithMeemWithHahInitialForm BMPString ::= {0, 0, 253, 136}

-- arabicLigatureMeemWithHahWithJeemInitialForm BMPString ::= {0, 0, 253, 137}

-- arabicLigatureMeemWithHahWithMeemInitialForm BMPString ::= {0, 0, 253, 138}

-- arabicLigatureMeemWithHahWithYehFinalForm BMPString ::= {0, 0, 253, 139}

-- arabicLigatureMeemWithJeemWithHahInitialForm BMPString ::= {0, 0, 253, 140}

-- arabicLigatureMeemWithJeemWithMeemInitialForm BMPString ::= {0, 0, 253, 141}

-- arabicLigatureMeemWithKhahWithJeemInitialForm BMPString ::= {0, 0, 253, 142}

-- arabicLigatureMeemWithKhahWithMeemInitialForm BMPString ::= {0, 0, 253, 143}

-- arabicLigatureMeemWithJeemWithKhahInitialForm BMPString ::= {0, 0, 253, 146}

-- arabicLigatureHehWithMeemWithJeemInitialForm BMPString ::= {0, 0, 253, 147}

-- arabicLigatureHehWithMeemWithMeemInitialForm BMPString ::= {0, 0, 253, 148}

-- arabicLigatureNoonWithHahWithMeemInitialForm BMPString ::= {0, 0, 253, 149}

-- arabicLigatureNoonWithHahWithAlefMaksuraFinalForm BMPString ::=
--   {0, 0, 253, 150}

-- arabicLigatureNoonWithJeemWithMeemFinalForm BMPString ::= {0, 0, 253, 151}

-- arabicLigatureNoonWithJeemWithMeemInitialForm BMPString ::= {0, 0, 253, 152}

-- arabicLigatureNoonWithJeemWithAlefMaksuraFinalForm BMPString ::=
--   {0, 0, 253, 153}

-- arabicLigatureNoonWithMeemWithYehFinalForm BMPString ::= {0, 0, 253, 154}

-- arabicLigatureNoonWithMeemWithAlefMaksuraFinalForm BMPString ::=
--   {0, 0, 253, 155}

-- arabicLigatureYehWithMeemWithMeemFinalForm BMPString ::= {0, 0, 253, 156}

-- arabicLigatureYehWithMeemWithMeemInitialForm BMPString ::= {0, 0, 253, 157}

-- arabicLigatureBehWithKhahWithYehFinalForm BMPString ::= {0, 0, 253, 158}

-- arabicLigatureTehWithJeemWithYehFinalForm BMPString ::= {0, 0, 253, 159}

-- arabicLigatureTehWithJeemWithAlefMaksuraFinalForm BMPString ::=
--   {0, 0, 253, 160}

-- arabicLigatureTehWithKhahWithYehFinalForm BMPString ::= {0, 0, 253, 161}

-- arabicLigatureTehWithKhahWithAlefMaksuraFinalForm BMPString ::=
--   {0, 0, 253, 162}

-- arabicLigatureTehWithMeemWithYehFinalForm BMPString ::= {0, 0, 253, 163}

-- arabicLigatureTehWithMeemWithAlefMaksuraFinalForm BMPString ::=
--   {0, 0, 253, 164}

-- arabicLigatureJeemWithMeemWithYehFinalForm BMPString ::= {0, 0, 253, 165}

-- arabicLigatureJeemWithHahWithAlefMaksuraFinalForm BMPString ::=
--   {0, 0, 253, 166}

-- arabicLigatureJeemWithMeemWithAlefMaksuraFinalForm BMPString ::=
--   {0, 0, 253, 167}

-- arabicLigatureSeenWithKhahWithAlefMaksuraFinalForm BMPString ::=
--   {0, 0, 253, 168}

-- arabicLigatureSadWithHahWithYehFinalForm BMPString ::= {0, 0, 253, 169}

-- arabicLigatureSheenWithHahWithYehFinalForm BMPString ::= {0, 0, 253, 170}

-- arabicLigatureDadWithHahWithYehFinalForm BMPString ::= {0, 0, 253, 171}

-- arabicLigatureLamWithJeemWithYehFinalForm BMPString ::= {0, 0, 253, 172}

-- arabicLigatureLamWithMeemWithYehFinalForm BMPString ::= {0, 0, 253, 173}

-- arabicLigatureYehWithHahWithYehFinalForm BMPString ::= {0, 0, 253, 174}

-- arabicLigatureYehWithJeemWithYehFinalForm BMPString ::= {0, 0, 253, 175}

-- arabicLigatureYehWithMeemWithYehFinalForm BMPString ::= {0, 0, 253, 176}

-- arabicLigatureMeemWithMeemWithYehFinalForm BMPString ::= {0, 0, 253, 177}

-- arabicLigatureQafWithMeemWithYehFinalForm BMPString ::= {0, 0, 253, 178}

-- arabicLigatureNoonWithHahWithYehFinalForm BMPString ::= {0, 0, 253, 179}

-- arabicLigatureQafWithMeemWithHahInitialForm BMPString ::= {0, 0, 253, 180}

-- arabicLigatureLamWithHahWithMeemInitialForm BMPString ::= {0, 0, 253, 181}

-- arabicLigatureAinWithMeemWithYehFinalForm BMPString ::= {0, 0, 253, 182}

-- arabicLigatureKafWithMeemWithYehFinalForm BMPString ::= {0, 0, 253, 183}

-- arabicLigatureNoonWithJeemWithHahInitialForm BMPString ::= {0, 0, 253, 184}

-- arabicLigatureMeemWithKhahWithYehFinalForm BMPString ::= {0, 0, 253, 185}

-- arabicLigatureLamWithJeemWithMeemInitialForm BMPString ::= {0, 0, 253, 186}

-- arabicLigatureKafWithMeemWithMeemFinalForm BMPString ::= {0, 0, 253, 187}

-- arabicLigatureLamWithJeemWithMeemFinalForm BMPString ::= {0, 0, 253, 188}

-- arabicLigatureNoonWithJeemWithHahFinalForm BMPString ::= {0, 0, 253, 189}

-- arabicLigatureJeemWithHahWithYehFinalForm BMPString ::= {0, 0, 253, 190}

-- arabicLigatureHahWithJeemWithYehFinalForm BMPString ::= {0, 0, 253, 191}

-- arabicLigatureMeemWithJeemWithYehFinalForm BMPString ::= {0, 0, 253, 192}

-- arabicLigatureFehWithMeemWithYehFinalForm BMPString ::= {0, 0, 253, 193}

-- arabicLigatureBehWithHahWithYehFinalForm BMPString ::= {0, 0, 253, 194}

-- arabicLigatureKafWithMeemWithMeemInitialForm BMPString ::= {0, 0, 253, 195}

-- arabicLigatureAinWithJeemWithMeemInitialForm BMPString ::= {0, 0, 253, 196}

-- arabicLigatureSadWithMeemWithMeemInitialForm BMPString ::= {0, 0, 253, 197}

-- arabicLigatureSeenWithKhahWithYehFinalForm BMPString ::= {0, 0, 253, 198}

-- arabicLigatureNoonWithJeemWithYehFinalForm BMPString ::= {0, 0, 253, 199}

-- arabicLigatureSallaUsedAsKoranicStopSignIsolatedForm BMPString ::=
--   {0, 0, 253, 240}

-- arabicLigatureQalaUsedAsKoranicStopSignIsolatedForm BMPString ::=
--   {0, 0, 253, 241}

-- arabicLigatureAllahIsolatedForm BMPString ::= {0, 0, 253, 242}

-- arabicLigatureAkbarIsolatedForm BMPString ::= {0, 0, 253, 243}

-- arabicLigatureMohammadIsolatedForm BMPString ::= {0, 0, 253, 244}

-- arabicLigatureSalamIsolatedForm BMPString ::= {0, 0, 253, 245}

-- arabicLigatureRasoulIsolatedForm BMPString ::= {0, 0, 253, 246}

-- arabicLigatureAlayheIsolatedForm BMPString ::= {0, 0, 253, 247}

-- arabicLigatureWasallamIsolatedForm BMPString ::= {0, 0, 253, 248}

-- arabicLigatureSallaIsolatedForm BMPString ::= {0, 0, 253, 249}

-- arabicLigatureSallallahouAlayheWasallam BMPString ::= {0, 0, 253, 250}

-- arabicLigatureJallajalalouhou BMPString ::= {0, 0, 253, 251}

-- rialSign BMPString ::= {0, 0, 253, 252}

-- variationSelector-1 BMPString ::= {0, 0, 254, 0}

-- variationSelector-2 BMPString ::= {0, 0, 254, 1}

-- variationSelector-3 BMPString ::= {0, 0, 254, 2}

-- variationSelector-4 BMPString ::= {0, 0, 254, 3}

-- variationSelector-5 BMPString ::= {0, 0, 254, 4}

-- variationSelector-6 BMPString ::= {0, 0, 254, 5}

-- variationSelector-7 BMPString ::= {0, 0, 254, 6}

-- variationSelector-8 BMPString ::= {0, 0, 254, 7}

-- variationSelector-9 BMPString ::= {0, 0, 254, 8}

-- variationSelector-10 BMPString ::= {0, 0, 254, 9}

-- variationSelector-11 BMPString ::= {0, 0, 254, 10}

-- variationSelector-12 BMPString ::= {0, 0, 254, 11}

-- variationSelector-13 BMPString ::= {0, 0, 254, 12}

-- variationSelector-14 BMPString ::= {0, 0, 254, 13}

-- variationSelector-15 BMPString ::= {0, 0, 254, 14}

-- variationSelector-16 BMPString ::= {0, 0, 254, 15}

-- combiningLigatureLeftHalf BMPString ::= {0, 0, 254, 32}

-- combiningLigatureRightHalf BMPString ::= {0, 0, 254, 33}

-- combiningDoubleTildeLeftHalf BMPString ::= {0, 0, 254, 34}

-- combiningDoubleTildeRightHalf BMPString ::= {0, 0, 254, 35}

-- presentationFormForVerticalTwoDotLeader BMPString ::= {0, 0, 254, 48}

-- presentationFormForVerticalEmDash BMPString ::= {0, 0, 254, 49}

-- presentationFormForVerticalEnDash BMPString ::= {0, 0, 254, 50}

-- presentationFormForVerticalLowLine BMPString ::= {0, 0, 254, 51}

-- presentationFormForVerticalWavyLowLine BMPString ::= {0, 0, 254, 52}

-- presentationFormForVerticalLeftParenthesis BMPString ::= {0, 0, 254, 53}

-- presentationFormForVerticalRightParenthesis BMPString ::= {0, 0, 254, 54}

-- presentationFormForVerticalLeftCurlyBracket BMPString ::= {0, 0, 254, 55}

-- presentationFormForVerticalRightCurlyBracket BMPString ::= {0, 0, 254, 56}

-- presentationFormForVerticalLeftTortoiseShellBracket BMPString ::=
--   {0, 0, 254, 57}

-- presentationFormForVerticalRightTortoiseShellBracket BMPString ::=
--   {0, 0, 254, 58}

-- presentationFormForVerticalLeftBlackLenticularBracket BMPString ::=
--   {0, 0, 254, 59}

-- presentationFormForVerticalRightBlackLenticularBracket BMPString ::=
--   {0, 0, 254, 60}

-- presentationFormForVerticalLeftDoubleAngleBracket BMPString ::= {0, 0, 254, 61}

-- presentationFormForVerticalRightDoubleAngleBracket BMPString ::=
--   {0, 0, 254, 62}

-- presentationFormForVerticalLeftAngleBracket BMPString ::= {0, 0, 254, 63}

-- presentationFormForVerticalRightAngleBracket BMPString ::= {0, 0, 254, 64}

-- presentationFormForVerticalLeftCornerBracket BMPString ::= {0, 0, 254, 65}

-- presentationFormForVerticalRightCornerBracket BMPString ::= {0, 0, 254, 66}

-- presentationFormForVerticalLeftWhiteCornerBracket BMPString ::= {0, 0, 254, 67}

-- presentationFormForVerticalRightWhiteCornerBracket BMPString ::=
--   {0, 0, 254, 68}

-- sesameDot BMPString ::= {0, 0, 254, 69}

-- whiteSesameDot BMPString ::= {0, 0, 254, 70}

-- dashedOverline BMPString ::= {0, 0, 254, 73}

-- centrelineOverline BMPString ::= {0, 0, 254, 74}

-- wavyOverline BMPString ::= {0, 0, 254, 75}

-- doubleWavyOverline BMPString ::= {0, 0, 254, 76}

-- dashedLowLine BMPString ::= {0, 0, 254, 77}

-- centrelineLowLine BMPString ::= {0, 0, 254, 78}

-- wavyLowLine BMPString ::= {0, 0, 254, 79}

-- smallComma BMPString ::= {0, 0, 254, 80}

-- smallIdeographicComma BMPString ::= {0, 0, 254, 81}

-- smallFullStop BMPString ::= {0, 0, 254, 82}

-- smallSemicolon BMPString ::= {0, 0, 254, 84}

-- smallColon BMPString ::= {0, 0, 254, 85}

-- smallQuestionMark BMPString ::= {0, 0, 254, 86}

-- smallExclamationMark BMPString ::= {0, 0, 254, 87}

-- smallEmDash BMPString ::= {0, 0, 254, 88}

-- smallLeftParenthesis BMPString ::= {0, 0, 254, 89}

-- smallRightParenthesis BMPString ::= {0, 0, 254, 90}

-- smallLeftCurlyBracket BMPString ::= {0, 0, 254, 91}

-- smallRightCurlyBracket BMPString ::= {0, 0, 254, 92}

-- smallLeftTortoiseShellBracket BMPString ::= {0, 0, 254, 93}

-- smallRightTortoiseShellBracket BMPString ::= {0, 0, 254, 94}

-- smallNumberSign BMPString ::= {0, 0, 254, 95}

-- smallAmpersand BMPString ::= {0, 0, 254, 96}

-- smallAsterisk BMPString ::= {0, 0, 254, 97}

-- smallPlusSign BMPString ::= {0, 0, 254, 98}

-- smallHyphen-minus BMPString ::= {0, 0, 254, 99}

-- smallLess-thanSign BMPString ::= {0, 0, 254, 100}

-- smallGreater-thanSign BMPString ::= {0, 0, 254, 101}

-- smallEqualsSign BMPString ::= {0, 0, 254, 102}

-- smallReverseSolidus BMPString ::= {0, 0, 254, 104}

-- smallDollarSign BMPString ::= {0, 0, 254, 105}

-- smallPercentSign BMPString ::= {0, 0, 254, 106}

-- smallCommercialAt BMPString ::= {0, 0, 254, 107}

-- arabicFathatanIsolatedForm BMPString ::= {0, 0, 254, 112}

-- arabicTatweelWithFathatanAbove BMPString ::= {0, 0, 254, 113}

-- arabicDammatanIsolatedForm BMPString ::= {0, 0, 254, 114}

-- arabicTailFragment BMPString ::= {0, 0, 254, 115}

-- arabicKasratanIsolatedForm BMPString ::= {0, 0, 254, 116}

-- arabicFathaIsolatedForm BMPString ::= {0, 0, 254, 118}

-- arabicFathaMedialForm BMPString ::= {0, 0, 254, 119}

-- arabicDammaIsolatedForm BMPString ::= {0, 0, 254, 120}

-- arabicDammaMedialForm BMPString ::= {0, 0, 254, 121}

-- arabicKasraIsolatedForm BMPString ::= {0, 0, 254, 122}

-- arabicKasraMedialForm BMPString ::= {0, 0, 254, 123}

-- arabicShaddaIsolatedForm BMPString ::= {0, 0, 254, 124}

-- arabicShaddaMedialForm BMPString ::= {0, 0, 254, 125}

-- arabicSukunIsolatedForm BMPString ::= {0, 0, 254, 126}

-- arabicSukunMedialForm BMPString ::= {0, 0, 254, 127}

-- arabicLetterHamzaIsolatedForm BMPString ::= {0, 0, 254, 128}

-- arabicLetterAlefWithMaddaAboveIsolatedForm BMPString ::= {0, 0, 254, 129}

-- arabicLetterAlefWithMaddaAboveFinalForm BMPString ::= {0, 0, 254, 130}

-- arabicLetterAlefWithHamzaAboveIsolatedForm BMPString ::= {0, 0, 254, 131}

-- arabicLetterAlefWithHamzaAboveFinalForm BMPString ::= {0, 0, 254, 132}

-- arabicLetterWawWithHamzaAboveIsolatedForm BMPString ::= {0, 0, 254, 133}

-- arabicLetterWawWithHamzaAboveFinalForm BMPString ::= {0, 0, 254, 134}

-- arabicLetterAlefWithHamzaBelowIsolatedForm BMPString ::= {0, 0, 254, 135}

-- arabicLetterAlefWithHamzaBelowFinalForm BMPString ::= {0, 0, 254, 136}

-- arabicLetterYehWithHamzaAboveIsolatedForm BMPString ::= {0, 0, 254, 137}

-- arabicLetterYehWithHamzaAboveFinalForm BMPString ::= {0, 0, 254, 138}

-- arabicLetterYehWithHamzaAboveInitialForm BMPString ::= {0, 0, 254, 139}

-- arabicLetterYehWithHamzaAboveMedialForm BMPString ::= {0, 0, 254, 140}

-- arabicLetterAlefIsolatedForm BMPString ::= {0, 0, 254, 141}

-- arabicLetterAlefFinalForm BMPString ::= {0, 0, 254, 142}

-- arabicLetterBehIsolatedForm BMPString ::= {0, 0, 254, 143}

-- arabicLetterBehFinalForm BMPString ::= {0, 0, 254, 144}

-- arabicLetterBehInitialForm BMPString ::= {0, 0, 254, 145}

-- arabicLetterBehMedialForm BMPString ::= {0, 0, 254, 146}

-- arabicLetterTehMarbutaIsolatedForm BMPString ::= {0, 0, 254, 147}

-- arabicLetterTehMarbutaFinalForm BMPString ::= {0, 0, 254, 148}

-- arabicLetterTehIsolatedForm BMPString ::= {0, 0, 254, 149}

-- arabicLetterTehFinalForm BMPString ::= {0, 0, 254, 150}

-- arabicLetterTehInitialForm BMPString ::= {0, 0, 254, 151}

-- arabicLetterTehMedialForm BMPString ::= {0, 0, 254, 152}

-- arabicLetterThehIsolatedForm BMPString ::= {0, 0, 254, 153}

-- arabicLetterThehFinalForm BMPString ::= {0, 0, 254, 154}

-- arabicLetterThehInitialForm BMPString ::= {0, 0, 254, 155}

-- arabicLetterThehMedialForm BMPString ::= {0, 0, 254, 156}

-- arabicLetterJeemIsolatedForm BMPString ::= {0, 0, 254, 157}

-- arabicLetterJeemFinalForm BMPString ::= {0, 0, 254, 158}

-- arabicLetterJeemInitialForm BMPString ::= {0, 0, 254, 159}

-- arabicLetterJeemMedialForm BMPString ::= {0, 0, 254, 160}

-- arabicLetterHahIsolatedForm BMPString ::= {0, 0, 254, 161}

-- arabicLetterHahFinalForm BMPString ::= {0, 0, 254, 162}

-- arabicLetterHahInitialForm BMPString ::= {0, 0, 254, 163}

-- arabicLetterHahMedialForm BMPString ::= {0, 0, 254, 164}

-- arabicLetterKhahIsolatedForm BMPString ::= {0, 0, 254, 165}

-- arabicLetterKhahFinalForm BMPString ::= {0, 0, 254, 166}

-- arabicLetterKhahInitialForm BMPString ::= {0, 0, 254, 167}

-- arabicLetterKhahMedialForm BMPString ::= {0, 0, 254, 168}

-- arabicLetterDalIsolatedForm BMPString ::= {0, 0, 254, 169}

-- arabicLetterDalFinalForm BMPString ::= {0, 0, 254, 170}

-- arabicLetterThalIsolatedForm BMPString ::= {0, 0, 254, 171}

-- arabicLetterThalFinalForm BMPString ::= {0, 0, 254, 172}

-- arabicLetterRehIsolatedForm BMPString ::= {0, 0, 254, 173}

-- arabicLetterRehFinalForm BMPString ::= {0, 0, 254, 174}

-- arabicLetterZainIsolatedForm BMPString ::= {0, 0, 254, 175}

-- arabicLetterZainFinalForm BMPString ::= {0, 0, 254, 176}

-- arabicLetterSeenIsolatedForm BMPString ::= {0, 0, 254, 177}

-- arabicLetterSeenFinalForm BMPString ::= {0, 0, 254, 178}

-- arabicLetterSeenInitialForm BMPString ::= {0, 0, 254, 179}

-- arabicLetterSeenMedialForm BMPString ::= {0, 0, 254, 180}

-- arabicLetterSheenIsolatedForm BMPString ::= {0, 0, 254, 181}

-- arabicLetterSheenFinalForm BMPString ::= {0, 0, 254, 182}

-- arabicLetterSheenInitialForm BMPString ::= {0, 0, 254, 183}

-- arabicLetterSheenMedialForm BMPString ::= {0, 0, 254, 184}

-- arabicLetterSadIsolatedForm BMPString ::= {0, 0, 254, 185}

-- arabicLetterSadFinalForm BMPString ::= {0, 0, 254, 186}

-- arabicLetterSadInitialForm BMPString ::= {0, 0, 254, 187}

-- arabicLetterSadMedialForm BMPString ::= {0, 0, 254, 188}

-- arabicLetterDadIsolatedForm BMPString ::= {0, 0, 254, 189}

-- arabicLetterDadFinalForm BMPString ::= {0, 0, 254, 190}

-- arabicLetterDadInitialForm BMPString ::= {0, 0, 254, 191}

-- arabicLetterDadMedialForm BMPString ::= {0, 0, 254, 192}

-- arabicLetterTahIsolatedForm BMPString ::= {0, 0, 254, 193}

-- arabicLetterTahFinalForm BMPString ::= {0, 0, 254, 194}

-- arabicLetterTahInitialForm BMPString ::= {0, 0, 254, 195}

-- arabicLetterTahMedialForm BMPString ::= {0, 0, 254, 196}

-- arabicLetterZahIsolatedForm BMPString ::= {0, 0, 254, 197}

-- arabicLetterZahFinalForm BMPString ::= {0, 0, 254, 198}

-- arabicLetterZahInitialForm BMPString ::= {0, 0, 254, 199}

-- arabicLetterZahMedialForm BMPString ::= {0, 0, 254, 200}

-- arabicLetterAinIsolatedForm BMPString ::= {0, 0, 254, 201}

-- arabicLetterAinFinalForm BMPString ::= {0, 0, 254, 202}

-- arabicLetterAinInitialForm BMPString ::= {0, 0, 254, 203}

-- arabicLetterAinMedialForm BMPString ::= {0, 0, 254, 204}

-- arabicLetterGhainIsolatedForm BMPString ::= {0, 0, 254, 205}

-- arabicLetterGhainFinalForm BMPString ::= {0, 0, 254, 206}

-- arabicLetterGhainInitialForm BMPString ::= {0, 0, 254, 207}

-- arabicLetterGhainMedialForm BMPString ::= {0, 0, 254, 208}

-- arabicLetterFehIsolatedForm BMPString ::= {0, 0, 254, 209}

-- arabicLetterFehFinalForm BMPString ::= {0, 0, 254, 210}

-- arabicLetterFehInitialForm BMPString ::= {0, 0, 254, 211}

-- arabicLetterFehMedialForm BMPString ::= {0, 0, 254, 212}

-- arabicLetterQafIsolatedForm BMPString ::= {0, 0, 254, 213}

-- arabicLetterQafFinalForm BMPString ::= {0, 0, 254, 214}

-- arabicLetterQafInitialForm BMPString ::= {0, 0, 254, 215}

-- arabicLetterQafMedialForm BMPString ::= {0, 0, 254, 216}

-- arabicLetterKafIsolatedForm BMPString ::= {0, 0, 254, 217}

-- arabicLetterKafFinalForm BMPString ::= {0, 0, 254, 218}

-- arabicLetterKafInitialForm BMPString ::= {0, 0, 254, 219}

-- arabicLetterKafMedialForm BMPString ::= {0, 0, 254, 220}

-- arabicLetterLamIsolatedForm BMPString ::= {0, 0, 254, 221}

-- arabicLetterLamFinalForm BMPString ::= {0, 0, 254, 222}

-- arabicLetterLamInitialForm BMPString ::= {0, 0, 254, 223}

-- arabicLetterLamMedialForm BMPString ::= {0, 0, 254, 224}

-- arabicLetterMeemIsolatedForm BMPString ::= {0, 0, 254, 225}

-- arabicLetterMeemFinalForm BMPString ::= {0, 0, 254, 226}

-- arabicLetterMeemInitialForm BMPString ::= {0, 0, 254, 227}

-- arabicLetterMeemMedialForm BMPString ::= {0, 0, 254, 228}

-- arabicLetterNoonIsolatedForm BMPString ::= {0, 0, 254, 229}

-- arabicLetterNoonFinalForm BMPString ::= {0, 0, 254, 230}

-- arabicLetterNoonInitialForm BMPString ::= {0, 0, 254, 231}

-- arabicLetterNoonMedialForm BMPString ::= {0, 0, 254, 232}

-- arabicLetterHehIsolatedForm BMPString ::= {0, 0, 254, 233}

-- arabicLetterHehFinalForm BMPString ::= {0, 0, 254, 234}

-- arabicLetterHehInitialForm BMPString ::= {0, 0, 254, 235}

-- arabicLetterHehMedialForm BMPString ::= {0, 0, 254, 236}

-- arabicLetterWawIsolatedForm BMPString ::= {0, 0, 254, 237}

-- arabicLetterWawFinalForm BMPString ::= {0, 0, 254, 238}

-- arabicLetterAlefMaksuraIsolatedForm BMPString ::= {0, 0, 254, 239}

-- arabicLetterAlefMaksuraFinalForm BMPString ::= {0, 0, 254, 240}

-- arabicLetterYehIsolatedForm BMPString ::= {0, 0, 254, 241}

-- arabicLetterYehFinalForm BMPString ::= {0, 0, 254, 242}

-- arabicLetterYehInitialForm BMPString ::= {0, 0, 254, 243}

-- arabicLetterYehMedialForm BMPString ::= {0, 0, 254, 244}

-- arabicLigatureLamWithAlefWithMaddaAboveIsolatedForm BMPString ::=
--   {0, 0, 254, 245}

-- arabicLigatureLamWithAlefWithMaddaAboveFinalForm BMPString ::= {0, 0, 254, 246}

-- arabicLigatureLamWithAlefWithHamzaAboveIsolatedForm BMPString ::=
--   {0, 0, 254, 247}

-- arabicLigatureLamWithAlefWithHamzaAboveFinalForm BMPString ::= {0, 0, 254, 248}

-- arabicLigatureLamWithAlefWithHamzaBelowIsolatedForm BMPString ::=
--   {0, 0, 254, 249}

-- arabicLigatureLamWithAlefWithHamzaBelowFinalForm BMPString ::= {0, 0, 254, 250}

-- arabicLigatureLamWithAlefIsolatedForm BMPString ::= {0, 0, 254, 251}

-- arabicLigatureLamWithAlefFinalForm BMPString ::= {0, 0, 254, 252}

-- zeroWidthNo-breakSpace BMPString ::= {0, 0, 254, 255}

-- fullwidthExclamationMark BMPString ::= {0, 0, 255, 1}

-- fullwidthQuotationMark BMPString ::= {0, 0, 255, 2}

-- fullwidthNumberSign BMPString ::= {0, 0, 255, 3}

-- fullwidthDollarSign BMPString ::= {0, 0, 255, 4}

-- fullwidthPercentSign BMPString ::= {0, 0, 255, 5}

-- fullwidthAmpersand BMPString ::= {0, 0, 255, 6}

-- fullwidthApostrophe BMPString ::= {0, 0, 255, 7}

-- fullwidthLeftParenthesis BMPString ::= {0, 0, 255, 8}

-- fullwidthRightParenthesis BMPString ::= {0, 0, 255, 9}

-- fullwidthAsterisk BMPString ::= {0, 0, 255, 10}

-- fullwidthPlusSign BMPString ::= {0, 0, 255, 11}

-- fullwidthComma BMPString ::= {0, 0, 255, 12}

-- fullwidthHyphen-minus BMPString ::= {0, 0, 255, 13}

-- fullwidthFullStop BMPString ::= {0, 0, 255, 14}

-- fullwidthSolidus BMPString ::= {0, 0, 255, 15}

-- fullwidthDigitZero BMPString ::= {0, 0, 255, 16}

-- fullwidthDigitOne BMPString ::= {0, 0, 255, 17}

-- fullwidthDigitTwo BMPString ::= {0, 0, 255, 18}

-- fullwidthDigitThree BMPString ::= {0, 0, 255, 19}

-- fullwidthDigitFour BMPString ::= {0, 0, 255, 20}

-- fullwidthDigitFive BMPString ::= {0, 0, 255, 21}

-- fullwidthDigitSix BMPString ::= {0, 0, 255, 22}

-- fullwidthDigitSeven BMPString ::= {0, 0, 255, 23}

-- fullwidthDigitEight BMPString ::= {0, 0, 255, 24}

-- fullwidthDigitNine BMPString ::= {0, 0, 255, 25}

-- fullwidthColon BMPString ::= {0, 0, 255, 26}

-- fullwidthSemicolon BMPString ::= {0, 0, 255, 27}

-- fullwidthLess-thanSign BMPString ::= {0, 0, 255, 28}

-- fullwidthEqualsSign BMPString ::= {0, 0, 255, 29}

-- fullwidthGreater-thanSign BMPString ::= {0, 0, 255, 30}

-- fullwidthQuestionMark BMPString ::= {0, 0, 255, 31}

-- fullwidthCommercialAt BMPString ::= {0, 0, 255, 32}

-- fullwidthLatinCapitalLetterA BMPString ::= {0, 0, 255, 33}

-- fullwidthLatinCapitalLetterB BMPString ::= {0, 0, 255, 34}

-- fullwidthLatinCapitalLetterC BMPString ::= {0, 0, 255, 35}

-- fullwidthLatinCapitalLetterD BMPString ::= {0, 0, 255, 36}

-- fullwidthLatinCapitalLetterE BMPString ::= {0, 0, 255, 37}

-- fullwidthLatinCapitalLetterF BMPString ::= {0, 0, 255, 38}

-- fullwidthLatinCapitalLetterG BMPString ::= {0, 0, 255, 39}

-- fullwidthLatinCapitalLetterH BMPString ::= {0, 0, 255, 40}

-- fullwidthLatinCapitalLetterI BMPString ::= {0, 0, 255, 41}

-- fullwidthLatinCapitalLetterJ BMPString ::= {0, 0, 255, 42}

-- fullwidthLatinCapitalLetterK BMPString ::= {0, 0, 255, 43}

-- fullwidthLatinCapitalLetterL BMPString ::= {0, 0, 255, 44}

-- fullwidthLatinCapitalLetterM BMPString ::= {0, 0, 255, 45}

-- fullwidthLatinCapitalLetterN BMPString ::= {0, 0, 255, 46}

-- fullwidthLatinCapitalLetterO BMPString ::= {0, 0, 255, 47}

-- fullwidthLatinCapitalLetterP BMPString ::= {0, 0, 255, 48}

-- fullwidthLatinCapitalLetterQ BMPString ::= {0, 0, 255, 49}

-- fullwidthLatinCapitalLetterR BMPString ::= {0, 0, 255, 50}

-- fullwidthLatinCapitalLetterS BMPString ::= {0, 0, 255, 51}

-- fullwidthLatinCapitalLetterT BMPString ::= {0, 0, 255, 52}

-- fullwidthLatinCapitalLetterU BMPString ::= {0, 0, 255, 53}

-- fullwidthLatinCapitalLetterV BMPString ::= {0, 0, 255, 54}

-- fullwidthLatinCapitalLetterW BMPString ::= {0, 0, 255, 55}

-- fullwidthLatinCapitalLetterX BMPString ::= {0, 0, 255, 56}

-- fullwidthLatinCapitalLetterY BMPString ::= {0, 0, 255, 57}

-- fullwidthLatinCapitalLetterZ BMPString ::= {0, 0, 255, 58}

-- fullwidthLeftSquareBracket BMPString ::= {0, 0, 255, 59}

-- fullwidthReverseSolidus BMPString ::= {0, 0, 255, 60}

-- fullwidthRightSquareBracket BMPString ::= {0, 0, 255, 61}

-- fullwidthCircumflexAccent BMPString ::= {0, 0, 255, 62}

-- fullwidthLowLine BMPString ::= {0, 0, 255, 63}

-- fullwidthGraveAccent BMPString ::= {0, 0, 255, 64}

-- fullwidthLatinSmallLetterA BMPString ::= {0, 0, 255, 65}

-- fullwidthLatinSmallLetterB BMPString ::= {0, 0, 255, 66}

-- fullwidthLatinSmallLetterC BMPString ::= {0, 0, 255, 67}

-- fullwidthLatinSmallLetterD BMPString ::= {0, 0, 255, 68}

-- fullwidthLatinSmallLetterE BMPString ::= {0, 0, 255, 69}

-- fullwidthLatinSmallLetterF BMPString ::= {0, 0, 255, 70}

-- fullwidthLatinSmallLetterG BMPString ::= {0, 0, 255, 71}

-- fullwidthLatinSmallLetterH BMPString ::= {0, 0, 255, 72}

-- fullwidthLatinSmallLetterI BMPString ::= {0, 0, 255, 73}

-- fullwidthLatinSmallLetterJ BMPString ::= {0, 0, 255, 74}

-- fullwidthLatinSmallLetterK BMPString ::= {0, 0, 255, 75}

-- fullwidthLatinSmallLetterL BMPString ::= {0, 0, 255, 76}

-- fullwidthLatinSmallLetterM BMPString ::= {0, 0, 255, 77}

-- fullwidthLatinSmallLetterN BMPString ::= {0, 0, 255, 78}

-- fullwidthLatinSmallLetterO BMPString ::= {0, 0, 255, 79}

-- fullwidthLatinSmallLetterP BMPString ::= {0, 0, 255, 80}

-- fullwidthLatinSmallLetterQ BMPString ::= {0, 0, 255, 81}

-- fullwidthLatinSmallLetterR BMPString ::= {0, 0, 255, 82}

-- fullwidthLatinSmallLetterS BMPString ::= {0, 0, 255, 83}

-- fullwidthLatinSmallLetterT BMPString ::= {0, 0, 255, 84}

-- fullwidthLatinSmallLetterU BMPString ::= {0, 0, 255, 85}

-- fullwidthLatinSmallLetterV BMPString ::= {0, 0, 255, 86}

-- fullwidthLatinSmallLetterW BMPString ::= {0, 0, 255, 87}

-- fullwidthLatinSmallLetterX BMPString ::= {0, 0, 255, 88}

-- fullwidthLatinSmallLetterY BMPString ::= {0, 0, 255, 89}

-- fullwidthLatinSmallLetterZ BMPString ::= {0, 0, 255, 90}

-- fullwidthLeftCurlyBracket BMPString ::= {0, 0, 255, 91}

-- fullwidthVerticalLine BMPString ::= {0, 0, 255, 92}

-- fullwidthRightCurlyBracket BMPString ::= {0, 0, 255, 93}

-- fullwidthTilde BMPString ::= {0, 0, 255, 94}

-- fullwidthLeftWhiteParenthesis BMPString ::= {0, 0, 255, 95}

-- fullwidthRightWhiteParenthesis BMPString ::= {0, 0, 255, 96}

-- halfwidthIdeographicFullStop BMPString ::= {0, 0, 255, 97}

-- halfwidthLeftCornerBracket BMPString ::= {0, 0, 255, 98}

-- halfwidthRightCornerBracket BMPString ::= {0, 0, 255, 99}

-- halfwidthIdeographicComma BMPString ::= {0, 0, 255, 100}

-- halfwidthKatakanaMiddleDot BMPString ::= {0, 0, 255, 101}

-- halfwidthKatakanaLetterWo BMPString ::= {0, 0, 255, 102}

-- halfwidthKatakanaLetterSmallA BMPString ::= {0, 0, 255, 103}

-- halfwidthKatakanaLetterSmallI BMPString ::= {0, 0, 255, 104}

-- halfwidthKatakanaLetterSmallU BMPString ::= {0, 0, 255, 105}

-- halfwidthKatakanaLetterSmallE BMPString ::= {0, 0, 255, 106}

-- halfwidthKatakanaLetterSmallO BMPString ::= {0, 0, 255, 107}

-- halfwidthKatakanaLetterSmallYa BMPString ::= {0, 0, 255, 108}

-- halfwidthKatakanaLetterSmallYu BMPString ::= {0, 0, 255, 109}

-- halfwidthKatakanaLetterSmallYo BMPString ::= {0, 0, 255, 110}

-- halfwidthKatakanaLetterSmallTu BMPString ::= {0, 0, 255, 111}

-- halfwidthKatakana-hiraganaProlongedSoundMark BMPString ::= {0, 0, 255, 112}

-- halfwidthKatakanaLetterA BMPString ::= {0, 0, 255, 113}

-- halfwidthKatakanaLetterI BMPString ::= {0, 0, 255, 114}

-- halfwidthKatakanaLetterU BMPString ::= {0, 0, 255, 115}

-- halfwidthKatakanaLetterE BMPString ::= {0, 0, 255, 116}

-- halfwidthKatakanaLetterO BMPString ::= {0, 0, 255, 117}

-- halfwidthKatakanaLetterKa BMPString ::= {0, 0, 255, 118}

-- halfwidthKatakanaLetterKi BMPString ::= {0, 0, 255, 119}

-- halfwidthKatakanaLetterKu BMPString ::= {0, 0, 255, 120}

-- halfwidthKatakanaLetterKe BMPString ::= {0, 0, 255, 121}

-- halfwidthKatakanaLetterKo BMPString ::= {0, 0, 255, 122}

-- halfwidthKatakanaLetterSa BMPString ::= {0, 0, 255, 123}

-- halfwidthKatakanaLetterSi BMPString ::= {0, 0, 255, 124}

-- halfwidthKatakanaLetterSu BMPString ::= {0, 0, 255, 125}

-- halfwidthKatakanaLetterSe BMPString ::= {0, 0, 255, 126}

-- halfwidthKatakanaLetterSo BMPString ::= {0, 0, 255, 127}

-- halfwidthKatakanaLetterTa BMPString ::= {0, 0, 255, 128}

-- halfwidthKatakanaLetterTi BMPString ::= {0, 0, 255, 129}

-- halfwidthKatakanaLetterTu BMPString ::= {0, 0, 255, 130}

-- halfwidthKatakanaLetterTe BMPString ::= {0, 0, 255, 131}

-- halfwidthKatakanaLetterTo BMPString ::= {0, 0, 255, 132}

-- halfwidthKatakanaLetterNa BMPString ::= {0, 0, 255, 133}

-- halfwidthKatakanaLetterNi BMPString ::= {0, 0, 255, 134}

-- halfwidthKatakanaLetterNu BMPString ::= {0, 0, 255, 135}

-- halfwidthKatakanaLetterNe BMPString ::= {0, 0, 255, 136}

-- halfwidthKatakanaLetterNo BMPString ::= {0, 0, 255, 137}

-- halfwidthKatakanaLetterHa BMPString ::= {0, 0, 255, 138}

-- halfwidthKatakanaLetterHi BMPString ::= {0, 0, 255, 139}

-- halfwidthKatakanaLetterHu BMPString ::= {0, 0, 255, 140}

-- halfwidthKatakanaLetterHe BMPString ::= {0, 0, 255, 141}

-- halfwidthKatakanaLetterHo BMPString ::= {0, 0, 255, 142}

-- halfwidthKatakanaLetterMa BMPString ::= {0, 0, 255, 143}

-- halfwidthKatakanaLetterMi BMPString ::= {0, 0, 255, 144}

-- halfwidthKatakanaLetterMu BMPString ::= {0, 0, 255, 145}

-- halfwidthKatakanaLetterMe BMPString ::= {0, 0, 255, 146}

-- halfwidthKatakanaLetterMo BMPString ::= {0, 0, 255, 147}

-- halfwidthKatakanaLetterYa BMPString ::= {0, 0, 255, 148}

-- halfwidthKatakanaLetterYu BMPString ::= {0, 0, 255, 149}

-- halfwidthKatakanaLetterYo BMPString ::= {0, 0, 255, 150}

-- halfwidthKatakanaLetterRa BMPString ::= {0, 0, 255, 151}

-- halfwidthKatakanaLetterRi BMPString ::= {0, 0, 255, 152}

-- halfwidthKatakanaLetterRu BMPString ::= {0, 0, 255, 153}

-- halfwidthKatakanaLetterRe BMPString ::= {0, 0, 255, 154}

-- halfwidthKatakanaLetterRo BMPString ::= {0, 0, 255, 155}

-- halfwidthKatakanaLetterWa BMPString ::= {0, 0, 255, 156}

-- halfwidthKatakanaLetterN BMPString ::= {0, 0, 255, 157}

-- halfwidthKatakanaVoicedSoundMark BMPString ::= {0, 0, 255, 158}

-- halfwidthKatakanaSemi-voicedSoundMark BMPString ::= {0, 0, 255, 159}

-- halfwidthHangulFiller BMPString ::= {0, 0, 255, 160}

-- halfwidthHangulLetterKiyeok BMPString ::= {0, 0, 255, 161}

-- halfwidthHangulLetterSsangkiyeok BMPString ::= {0, 0, 255, 162}

-- halfwidthHangulLetterKiyeok-sios BMPString ::= {0, 0, 255, 163}

-- halfwidthHangulLetterNieun BMPString ::= {0, 0, 255, 164}

-- halfwidthHangulLetterNieun-cieuc BMPString ::= {0, 0, 255, 165}

-- halfwidthHangulLetterNieun-hieuh BMPString ::= {0, 0, 255, 166}

-- halfwidthHangulLetterTikeut BMPString ::= {0, 0, 255, 167}

-- halfwidthHangulLetterSsangtikeut BMPString ::= {0, 0, 255, 168}

-- halfwidthHangulLetterRieul BMPString ::= {0, 0, 255, 169}

-- halfwidthHangulLetterRieul-kiyeok BMPString ::= {0, 0, 255, 170}

-- halfwidthHangulLetterRieul-mieum BMPString ::= {0, 0, 255, 171}

-- halfwidthHangulLetterRieul-pieup BMPString ::= {0, 0, 255, 172}

-- halfwidthHangulLetterRieul-sios BMPString ::= {0, 0, 255, 173}

-- halfwidthHangulLetterRieul-thieuth BMPString ::= {0, 0, 255, 174}

-- halfwidthHangulLetterRieul-phieuph BMPString ::= {0, 0, 255, 175}

-- halfwidthHangulLetterRieul-hieuh BMPString ::= {0, 0, 255, 176}

-- halfwidthHangulLetterMieum BMPString ::= {0, 0, 255, 177}

-- halfwidthHangulLetterPieup BMPString ::= {0, 0, 255, 178}

-- halfwidthHangulLetterSsangpieup BMPString ::= {0, 0, 255, 179}

-- halfwidthHangulLetterPieup-sios BMPString ::= {0, 0, 255, 180}

-- halfwidthHangulLetterSios BMPString ::= {0, 0, 255, 181}

-- halfwidthHangulLetterSsangsios BMPString ::= {0, 0, 255, 182}

-- halfwidthHangulLetterIeung BMPString ::= {0, 0, 255, 183}

-- halfwidthHangulLetterCieuc BMPString ::= {0, 0, 255, 184}

-- halfwidthHangulLetterSsangcieuc BMPString ::= {0, 0, 255, 185}

-- halfwidthHangulLetterChieuch BMPString ::= {0, 0, 255, 186}

-- halfwidthHangulLetterKhieukh BMPString ::= {0, 0, 255, 187}

-- halfwidthHangulLetterThieuth BMPString ::= {0, 0, 255, 188}

-- halfwidthHangulLetterPhieuph BMPString ::= {0, 0, 255, 189}

-- halfwidthHangulLetterHieuh BMPString ::= {0, 0, 255, 190}

-- halfwidthHangulLetterA BMPString ::= {0, 0, 255, 194}

-- halfwidthHangulLetterAe BMPString ::= {0, 0, 255, 195}

-- halfwidthHangulLetterYa BMPString ::= {0, 0, 255, 196}

-- halfwidthHangulLetterYae BMPString ::= {0, 0, 255, 197}

-- halfwidthHangulLetterEo BMPString ::= {0, 0, 255, 198}

-- halfwidthHangulLetterE BMPString ::= {0, 0, 255, 199}

-- halfwidthHangulLetterYeo BMPString ::= {0, 0, 255, 202}

-- halfwidthHangulLetterYe BMPString ::= {0, 0, 255, 203}

-- halfwidthHangulLetterO BMPString ::= {0, 0, 255, 204}

-- halfwidthHangulLetterWa BMPString ::= {0, 0, 255, 205}

-- halfwidthHangulLetterWae BMPString ::= {0, 0, 255, 206}

-- halfwidthHangulLetterOe BMPString ::= {0, 0, 255, 207}

-- halfwidthHangulLetterYo BMPString ::= {0, 0, 255, 210}

-- halfwidthHangulLetterU BMPString ::= {0, 0, 255, 211}

-- halfwidthHangulLetterWeo BMPString ::= {0, 0, 255, 212}

-- halfwidthHangulLetterWe BMPString ::= {0, 0, 255, 213}

-- halfwidthHangulLetterWi BMPString ::= {0, 0, 255, 214}

-- halfwidthHangulLetterYu BMPString ::= {0, 0, 255, 215}

-- halfwidthHangulLetterEu BMPString ::= {0, 0, 255, 218}

-- halfwidthHangulLetterYi BMPString ::= {0, 0, 255, 219}

-- halfwidthHangulLetterI BMPString ::= {0, 0, 255, 220}

-- fullwidthCentSign BMPString ::= {0, 0, 255, 224}

-- fullwidthPoundSign BMPString ::= {0, 0, 255, 225}

-- fullwidthNotSign BMPString ::= {0, 0, 255, 226}

-- fullwidthMacron BMPString ::= {0, 0, 255, 227}

-- fullwidthBrokenBar BMPString ::= {0, 0, 255, 228}

-- fullwidthYenSign BMPString ::= {0, 0, 255, 229}

-- fullwidthWonSign BMPString ::= {0, 0, 255, 230}

-- halfwidthFormsLightVertical BMPString ::= {0, 0, 255, 232}

-- halfwidthLeftwardsArrow BMPString ::= {0, 0, 255, 233}

-- halfwidthUpwardsArrow BMPString ::= {0, 0, 255, 234}

-- halfwidthRightwardsArrow BMPString ::= {0, 0, 255, 235}

-- halfwidthDownwardsArrow BMPString ::= {0, 0, 255, 236}

-- halfwidthBlackSquare BMPString ::= {0, 0, 255, 237}

-- halfwidthWhiteCircle BMPString ::= {0, 0, 255, 238}

-- interlinearAnnotationAnchor BMPString ::= {0, 0, 255, 249}

-- interlinearAnnotationSeparator BMPString ::= {0, 0, 255, 250}

-- interlinearAnnotationTerminator BMPString ::= {0, 0, 255, 251}

-- objectReplacementCharacter BMPString ::= {0, 0, 255, 252}

-- replacementCharacter BMPString ::= {0, 0, 255, 253}

-- oldItalicLetterA UniversalString ::= {0, 1, 3, 0}

-- oldItalicLetterBe UniversalString ::= {0, 1, 3, 1}

-- oldItalicLetterKe UniversalString ::= {0, 1, 3, 2}

-- oldItalicLetterDe UniversalString ::= {0, 1, 3, 3}

-- oldItalicLetterE UniversalString ::= {0, 1, 3, 4}

-- oldItalicLetterVe UniversalString ::= {0, 1, 3, 5}

-- oldItalicLetterZe UniversalString ::= {0, 1, 3, 6}

-- oldItalicLetterHe UniversalString ::= {0, 1, 3, 7}

-- oldItalicLetterThe UniversalString ::= {0, 1, 3, 8}

-- oldItalicLetterI UniversalString ::= {0, 1, 3, 9}

-- oldItalicLetterKa UniversalString ::= {0, 1, 3, 10}

-- oldItalicLetterEl UniversalString ::= {0, 1, 3, 11}

-- oldItalicLetterEm UniversalString ::= {0, 1, 3, 12}

-- oldItalicLetterEn UniversalString ::= {0, 1, 3, 13}

-- oldItalicLetterEsh UniversalString ::= {0, 1, 3, 14}

-- oldItalicLetterO UniversalString ::= {0, 1, 3, 15}

-- oldItalicLetterPe UniversalString ::= {0, 1, 3, 16}

-- oldItalicLetterShe UniversalString ::= {0, 1, 3, 17}

-- oldItalicLetterKu UniversalString ::= {0, 1, 3, 18}

-- oldItalicLetterEr UniversalString ::= {0, 1, 3, 19}

-- oldItalicLetterEs UniversalString ::= {0, 1, 3, 20}

-- oldItalicLetterTe UniversalString ::= {0, 1, 3, 21}

-- oldItalicLetterU UniversalString ::= {0, 1, 3, 22}

-- oldItalicLetterEks UniversalString ::= {0, 1, 3, 23}

-- oldItalicLetterPhe UniversalString ::= {0, 1, 3, 24}

-- oldItalicLetterKhe UniversalString ::= {0, 1, 3, 25}

-- oldItalicLetterEf UniversalString ::= {0, 1, 3, 26}

-- oldItalicLetterErs UniversalString ::= {0, 1, 3, 27}

-- oldItalicLetterChe UniversalString ::= {0, 1, 3, 28}

-- oldItalicLetterIi UniversalString ::= {0, 1, 3, 29}

-- oldItalicLetterUu UniversalString ::= {0, 1, 3, 30}

-- oldItalicNumeralOne UniversalString ::= {0, 1, 3, 32}

-- oldItalicNumeralFive UniversalString ::= {0, 1, 3, 33}

-- oldItalicNumeralTen UniversalString ::= {0, 1, 3, 34}

-- oldItalicNumeralFifty UniversalString ::= {0, 1, 3, 35}

-- gothicLetterAhsa UniversalString ::= {0, 1, 3, 48}

-- gothicLetterBairkan UniversalString ::= {0, 1, 3, 49}

-- gothicLetterGiba UniversalString ::= {0, 1, 3, 50}

-- gothicLetterDags UniversalString ::= {0, 1, 3, 51}

-- gothicLetterAihvus UniversalString ::= {0, 1, 3, 52}

-- gothicLetterQairthra UniversalString ::= {0, 1, 3, 53}

-- gothicLetterIuja UniversalString ::= {0, 1, 3, 54}

-- gothicLetterHagl UniversalString ::= {0, 1, 3, 55}

-- gothicLetterThiuth UniversalString ::= {0, 1, 3, 56}

-- gothicLetterEis UniversalString ::= {0, 1, 3, 57}

-- gothicLetterKusma UniversalString ::= {0, 1, 3, 58}

-- gothicLetterLagus UniversalString ::= {0, 1, 3, 59}

-- gothicLetterManna UniversalString ::= {0, 1, 3, 60}

-- gothicLetterNauths UniversalString ::= {0, 1, 3, 61}

-- gothicLetterJer UniversalString ::= {0, 1, 3, 62}

-- gothicLetterUrus UniversalString ::= {0, 1, 3, 63}

-- gothicLetterPairthra UniversalString ::= {0, 1, 3, 64}

-- gothicLetterNinety UniversalString ::= {0, 1, 3, 65}

-- gothicLetterRaida UniversalString ::= {0, 1, 3, 66}

-- gothicLetterSauil UniversalString ::= {0, 1, 3, 67}

-- gothicLetterTeiws UniversalString ::= {0, 1, 3, 68}

-- gothicLetterWinja UniversalString ::= {0, 1, 3, 69}

-- gothicLetterFaihu UniversalString ::= {0, 1, 3, 70}

-- gothicLetterIggws UniversalString ::= {0, 1, 3, 71}

-- gothicLetterHwair UniversalString ::= {0, 1, 3, 72}

-- gothicLetterOthal UniversalString ::= {0, 1, 3, 73}

-- gothicLetterNineHundred UniversalString ::= {0, 1, 3, 74}

-- deseretCapitalLetterLongI UniversalString ::= {0, 1, 4, 0}

-- deseretCapitalLetterLongE UniversalString ::= {0, 1, 4, 1}

-- deseretCapitalLetterLongA UniversalString ::= {0, 1, 4, 2}

-- deseretCapitalLetterLongAh UniversalString ::= {0, 1, 4, 3}

-- deseretCapitalLetterLongO UniversalString ::= {0, 1, 4, 4}

-- deseretCapitalLetterLongOo UniversalString ::= {0, 1, 4, 5}

-- deseretCapitalLetterShortI UniversalString ::= {0, 1, 4, 6}

-- deseretCapitalLetterShortE UniversalString ::= {0, 1, 4, 7}

-- deseretCapitalLetterShortA UniversalString ::= {0, 1, 4, 8}

-- deseretCapitalLetterShortAh UniversalString ::= {0, 1, 4, 9}

-- deseretCapitalLetterShortO UniversalString ::= {0, 1, 4, 10}

-- deseretCapitalLetterShortOo UniversalString ::= {0, 1, 4, 11}

-- deseretCapitalLetterAy UniversalString ::= {0, 1, 4, 12}

-- deseretCapitalLetterOw UniversalString ::= {0, 1, 4, 13}

-- deseretCapitalLetterWu UniversalString ::= {0, 1, 4, 14}

-- deseretCapitalLetterYee UniversalString ::= {0, 1, 4, 15}

-- deseretCapitalLetterH UniversalString ::= {0, 1, 4, 16}

-- deseretCapitalLetterPee UniversalString ::= {0, 1, 4, 17}

-- deseretCapitalLetterBee UniversalString ::= {0, 1, 4, 18}

-- deseretCapitalLetterTee UniversalString ::= {0, 1, 4, 19}

-- deseretCapitalLetterDee UniversalString ::= {0, 1, 4, 20}

-- deseretCapitalLetterChee UniversalString ::= {0, 1, 4, 21}

-- deseretCapitalLetterJee UniversalString ::= {0, 1, 4, 22}

-- deseretCapitalLetterKay UniversalString ::= {0, 1, 4, 23}

-- deseretCapitalLetterGay UniversalString ::= {0, 1, 4, 24}

-- deseretCapitalLetterEf UniversalString ::= {0, 1, 4, 25}

-- deseretCapitalLetterVee UniversalString ::= {0, 1, 4, 26}

-- deseretCapitalLetterEth UniversalString ::= {0, 1, 4, 27}

-- deseretCapitalLetterThee UniversalString ::= {0, 1, 4, 28}

-- deseretCapitalLetterEs UniversalString ::= {0, 1, 4, 29}

-- deseretCapitalLetterZee UniversalString ::= {0, 1, 4, 30}

-- deseretCapitalLetterEsh UniversalString ::= {0, 1, 4, 31}

-- deseretCapitalLetterZhee UniversalString ::= {0, 1, 4, 32}

-- deseretCapitalLetterEr UniversalString ::= {0, 1, 4, 33}

-- deseretCapitalLetterEl UniversalString ::= {0, 1, 4, 34}

-- deseretCapitalLetterEm UniversalString ::= {0, 1, 4, 35}

-- deseretCapitalLetterEn UniversalString ::= {0, 1, 4, 36}

-- deseretCapitalLetterEng UniversalString ::= {0, 1, 4, 37}

-- deseretSmallLetterLongI UniversalString ::= {0, 1, 4, 40}

-- deseretSmallLetterLongE UniversalString ::= {0, 1, 4, 41}

-- deseretSmallLetterLongA UniversalString ::= {0, 1, 4, 42}

-- deseretSmallLetterLongAh UniversalString ::= {0, 1, 4, 43}

-- deseretSmallLetterLongO UniversalString ::= {0, 1, 4, 44}

-- deseretSmallLetterLongOo UniversalString ::= {0, 1, 4, 45}

-- deseretSmallLetterShortI UniversalString ::= {0, 1, 4, 46}

-- deseretSmallLetterShortE UniversalString ::= {0, 1, 4, 47}

-- deseretSmallLetterShortA UniversalString ::= {0, 1, 4, 48}

-- deseretSmallLetterShortAh UniversalString ::= {0, 1, 4, 49}

-- deseretSmallLetterShortO UniversalString ::= {0, 1, 4, 50}

-- deseretSmallLetterShortOo UniversalString ::= {0, 1, 4, 51}

-- deseretSmallLetterAy UniversalString ::= {0, 1, 4, 52}

-- deseretSmallLetterOw UniversalString ::= {0, 1, 4, 53}

-- deseretSmallLetterWu UniversalString ::= {0, 1, 4, 54}

-- deseretSmallLetterYee UniversalString ::= {0, 1, 4, 55}

-- deseretSmallLetterH UniversalString ::= {0, 1, 4, 56}

-- deseretSmallLetterPee UniversalString ::= {0, 1, 4, 57}

-- deseretSmallLetterBee UniversalString ::= {0, 1, 4, 58}

-- deseretSmallLetterTee UniversalString ::= {0, 1, 4, 59}

-- deseretSmallLetterDee UniversalString ::= {0, 1, 4, 60}

-- deseretSmallLetterChee UniversalString ::= {0, 1, 4, 61}

-- deseretSmallLetterJee UniversalString ::= {0, 1, 4, 62}

-- deseretSmallLetterKay UniversalString ::= {0, 1, 4, 63}

-- deseretSmallLetterGay UniversalString ::= {0, 1, 4, 64}

-- deseretSmallLetterEf UniversalString ::= {0, 1, 4, 65}

-- deseretSmallLetterVee UniversalString ::= {0, 1, 4, 66}

-- deseretSmallLetterEth UniversalString ::= {0, 1, 4, 67}

-- deseretSmallLetterThee UniversalString ::= {0, 1, 4, 68}

-- deseretSmallLetterEs UniversalString ::= {0, 1, 4, 69}

-- deseretSmallLetterZee UniversalString ::= {0, 1, 4, 70}

-- deseretSmallLetterEsh UniversalString ::= {0, 1, 4, 71}

-- deseretSmallLetterZhee UniversalString ::= {0, 1, 4, 72}

-- deseretSmallLetterEr UniversalString ::= {0, 1, 4, 73}

-- deseretSmallLetterEl UniversalString ::= {0, 1, 4, 74}

-- deseretSmallLetterEm UniversalString ::= {0, 1, 4, 75}

-- deseretSmallLetterEn UniversalString ::= {0, 1, 4, 76}

-- deseretSmallLetterEng UniversalString ::= {0, 1, 4, 77}

-- byzantineMusicalSymbolPsili UniversalString ::= {0, 1, 208, 0}

-- byzantineMusicalSymbolDaseia UniversalString ::= {0, 1, 208, 1}

-- byzantineMusicalSymbolPerispomeni UniversalString ::= {0, 1, 208, 2}

-- byzantineMusicalSymbolOxeiaEkfonitikon UniversalString ::= {0, 1, 208, 3}

-- byzantineMusicalSymbolOxeiaDipli UniversalString ::= {0, 1, 208, 4}

-- byzantineMusicalSymbolVareiaEkfonitikon UniversalString ::= {0, 1, 208, 5}

-- byzantineMusicalSymbolVareiaDipli UniversalString ::= {0, 1, 208, 6}

-- byzantineMusicalSymbolKathisti UniversalString ::= {0, 1, 208, 7}

-- byzantineMusicalSymbolSyrmatiki UniversalString ::= {0, 1, 208, 8}

-- byzantineMusicalSymbolParaklitiki UniversalString ::= {0, 1, 208, 9}

-- byzantineMusicalSymbolYpokrisis UniversalString ::= {0, 1, 208, 10}

-- byzantineMusicalSymbolYpokrisisDipli UniversalString ::= {0, 1, 208, 11}

-- byzantineMusicalSymbolKremasti UniversalString ::= {0, 1, 208, 12}

-- byzantineMusicalSymbolApesoEkfonitikon UniversalString ::= {0, 1, 208, 13}

-- byzantineMusicalSymbolExoEkfonitikon UniversalString ::= {0, 1, 208, 14}

-- byzantineMusicalSymbolTeleia UniversalString ::= {0, 1, 208, 15}

-- byzantineMusicalSymbolKentimata UniversalString ::= {0, 1, 208, 16}

-- byzantineMusicalSymbolApostrofos UniversalString ::= {0, 1, 208, 17}

-- byzantineMusicalSymbolApostrofosDipli UniversalString ::= {0, 1, 208, 18}

-- byzantineMusicalSymbolSynevma UniversalString ::= {0, 1, 208, 19}

-- byzantineMusicalSymbolThita UniversalString ::= {0, 1, 208, 20}

-- byzantineMusicalSymbolOligonArchaion UniversalString ::= {0, 1, 208, 21}

-- byzantineMusicalSymbolGorgonArchaion UniversalString ::= {0, 1, 208, 22}

-- byzantineMusicalSymbolPsilon UniversalString ::= {0, 1, 208, 23}

-- byzantineMusicalSymbolChamilon UniversalString ::= {0, 1, 208, 24}

-- byzantineMusicalSymbolVathy UniversalString ::= {0, 1, 208, 25}

-- byzantineMusicalSymbolIsonArchaion UniversalString ::= {0, 1, 208, 26}

-- byzantineMusicalSymbolKentimaArchaion UniversalString ::= {0, 1, 208, 27}

-- byzantineMusicalSymbolKentimataArchaion UniversalString ::= {0, 1, 208, 28}

-- byzantineMusicalSymbolSaximata UniversalString ::= {0, 1, 208, 29}

-- byzantineMusicalSymbolParichon UniversalString ::= {0, 1, 208, 30}

-- byzantineMusicalSymbolStavrosApodexia UniversalString ::= {0, 1, 208, 31}

-- byzantineMusicalSymbolOxeiaiArchaion UniversalString ::= {0, 1, 208, 32}

-- byzantineMusicalSymbolVareiaiArchaion UniversalString ::= {0, 1, 208, 33}

-- byzantineMusicalSymbolApodermaArchaion UniversalString ::= {0, 1, 208, 34}

-- byzantineMusicalSymbolApothema UniversalString ::= {0, 1, 208, 35}

-- byzantineMusicalSymbolKlasma UniversalString ::= {0, 1, 208, 36}

-- byzantineMusicalSymbolRevma UniversalString ::= {0, 1, 208, 37}

-- byzantineMusicalSymbolPiasmaArchaion UniversalString ::= {0, 1, 208, 38}

-- byzantineMusicalSymbolTinagma UniversalString ::= {0, 1, 208, 39}

-- byzantineMusicalSymbolAnatrichisma UniversalString ::= {0, 1, 208, 40}

-- byzantineMusicalSymbolSeisma UniversalString ::= {0, 1, 208, 41}

-- byzantineMusicalSymbolSynagmaArchaion UniversalString ::= {0, 1, 208, 42}

-- byzantineMusicalSymbolSynagmaMetaStavrou UniversalString ::= {0, 1, 208, 43}

-- byzantineMusicalSymbolOyranismaArchaion UniversalString ::= {0, 1, 208, 44}

-- byzantineMusicalSymbolThema UniversalString ::= {0, 1, 208, 45}

-- byzantineMusicalSymbolLemoi UniversalString ::= {0, 1, 208, 46}

-- byzantineMusicalSymbolDyo UniversalString ::= {0, 1, 208, 47}

-- byzantineMusicalSymbolTria UniversalString ::= {0, 1, 208, 48}

-- byzantineMusicalSymbolTessera UniversalString ::= {0, 1, 208, 49}

-- byzantineMusicalSymbolKratimata UniversalString ::= {0, 1, 208, 50}

-- byzantineMusicalSymbolApesoExoNeo UniversalString ::= {0, 1, 208, 51}

-- byzantineMusicalSymbolFthoraArchaion UniversalString ::= {0, 1, 208, 52}

-- byzantineMusicalSymbolImifthora UniversalString ::= {0, 1, 208, 53}

-- byzantineMusicalSymbolTromikonArchaion UniversalString ::= {0, 1, 208, 54}

-- byzantineMusicalSymbolKatavaTromikon UniversalString ::= {0, 1, 208, 55}

-- byzantineMusicalSymbolPelaston UniversalString ::= {0, 1, 208, 56}

-- byzantineMusicalSymbolPsifiston UniversalString ::= {0, 1, 208, 57}

-- byzantineMusicalSymbolKontevma UniversalString ::= {0, 1, 208, 58}

-- byzantineMusicalSymbolChorevmaArchaion UniversalString ::= {0, 1, 208, 59}

-- byzantineMusicalSymbolRapisma UniversalString ::= {0, 1, 208, 60}

-- byzantineMusicalSymbolParakalesmaArchaion UniversalString ::= {0, 1, 208, 61}

-- byzantineMusicalSymbolParaklitikiArchaion UniversalString ::= {0, 1, 208, 62}

-- byzantineMusicalSymbolIchadin UniversalString ::= {0, 1, 208, 63}

-- byzantineMusicalSymbolNana UniversalString ::= {0, 1, 208, 64}

-- byzantineMusicalSymbolPetasma UniversalString ::= {0, 1, 208, 65}

-- byzantineMusicalSymbolKontevmaAllo UniversalString ::= {0, 1, 208, 66}

-- byzantineMusicalSymbolTromikonAllo UniversalString ::= {0, 1, 208, 67}

-- byzantineMusicalSymbolStraggismata UniversalString ::= {0, 1, 208, 68}

-- byzantineMusicalSymbolGronthismata UniversalString ::= {0, 1, 208, 69}

-- byzantineMusicalSymbolIsonNeo UniversalString ::= {0, 1, 208, 70}

-- byzantineMusicalSymbolOligonNeo UniversalString ::= {0, 1, 208, 71}

-- byzantineMusicalSymbolOxeiaNeo UniversalString ::= {0, 1, 208, 72}

-- byzantineMusicalSymbolPetasti UniversalString ::= {0, 1, 208, 73}

-- byzantineMusicalSymbolKoufisma UniversalString ::= {0, 1, 208, 74}

-- byzantineMusicalSymbolPetastokoufisma UniversalString ::= {0, 1, 208, 75}

-- byzantineMusicalSymbolKratimokoufisma UniversalString ::= {0, 1, 208, 76}

-- byzantineMusicalSymbolPelastonNeo UniversalString ::= {0, 1, 208, 77}

-- byzantineMusicalSymbolKentimataNeoAno UniversalString ::= {0, 1, 208, 78}

-- byzantineMusicalSymbolKentimaNeoAno UniversalString ::= {0, 1, 208, 79}

-- byzantineMusicalSymbolYpsili UniversalString ::= {0, 1, 208, 80}

-- byzantineMusicalSymbolApostrofosNeo UniversalString ::= {0, 1, 208, 81}

-- byzantineMusicalSymbolApostrofoiSyndesmosNeo UniversalString ::=
--   {0, 1, 208, 82}

-- byzantineMusicalSymbolYporroi UniversalString ::= {0, 1, 208, 83}

-- byzantineMusicalSymbolKratimoyporroon UniversalString ::= {0, 1, 208, 84}

-- byzantineMusicalSymbolElafron UniversalString ::= {0, 1, 208, 85}

-- byzantineMusicalSymbolChamili UniversalString ::= {0, 1, 208, 86}

-- byzantineMusicalSymbolMikronIson UniversalString ::= {0, 1, 208, 87}

-- byzantineMusicalSymbolVareiaNeo UniversalString ::= {0, 1, 208, 88}

-- byzantineMusicalSymbolPiasmaNeo UniversalString ::= {0, 1, 208, 89}

-- byzantineMusicalSymbolPsifistonNeo UniversalString ::= {0, 1, 208, 90}

-- byzantineMusicalSymbolOmalon UniversalString ::= {0, 1, 208, 91}

-- byzantineMusicalSymbolAntikenoma UniversalString ::= {0, 1, 208, 92}

-- byzantineMusicalSymbolLygisma UniversalString ::= {0, 1, 208, 93}

-- byzantineMusicalSymbolParaklitikiNeo UniversalString ::= {0, 1, 208, 94}

-- byzantineMusicalSymbolParakalesmaNeo UniversalString ::= {0, 1, 208, 95}

-- byzantineMusicalSymbolEteronParakalesma UniversalString ::= {0, 1, 208, 96}

-- byzantineMusicalSymbolKylisma UniversalString ::= {0, 1, 208, 97}

-- byzantineMusicalSymbolAntikenokylisma UniversalString ::= {0, 1, 208, 98}

-- byzantineMusicalSymbolTromikonNeo UniversalString ::= {0, 1, 208, 99}

-- byzantineMusicalSymbolEkstrepton UniversalString ::= {0, 1, 208, 100}

-- byzantineMusicalSymbolSynagmaNeo UniversalString ::= {0, 1, 208, 101}

-- byzantineMusicalSymbolSyrma UniversalString ::= {0, 1, 208, 102}

-- byzantineMusicalSymbolChorevmaNeo UniversalString ::= {0, 1, 208, 103}

-- byzantineMusicalSymbolEpegerma UniversalString ::= {0, 1, 208, 104}

-- byzantineMusicalSymbolSeismaNeo UniversalString ::= {0, 1, 208, 105}

-- byzantineMusicalSymbolXironKlasma UniversalString ::= {0, 1, 208, 106}

-- byzantineMusicalSymbolTromikopsifiston UniversalString ::= {0, 1, 208, 107}

-- byzantineMusicalSymbolPsifistolygisma UniversalString ::= {0, 1, 208, 108}

-- byzantineMusicalSymbolTromikolygisma UniversalString ::= {0, 1, 208, 109}

-- byzantineMusicalSymbolTromikoparakalesma UniversalString ::= {0, 1, 208, 110}

-- byzantineMusicalSymbolPsifistoparakalesma UniversalString ::= {0, 1, 208, 111}

-- byzantineMusicalSymbolTromikosynagma UniversalString ::= {0, 1, 208, 112}

-- byzantineMusicalSymbolPsifistosynagma UniversalString ::= {0, 1, 208, 113}

-- byzantineMusicalSymbolGorgosyntheton UniversalString ::= {0, 1, 208, 114}

-- byzantineMusicalSymbolArgosyntheton UniversalString ::= {0, 1, 208, 115}

-- byzantineMusicalSymbolEteronArgosyntheton UniversalString ::= {0, 1, 208, 116}

-- byzantineMusicalSymbolOyranismaNeo UniversalString ::= {0, 1, 208, 117}

-- byzantineMusicalSymbolThematismosEso UniversalString ::= {0, 1, 208, 118}

-- byzantineMusicalSymbolThematismosExo UniversalString ::= {0, 1, 208, 119}

-- byzantineMusicalSymbolThemaAploun UniversalString ::= {0, 1, 208, 120}

-- byzantineMusicalSymbolThesKaiApothes UniversalString ::= {0, 1, 208, 121}

-- byzantineMusicalSymbolKatavasma UniversalString ::= {0, 1, 208, 122}

-- byzantineMusicalSymbolEndofonon UniversalString ::= {0, 1, 208, 123}

-- byzantineMusicalSymbolYfenKato UniversalString ::= {0, 1, 208, 124}

-- byzantineMusicalSymbolYfenAno UniversalString ::= {0, 1, 208, 125}

-- byzantineMusicalSymbolStavros UniversalString ::= {0, 1, 208, 126}

-- byzantineMusicalSymbolKlasmaAno UniversalString ::= {0, 1, 208, 127}

-- byzantineMusicalSymbolDipliArchaion UniversalString ::= {0, 1, 208, 128}

-- byzantineMusicalSymbolKratimaArchaion UniversalString ::= {0, 1, 208, 129}

-- byzantineMusicalSymbolKratimaAllo UniversalString ::= {0, 1, 208, 130}

-- byzantineMusicalSymbolKratimaNeo UniversalString ::= {0, 1, 208, 131}

-- byzantineMusicalSymbolApodermaNeo UniversalString ::= {0, 1, 208, 132}

-- byzantineMusicalSymbolApli UniversalString ::= {0, 1, 208, 133}

-- byzantineMusicalSymbolDipli UniversalString ::= {0, 1, 208, 134}

-- byzantineMusicalSymbolTripli UniversalString ::= {0, 1, 208, 135}

-- byzantineMusicalSymbolTetrapli UniversalString ::= {0, 1, 208, 136}

-- byzantineMusicalSymbolKoronis UniversalString ::= {0, 1, 208, 137}

-- byzantineMusicalSymbolLeimmaEnosChronou UniversalString ::= {0, 1, 208, 138}

-- byzantineMusicalSymbolLeimmaDyoChronon UniversalString ::= {0, 1, 208, 139}

-- byzantineMusicalSymbolLeimmaTrionChronon UniversalString ::= {0, 1, 208, 140}

-- byzantineMusicalSymbolLeimmaTessaronChronon UniversalString ::=
--   {0, 1, 208, 141}

-- byzantineMusicalSymbolLeimmaImiseosChronou UniversalString ::= {0, 1, 208, 142}

-- byzantineMusicalSymbolGorgonNeoAno UniversalString ::= {0, 1, 208, 143}

-- byzantineMusicalSymbolGorgonParestigmenonAristera UniversalString ::=
--   {0, 1, 208, 144}

-- byzantineMusicalSymbolGorgonParestigmenonDexia UniversalString ::=
--   {0, 1, 208, 145}

-- byzantineMusicalSymbolDigorgon UniversalString ::= {0, 1, 208, 146}

-- byzantineMusicalSymbolDigorgonParestigmenonAristeraKato UniversalString ::=
--   {0, 1, 208, 147}

-- byzantineMusicalSymbolDigorgonParestigmenonAristeraAno UniversalString ::=
--   {0, 1, 208, 148}

-- byzantineMusicalSymbolDigorgonParestigmenonDexia UniversalString ::=
--   {0, 1, 208, 149}

-- byzantineMusicalSymbolTrigorgon UniversalString ::= {0, 1, 208, 150}

-- byzantineMusicalSymbolArgon UniversalString ::= {0, 1, 208, 151}

-- byzantineMusicalSymbolImidiargon UniversalString ::= {0, 1, 208, 152}

-- byzantineMusicalSymbolDiargon UniversalString ::= {0, 1, 208, 153}

-- byzantineMusicalSymbolAgogiPoliArgi UniversalString ::= {0, 1, 208, 154}

-- byzantineMusicalSymbolAgogiArgoteri UniversalString ::= {0, 1, 208, 155}

-- byzantineMusicalSymbolAgogiArgi UniversalString ::= {0, 1, 208, 156}

-- byzantineMusicalSymbolAgogiMetria UniversalString ::= {0, 1, 208, 157}

-- byzantineMusicalSymbolAgogiMesi UniversalString ::= {0, 1, 208, 158}

-- byzantineMusicalSymbolAgogiGorgi UniversalString ::= {0, 1, 208, 159}

-- byzantineMusicalSymbolAgogiGorgoteri UniversalString ::= {0, 1, 208, 160}

-- byzantineMusicalSymbolAgogiPoliGorgi UniversalString ::= {0, 1, 208, 161}

-- byzantineMusicalSymbolMartyriaProtosIchos UniversalString ::= {0, 1, 208, 162}

-- byzantineMusicalSymbolMartyriaAlliProtosIchos UniversalString ::=
--   {0, 1, 208, 163}

-- byzantineMusicalSymbolMartyriaDeyterosIchos UniversalString ::=
--   {0, 1, 208, 164}

-- byzantineMusicalSymbolMartyriaAlliDeyterosIchos UniversalString ::=
--   {0, 1, 208, 165}

-- byzantineMusicalSymbolMartyriaTritosIchos UniversalString ::= {0, 1, 208, 166}

-- byzantineMusicalSymbolMartyriaTrifonias UniversalString ::= {0, 1, 208, 167}

-- byzantineMusicalSymbolMartyriaTetartosIchos UniversalString ::=
--   {0, 1, 208, 168}

-- byzantineMusicalSymbolMartyriaTetartosLegetosIchos UniversalString ::=
--   {0, 1, 208, 169}

-- byzantineMusicalSymbolMartyriaLegetosIchos UniversalString ::= {0, 1, 208, 170}

-- byzantineMusicalSymbolMartyriaPlagiosIchos UniversalString ::= {0, 1, 208, 171}

-- byzantineMusicalSymbolIsakiaTelousIchimatos UniversalString ::=
--   {0, 1, 208, 172}

-- byzantineMusicalSymbolApostrofoiTelousIchimatos UniversalString ::=
--   {0, 1, 208, 173}

-- byzantineMusicalSymbolFanerosisTetrafonias UniversalString ::= {0, 1, 208, 174}

-- byzantineMusicalSymbolFanerosisMonofonias UniversalString ::= {0, 1, 208, 175}

-- byzantineMusicalSymbolFanerosisDifonias UniversalString ::= {0, 1, 208, 176}

-- byzantineMusicalSymbolMartyriaVarysIchos UniversalString ::= {0, 1, 208, 177}

-- byzantineMusicalSymbolMartyriaProtovarysIchos UniversalString ::=
--   {0, 1, 208, 178}

-- byzantineMusicalSymbolMartyriaPlagiosTetartosIchos UniversalString ::=
--   {0, 1, 208, 179}

-- byzantineMusicalSymbolGorthmikonNAploun UniversalString ::= {0, 1, 208, 180}

-- byzantineMusicalSymbolGorthmikonNDiploun UniversalString ::= {0, 1, 208, 181}

-- byzantineMusicalSymbolEnarxisKaiFthoraVou UniversalString ::= {0, 1, 208, 182}

-- byzantineMusicalSymbolImifonon UniversalString ::= {0, 1, 208, 183}

-- byzantineMusicalSymbolImifthoron UniversalString ::= {0, 1, 208, 184}

-- byzantineMusicalSymbolFthoraArchaionDeyterouIchou UniversalString ::=
--   {0, 1, 208, 185}

-- byzantineMusicalSymbolFthoraDiatonikiPa UniversalString ::= {0, 1, 208, 186}

-- byzantineMusicalSymbolFthoraDiatonikiNana UniversalString ::= {0, 1, 208, 187}

-- byzantineMusicalSymbolFthoraNaosIchos UniversalString ::= {0, 1, 208, 188}

-- byzantineMusicalSymbolFthoraDiatonikiDi UniversalString ::= {0, 1, 208, 189}

-- byzantineMusicalSymbolFthoraSklironDiatononDi UniversalString ::=
--   {0, 1, 208, 190}

-- byzantineMusicalSymbolFthoraDiatonikiKe UniversalString ::= {0, 1, 208, 191}

-- byzantineMusicalSymbolFthoraDiatonikiZo UniversalString ::= {0, 1, 208, 192}

-- byzantineMusicalSymbolFthoraDiatonikiNiKato UniversalString ::=
--   {0, 1, 208, 193}

-- byzantineMusicalSymbolFthoraDiatonikiNiAno UniversalString ::= {0, 1, 208, 194}

-- byzantineMusicalSymbolFthoraMalakonChromaDifonias UniversalString ::=
--   {0, 1, 208, 195}

-- byzantineMusicalSymbolFthoraMalakonChromaMonofonias UniversalString ::=
--   {0, 1, 208, 196}

-- byzantineMusicalSymbolFhtoraSklironChromaVasis UniversalString ::=
--   {0, 1, 208, 197}

-- byzantineMusicalSymbolFthoraSklironChromaSynafi UniversalString ::=
--   {0, 1, 208, 198}

-- byzantineMusicalSymbolFthoraNenano UniversalString ::= {0, 1, 208, 199}

-- byzantineMusicalSymbolChroaZygos UniversalString ::= {0, 1, 208, 200}

-- byzantineMusicalSymbolChroaKliton UniversalString ::= {0, 1, 208, 201}

-- byzantineMusicalSymbolChroaSpathi UniversalString ::= {0, 1, 208, 202}

-- byzantineMusicalSymbolFthoraIYfesisTetartimorion UniversalString ::=
--   {0, 1, 208, 203}

-- byzantineMusicalSymbolFthoraEnarmoniosAntifonia UniversalString ::=
--   {0, 1, 208, 204}

-- byzantineMusicalSymbolYfesisTritimorion UniversalString ::= {0, 1, 208, 205}

-- byzantineMusicalSymbolDiesisTritimorion UniversalString ::= {0, 1, 208, 206}

-- byzantineMusicalSymbolDiesisTetartimorion UniversalString ::= {0, 1, 208, 207}

-- byzantineMusicalSymbolDiesisApliDyoDodekata UniversalString ::=
--   {0, 1, 208, 208}

-- byzantineMusicalSymbolDiesisMonogrammosTesseraDodekata UniversalString ::=
--   {0, 1, 208, 209}

-- byzantineMusicalSymbolDiesisDigrammosExDodekata UniversalString ::=
--   {0, 1, 208, 210}

-- byzantineMusicalSymbolDiesisTrigrammosOktoDodekata UniversalString ::=
--   {0, 1, 208, 211}

-- byzantineMusicalSymbolYfesisApliDyoDodekata UniversalString ::=
--   {0, 1, 208, 212}

-- byzantineMusicalSymbolYfesisMonogrammosTesseraDodekata UniversalString ::=
--   {0, 1, 208, 213}

-- byzantineMusicalSymbolYfesisDigrammosExDodekata UniversalString ::=
--   {0, 1, 208, 214}

-- byzantineMusicalSymbolYfesisTrigrammosOktoDodekata UniversalString ::=
--   {0, 1, 208, 215}

-- byzantineMusicalSymbolGenikiDiesis UniversalString ::= {0, 1, 208, 216}

-- byzantineMusicalSymbolGenikiYfesis UniversalString ::= {0, 1, 208, 217}

-- byzantineMusicalSymbolDiastoliApliMikri UniversalString ::= {0, 1, 208, 218}

-- byzantineMusicalSymbolDiastoliApliMegali UniversalString ::= {0, 1, 208, 219}

-- byzantineMusicalSymbolDiastoliDipli UniversalString ::= {0, 1, 208, 220}

-- byzantineMusicalSymbolDiastoliTheseos UniversalString ::= {0, 1, 208, 221}

-- byzantineMusicalSymbolSimansisTheseos UniversalString ::= {0, 1, 208, 222}

-- byzantineMusicalSymbolSimansisTheseosDisimou UniversalString ::=
--   {0, 1, 208, 223}

-- byzantineMusicalSymbolSimansisTheseosTrisimou UniversalString ::=
--   {0, 1, 208, 224}

-- byzantineMusicalSymbolSimansisTheseosTetrasimou UniversalString ::=
--   {0, 1, 208, 225}

-- byzantineMusicalSymbolSimansisArseos UniversalString ::= {0, 1, 208, 226}

-- byzantineMusicalSymbolSimansisArseosDisimou UniversalString ::=
--   {0, 1, 208, 227}

-- byzantineMusicalSymbolSimansisArseosTrisimou UniversalString ::=
--   {0, 1, 208, 228}

-- byzantineMusicalSymbolSimansisArseosTetrasimou UniversalString ::=
--   {0, 1, 208, 229}

-- byzantineMusicalSymbolDigrammaGg UniversalString ::= {0, 1, 208, 230}

-- byzantineMusicalSymbolDiftoggosOu UniversalString ::= {0, 1, 208, 231}

-- byzantineMusicalSymbolStigma UniversalString ::= {0, 1, 208, 232}

-- byzantineMusicalSymbolArktikoPa UniversalString ::= {0, 1, 208, 233}

-- byzantineMusicalSymbolArktikoVou UniversalString ::= {0, 1, 208, 234}

-- byzantineMusicalSymbolArktikoGa UniversalString ::= {0, 1, 208, 235}

-- byzantineMusicalSymbolArktikoDi UniversalString ::= {0, 1, 208, 236}

-- byzantineMusicalSymbolArktikoKe UniversalString ::= {0, 1, 208, 237}

-- byzantineMusicalSymbolArktikoZo UniversalString ::= {0, 1, 208, 238}

-- byzantineMusicalSymbolArktikoNi UniversalString ::= {0, 1, 208, 239}

-- byzantineMusicalSymbolKentimataNeoMeso UniversalString ::= {0, 1, 208, 240}

-- byzantineMusicalSymbolKentimaNeoMeso UniversalString ::= {0, 1, 208, 241}

-- byzantineMusicalSymbolKentimataNeoKato UniversalString ::= {0, 1, 208, 242}

-- byzantineMusicalSymbolKentimaNeoKato UniversalString ::= {0, 1, 208, 243}

-- byzantineMusicalSymbolKlasmaKato UniversalString ::= {0, 1, 208, 244}

-- byzantineMusicalSymbolGorgonNeoKato UniversalString ::= {0, 1, 208, 245}

-- musicalSymbolSingleBarline UniversalString ::= {0, 1, 209, 0}

-- musicalSymbolDoubleBarline UniversalString ::= {0, 1, 209, 1}

-- musicalSymbolFinalBarline UniversalString ::= {0, 1, 209, 2}

-- musicalSymbolReverseFinalBarline UniversalString ::= {0, 1, 209, 3}

-- musicalSymbolDashedBarline UniversalString ::= {0, 1, 209, 4}

-- musicalSymbolShortBarline UniversalString ::= {0, 1, 209, 5}

-- musicalSymbolLeftRepeatSign UniversalString ::= {0, 1, 209, 6}

-- musicalSymbolRightRepeatSign UniversalString ::= {0, 1, 209, 7}

-- musicalSymbolRepeatDots UniversalString ::= {0, 1, 209, 8}

-- musicalSymbolDalSegno UniversalString ::= {0, 1, 209, 9}

-- musicalSymbolDaCapo UniversalString ::= {0, 1, 209, 10}

-- musicalSymbolSegno UniversalString ::= {0, 1, 209, 11}

-- musicalSymbolCoda UniversalString ::= {0, 1, 209, 12}

-- musicalSymbolRepeatedFigure-1 UniversalString ::= {0, 1, 209, 13}

-- musicalSymbolRepeatedFigure-2 UniversalString ::= {0, 1, 209, 14}

-- musicalSymbolRepeatedFigure-3 UniversalString ::= {0, 1, 209, 15}

-- musicalSymbolFermata UniversalString ::= {0, 1, 209, 16}

-- musicalSymbolFermataBelow UniversalString ::= {0, 1, 209, 17}

-- musicalSymbolBreathMark UniversalString ::= {0, 1, 209, 18}

-- musicalSymbolCaesura UniversalString ::= {0, 1, 209, 19}

-- musicalSymbolBrace UniversalString ::= {0, 1, 209, 20}

-- musicalSymbolBracket UniversalString ::= {0, 1, 209, 21}

-- musicalSymbolOne-lineStaff UniversalString ::= {0, 1, 209, 22}

-- musicalSymbolTwo-lineStaff UniversalString ::= {0, 1, 209, 23}

-- musicalSymbolThree-lineStaff UniversalString ::= {0, 1, 209, 24}

-- musicalSymbolFour-lineStaff UniversalString ::= {0, 1, 209, 25}

-- musicalSymbolFive-lineStaff UniversalString ::= {0, 1, 209, 26}

-- musicalSymbolSix-lineStaff UniversalString ::= {0, 1, 209, 27}

-- musicalSymbolSix-stringFretboard UniversalString ::= {0, 1, 209, 28}

-- musicalSymbolFour-stringFretboard UniversalString ::= {0, 1, 209, 29}

-- musicalSymbolGClef UniversalString ::= {0, 1, 209, 30}

-- musicalSymbolGClefOttavaAlta UniversalString ::= {0, 1, 209, 31}

-- musicalSymbolGClefOttavaBassa UniversalString ::= {0, 1, 209, 32}

-- musicalSymbolCClef UniversalString ::= {0, 1, 209, 33}

-- musicalSymbolFClef UniversalString ::= {0, 1, 209, 34}

-- musicalSymbolFClefOttavaAlta UniversalString ::= {0, 1, 209, 35}

-- musicalSymbolFClefOttavaBassa UniversalString ::= {0, 1, 209, 36}

-- musicalSymbolDrumClef-1 UniversalString ::= {0, 1, 209, 37}

-- musicalSymbolDrumClef-2 UniversalString ::= {0, 1, 209, 38}

-- musicalSymbolDoubleSharp UniversalString ::= {0, 1, 209, 42}

-- musicalSymbolDoubleFlat UniversalString ::= {0, 1, 209, 43}

-- musicalSymbolFlatUp UniversalString ::= {0, 1, 209, 44}

-- musicalSymbolFlatDown UniversalString ::= {0, 1, 209, 45}

-- musicalSymbolNaturalUp UniversalString ::= {0, 1, 209, 46}

-- musicalSymbolNaturalDown UniversalString ::= {0, 1, 209, 47}

-- musicalSymbolSharpUp UniversalString ::= {0, 1, 209, 48}

-- musicalSymbolSharpDown UniversalString ::= {0, 1, 209, 49}

-- musicalSymbolQuarterToneSharp UniversalString ::= {0, 1, 209, 50}

-- musicalSymbolQuarterToneFlat UniversalString ::= {0, 1, 209, 51}

-- musicalSymbolCommonTime UniversalString ::= {0, 1, 209, 52}

-- musicalSymbolCutTime UniversalString ::= {0, 1, 209, 53}

-- musicalSymbolOttavaAlta UniversalString ::= {0, 1, 209, 54}

-- musicalSymbolOttavaBassa UniversalString ::= {0, 1, 209, 55}

-- musicalSymbolQuindicesimaAlta UniversalString ::= {0, 1, 209, 56}

-- musicalSymbolQuindicesimaBassa UniversalString ::= {0, 1, 209, 57}

-- musicalSymbolMultiRest UniversalString ::= {0, 1, 209, 58}

-- musicalSymbolWholeRest UniversalString ::= {0, 1, 209, 59}

-- musicalSymbolHalfRest UniversalString ::= {0, 1, 209, 60}

-- musicalSymbolQuarterRest UniversalString ::= {0, 1, 209, 61}

-- musicalSymbolEighthRest UniversalString ::= {0, 1, 209, 62}

-- musicalSymbolSixteenthRest UniversalString ::= {0, 1, 209, 63}

-- musicalSymbolThirty-secondRest UniversalString ::= {0, 1, 209, 64}

-- musicalSymbolSixty-fourthRest UniversalString ::= {0, 1, 209, 65}

-- musicalSymbolOneHundredTwenty-eighthRest UniversalString ::= {0, 1, 209, 66}

-- musicalSymbolXNotehead UniversalString ::= {0, 1, 209, 67}

-- musicalSymbolPlusNotehead UniversalString ::= {0, 1, 209, 68}

-- musicalSymbolCircleXNotehead UniversalString ::= {0, 1, 209, 69}

-- musicalSymbolSquareNoteheadWhite UniversalString ::= {0, 1, 209, 70}

-- musicalSymbolSquareNoteheadBlack UniversalString ::= {0, 1, 209, 71}

-- musicalSymbolTriangleNoteheadUpWhite UniversalString ::= {0, 1, 209, 72}

-- musicalSymbolTriangleNoteheadUpBlack UniversalString ::= {0, 1, 209, 73}

-- musicalSymbolTriangleNoteheadLeftWhite UniversalString ::= {0, 1, 209, 74}

-- musicalSymbolTriangleNoteheadLeftBlack UniversalString ::= {0, 1, 209, 75}

-- musicalSymbolTriangleNoteheadRightWhite UniversalString ::= {0, 1, 209, 76}

-- musicalSymbolTriangleNoteheadRightBlack UniversalString ::= {0, 1, 209, 77}

-- musicalSymbolTriangleNoteheadDownWhite UniversalString ::= {0, 1, 209, 78}

-- musicalSymbolTriangleNoteheadDownBlack UniversalString ::= {0, 1, 209, 79}

-- musicalSymbolTriangleNoteheadUpRightWhite UniversalString ::= {0, 1, 209, 80}

-- musicalSymbolTriangleNoteheadUpRightBlack UniversalString ::= {0, 1, 209, 81}

-- musicalSymbolMoonNoteheadWhite UniversalString ::= {0, 1, 209, 82}

-- musicalSymbolMoonNoteheadBlack UniversalString ::= {0, 1, 209, 83}

-- musicalSymbolTriangle-roundNoteheadDownWhite UniversalString ::=
--   {0, 1, 209, 84}

-- musicalSymbolTriangle-roundNoteheadDownBlack UniversalString ::=
--   {0, 1, 209, 85}

-- musicalSymbolParenthesisNotehead UniversalString ::= {0, 1, 209, 86}

-- musicalSymbolVoidNotehead UniversalString ::= {0, 1, 209, 87}

-- musicalSymbolNoteheadBlack UniversalString ::= {0, 1, 209, 88}

-- musicalSymbolNullNotehead UniversalString ::= {0, 1, 209, 89}

-- musicalSymbolClusterNoteheadWhite UniversalString ::= {0, 1, 209, 90}

-- musicalSymbolClusterNoteheadBlack UniversalString ::= {0, 1, 209, 91}

-- musicalSymbolBreve UniversalString ::= {0, 1, 209, 92}

-- musicalSymbolWholeNote UniversalString ::= {0, 1, 209, 93}

-- musicalSymbolHalfNote UniversalString ::= {0, 1, 209, 94}

-- musicalSymbolQuarterNote UniversalString ::= {0, 1, 209, 95}

-- musicalSymbolEighthNote UniversalString ::= {0, 1, 209, 96}

-- musicalSymbolSixteenthNote UniversalString ::= {0, 1, 209, 97}

-- musicalSymbolThirty-secondNote UniversalString ::= {0, 1, 209, 98}

-- musicalSymbolSixty-fourthNote UniversalString ::= {0, 1, 209, 99}

-- musicalSymbolOneHundredTwenty-eighthNote UniversalString ::= {0, 1, 209, 100}

-- musicalSymbolCombiningStem UniversalString ::= {0, 1, 209, 101}

-- musicalSymbolCombiningSprechgesangStem UniversalString ::= {0, 1, 209, 102}

-- musicalSymbolCombiningTremolo-1 UniversalString ::= {0, 1, 209, 103}

-- musicalSymbolCombiningTremolo-2 UniversalString ::= {0, 1, 209, 104}

-- musicalSymbolCombiningTremolo-3 UniversalString ::= {0, 1, 209, 105}

-- musicalSymbolFingeredTremolo-1 UniversalString ::= {0, 1, 209, 106}

-- musicalSymbolFingeredTremolo-2 UniversalString ::= {0, 1, 209, 107}

-- musicalSymbolFingeredTremolo-3 UniversalString ::= {0, 1, 209, 108}

-- musicalSymbolCombiningAugmentationDot UniversalString ::= {0, 1, 209, 109}

-- musicalSymbolCombiningFlag-1 UniversalString ::= {0, 1, 209, 110}

-- musicalSymbolCombiningFlag-2 UniversalString ::= {0, 1, 209, 111}

-- musicalSymbolCombiningFlag-3 UniversalString ::= {0, 1, 209, 112}

-- musicalSymbolCombiningFlag-4 UniversalString ::= {0, 1, 209, 113}

-- musicalSymbolCombiningFlag-5 UniversalString ::= {0, 1, 209, 114}

-- musicalSymbolBeginBeam UniversalString ::= {0, 1, 209, 115}

-- musicalSymbolEndBeam UniversalString ::= {0, 1, 209, 116}

-- musicalSymbolBeginTie UniversalString ::= {0, 1, 209, 117}

-- musicalSymbolEndTie UniversalString ::= {0, 1, 209, 118}

-- musicalSymbolBeginSlur UniversalString ::= {0, 1, 209, 119}

-- musicalSymbolEndSlur UniversalString ::= {0, 1, 209, 120}

-- musicalSymbolBeginPhrase UniversalString ::= {0, 1, 209, 121}

-- musicalSymbolEndPhrase UniversalString ::= {0, 1, 209, 122}

-- musicalSymbolCombiningAccent UniversalString ::= {0, 1, 209, 123}

-- musicalSymbolCombiningStaccato UniversalString ::= {0, 1, 209, 124}

-- musicalSymbolCombiningTenuto UniversalString ::= {0, 1, 209, 125}

-- musicalSymbolCombiningStaccatissimo UniversalString ::= {0, 1, 209, 126}

-- musicalSymbolCombiningMarcato UniversalString ::= {0, 1, 209, 127}

-- musicalSymbolCombiningMarcato-staccato UniversalString ::= {0, 1, 209, 128}

-- musicalSymbolCombiningAccent-staccato UniversalString ::= {0, 1, 209, 129}

-- musicalSymbolCombiningLoure UniversalString ::= {0, 1, 209, 130}

-- musicalSymbolArpeggiatoUp UniversalString ::= {0, 1, 209, 131}

-- musicalSymbolArpeggiatoDown UniversalString ::= {0, 1, 209, 132}

-- musicalSymbolCombiningDoit UniversalString ::= {0, 1, 209, 133}

-- musicalSymbolCombiningRip UniversalString ::= {0, 1, 209, 134}

-- musicalSymbolCombiningFlip UniversalString ::= {0, 1, 209, 135}

-- musicalSymbolCombiningSmear UniversalString ::= {0, 1, 209, 136}

-- musicalSymbolCombiningBend UniversalString ::= {0, 1, 209, 137}

-- musicalSymbolCombiningDoubleTongue UniversalString ::= {0, 1, 209, 138}

-- musicalSymbolCombiningTripleTongue UniversalString ::= {0, 1, 209, 139}

-- musicalSymbolRinforzando UniversalString ::= {0, 1, 209, 140}

-- musicalSymbolSubito UniversalString ::= {0, 1, 209, 141}

-- musicalSymbolZ UniversalString ::= {0, 1, 209, 142}

-- musicalSymbolPiano UniversalString ::= {0, 1, 209, 143}

-- musicalSymbolMezzo UniversalString ::= {0, 1, 209, 144}

-- musicalSymbolForte UniversalString ::= {0, 1, 209, 145}

-- musicalSymbolCrescendo UniversalString ::= {0, 1, 209, 146}

-- musicalSymbolDecrescendo UniversalString ::= {0, 1, 209, 147}

-- musicalSymbolGraceNoteSlash UniversalString ::= {0, 1, 209, 148}

-- musicalSymbolGraceNoteNoSlash UniversalString ::= {0, 1, 209, 149}

-- musicalSymbolTr UniversalString ::= {0, 1, 209, 150}

-- musicalSymbolTurn UniversalString ::= {0, 1, 209, 151}

-- musicalSymbolInvertedTurn UniversalString ::= {0, 1, 209, 152}

-- musicalSymbolTurnSlash UniversalString ::= {0, 1, 209, 153}

-- musicalSymbolTurnUp UniversalString ::= {0, 1, 209, 154}

-- musicalSymbolOrnamentStroke-1 UniversalString ::= {0, 1, 209, 155}

-- musicalSymbolOrnamentStroke-2 UniversalString ::= {0, 1, 209, 156}

-- musicalSymbolOrnamentStroke-3 UniversalString ::= {0, 1, 209, 157}

-- musicalSymbolOrnamentStroke-4 UniversalString ::= {0, 1, 209, 158}

-- musicalSymbolOrnamentStroke-5 UniversalString ::= {0, 1, 209, 159}

-- musicalSymbolOrnamentStroke-6 UniversalString ::= {0, 1, 209, 160}

-- musicalSymbolOrnamentStroke-7 UniversalString ::= {0, 1, 209, 161}

-- musicalSymbolOrnamentStroke-8 UniversalString ::= {0, 1, 209, 162}

-- musicalSymbolOrnamentStroke-9 UniversalString ::= {0, 1, 209, 163}

-- musicalSymbolOrnamentStroke-10 UniversalString ::= {0, 1, 209, 164}

-- musicalSymbolOrnamentStroke-11 UniversalString ::= {0, 1, 209, 165}

-- musicalSymbolHauptstimme UniversalString ::= {0, 1, 209, 166}

-- musicalSymbolNebenstimme UniversalString ::= {0, 1, 209, 167}

-- musicalSymbolEndOfStimme UniversalString ::= {0, 1, 209, 168}

-- musicalSymbolDegreeSlash UniversalString ::= {0, 1, 209, 169}

-- musicalSymbolCombiningDownBow UniversalString ::= {0, 1, 209, 170}

-- musicalSymbolCombiningUpBow UniversalString ::= {0, 1, 209, 171}

-- musicalSymbolCombiningHarmonic UniversalString ::= {0, 1, 209, 172}

-- musicalSymbolCombiningSnapPizzicato UniversalString ::= {0, 1, 209, 173}

-- musicalSymbolPedalMark UniversalString ::= {0, 1, 209, 174}

-- musicalSymbolPedalUpMark UniversalString ::= {0, 1, 209, 175}

-- musicalSymbolHalfPedalMark UniversalString ::= {0, 1, 209, 176}

-- musicalSymbolGlissandoUp UniversalString ::= {0, 1, 209, 177}

-- musicalSymbolGlissandoDown UniversalString ::= {0, 1, 209, 178}

-- musicalSymbolWithFingernails UniversalString ::= {0, 1, 209, 179}

-- musicalSymbolDamp UniversalString ::= {0, 1, 209, 180}

-- musicalSymbolDampAll UniversalString ::= {0, 1, 209, 181}

-- musicalSymbolMaxima UniversalString ::= {0, 1, 209, 182}

-- musicalSymbolLonga UniversalString ::= {0, 1, 209, 183}

-- musicalSymbolBrevis UniversalString ::= {0, 1, 209, 184}

-- musicalSymbolSemibrevisWhite UniversalString ::= {0, 1, 209, 185}

-- musicalSymbolSemibrevisBlack UniversalString ::= {0, 1, 209, 186}

-- musicalSymbolMinima UniversalString ::= {0, 1, 209, 187}

-- musicalSymbolMinimaBlack UniversalString ::= {0, 1, 209, 188}

-- musicalSymbolSemiminimaWhite UniversalString ::= {0, 1, 209, 189}

-- musicalSymbolSemiminimaBlack UniversalString ::= {0, 1, 209, 190}

-- musicalSymbolFusaWhite UniversalString ::= {0, 1, 209, 191}

-- musicalSymbolFusaBlack UniversalString ::= {0, 1, 209, 192}

-- musicalSymbolLongaPerfectaRest UniversalString ::= {0, 1, 209, 193}

-- musicalSymbolLongaImperfectaRest UniversalString ::= {0, 1, 209, 194}

-- musicalSymbolBrevisRest UniversalString ::= {0, 1, 209, 195}

-- musicalSymbolSemibrevisRest UniversalString ::= {0, 1, 209, 196}

-- musicalSymbolMinimaRest UniversalString ::= {0, 1, 209, 197}

-- musicalSymbolSemiminimaRest UniversalString ::= {0, 1, 209, 198}

-- musicalSymbolTempusPerfectumCumProlationePerfecta UniversalString ::=
--   {0, 1, 209, 199}

-- musicalSymbolTempusPerfectumCumProlationeImperfecta UniversalString ::=
--   {0, 1, 209, 200}

-- musicalSymbolTempusPerfectumCumProlationePerfectaDiminution-1 UniversalString
--   ::=
--   {0, 1, 209, 201}

-- musicalSymbolTempusImperfectumCumProlationePerfecta UniversalString ::=
--   {0, 1, 209, 202}

-- musicalSymbolTempusImperfectumCumProlationeImperfecta UniversalString ::=
--   {0, 1, 209, 203}

-- musicalSymbolTempusImperfectumCumProlationeImperfectaDiminution-1
--   UniversalString ::=
--   {0, 1, 209, 204}

-- musicalSymbolTempusImperfectumCumProlationeImperfectaDiminution-2
--   UniversalString ::=
--   {0, 1, 209, 205}

-- musicalSymbolTempusImperfectumCumProlationeImperfectaDiminution-3
--   UniversalString ::=
--   {0, 1, 209, 206}

-- musicalSymbolCroix UniversalString ::= {0, 1, 209, 207}

-- musicalSymbolGregorianCClef UniversalString ::= {0, 1, 209, 208}

-- musicalSymbolGregorianFClef UniversalString ::= {0, 1, 209, 209}

-- musicalSymbolSquareB UniversalString ::= {0, 1, 209, 210}

-- musicalSymbolVirga UniversalString ::= {0, 1, 209, 211}

-- musicalSymbolPodatus UniversalString ::= {0, 1, 209, 212}

-- musicalSymbolClivis UniversalString ::= {0, 1, 209, 213}

-- musicalSymbolScandicus UniversalString ::= {0, 1, 209, 214}

-- musicalSymbolClimacus UniversalString ::= {0, 1, 209, 215}

-- musicalSymbolTorculus UniversalString ::= {0, 1, 209, 216}

-- musicalSymbolPorrectus UniversalString ::= {0, 1, 209, 217}

-- musicalSymbolPorrectusFlexus UniversalString ::= {0, 1, 209, 218}

-- musicalSymbolScandicusFlexus UniversalString ::= {0, 1, 209, 219}

-- musicalSymbolTorculusResupinus UniversalString ::= {0, 1, 209, 220}

-- musicalSymbolPesSubpunctis UniversalString ::= {0, 1, 209, 221}

-- mathematicalBoldCapitalA UniversalString ::= {0, 1, 212, 0}

-- mathematicalBoldCapitalB UniversalString ::= {0, 1, 212, 1}

-- mathematicalBoldCapitalC UniversalString ::= {0, 1, 212, 2}

-- mathematicalBoldCapitalD UniversalString ::= {0, 1, 212, 3}

-- mathematicalBoldCapitalE UniversalString ::= {0, 1, 212, 4}

-- mathematicalBoldCapitalF UniversalString ::= {0, 1, 212, 5}

-- mathematicalBoldCapitalG UniversalString ::= {0, 1, 212, 6}

-- mathematicalBoldCapitalH UniversalString ::= {0, 1, 212, 7}

-- mathematicalBoldCapitalI UniversalString ::= {0, 1, 212, 8}

-- mathematicalBoldCapitalJ UniversalString ::= {0, 1, 212, 9}

-- mathematicalBoldCapitalK UniversalString ::= {0, 1, 212, 10}

-- mathematicalBoldCapitalL UniversalString ::= {0, 1, 212, 11}

-- mathematicalBoldCapitalM UniversalString ::= {0, 1, 212, 12}

-- mathematicalBoldCapitalN UniversalString ::= {0, 1, 212, 13}

-- mathematicalBoldCapitalO UniversalString ::= {0, 1, 212, 14}

-- mathematicalBoldCapitalP UniversalString ::= {0, 1, 212, 15}

-- mathematicalBoldCapitalQ UniversalString ::= {0, 1, 212, 16}

-- mathematicalBoldCapitalR UniversalString ::= {0, 1, 212, 17}

-- mathematicalBoldCapitalS UniversalString ::= {0, 1, 212, 18}

-- mathematicalBoldCapitalT UniversalString ::= {0, 1, 212, 19}

-- mathematicalBoldCapitalU UniversalString ::= {0, 1, 212, 20}

-- mathematicalBoldCapitalV UniversalString ::= {0, 1, 212, 21}

-- mathematicalBoldCapitalW UniversalString ::= {0, 1, 212, 22}

-- mathematicalBoldCapitalX UniversalString ::= {0, 1, 212, 23}

-- mathematicalBoldCapitalY UniversalString ::= {0, 1, 212, 24}

-- mathematicalBoldCapitalZ UniversalString ::= {0, 1, 212, 25}

-- mathematicalBoldSmallA UniversalString ::= {0, 1, 212, 26}

-- mathematicalBoldSmallB UniversalString ::= {0, 1, 212, 27}

-- mathematicalBoldSmallC UniversalString ::= {0, 1, 212, 28}

-- mathematicalBoldSmallD UniversalString ::= {0, 1, 212, 29}

-- mathematicalBoldSmallE UniversalString ::= {0, 1, 212, 30}

-- mathematicalBoldSmallF UniversalString ::= {0, 1, 212, 31}

-- mathematicalBoldSmallG UniversalString ::= {0, 1, 212, 32}

-- mathematicalBoldSmallH UniversalString ::= {0, 1, 212, 33}

-- mathematicalBoldSmallI UniversalString ::= {0, 1, 212, 34}

-- mathematicalBoldSmallJ UniversalString ::= {0, 1, 212, 35}

-- mathematicalBoldSmallK UniversalString ::= {0, 1, 212, 36}

-- mathematicalBoldSmallL UniversalString ::= {0, 1, 212, 37}

-- mathematicalBoldSmallM UniversalString ::= {0, 1, 212, 38}

-- mathematicalBoldSmallN UniversalString ::= {0, 1, 212, 39}

-- mathematicalBoldSmallO UniversalString ::= {0, 1, 212, 40}

-- mathematicalBoldSmallP UniversalString ::= {0, 1, 212, 41}

-- mathematicalBoldSmallQ UniversalString ::= {0, 1, 212, 42}

-- mathematicalBoldSmallR UniversalString ::= {0, 1, 212, 43}

-- mathematicalBoldSmallS UniversalString ::= {0, 1, 212, 44}

-- mathematicalBoldSmallT UniversalString ::= {0, 1, 212, 45}

-- mathematicalBoldSmallU UniversalString ::= {0, 1, 212, 46}

-- mathematicalBoldSmallV UniversalString ::= {0, 1, 212, 47}

-- mathematicalBoldSmallW UniversalString ::= {0, 1, 212, 48}

-- mathematicalBoldSmallX UniversalString ::= {0, 1, 212, 49}

-- mathematicalBoldSmallY UniversalString ::= {0, 1, 212, 50}

-- mathematicalBoldSmallZ UniversalString ::= {0, 1, 212, 51}

-- mathematicalItalicCapitalA UniversalString ::= {0, 1, 212, 52}

-- mathematicalItalicCapitalB UniversalString ::= {0, 1, 212, 53}

-- mathematicalItalicCapitalC UniversalString ::= {0, 1, 212, 54}

-- mathematicalItalicCapitalD UniversalString ::= {0, 1, 212, 55}

-- mathematicalItalicCapitalE UniversalString ::= {0, 1, 212, 56}

-- mathematicalItalicCapitalF UniversalString ::= {0, 1, 212, 57}

-- mathematicalItalicCapitalG UniversalString ::= {0, 1, 212, 58}

-- mathematicalItalicCapitalH UniversalString ::= {0, 1, 212, 59}

-- mathematicalItalicCapitalI UniversalString ::= {0, 1, 212, 60}

-- mathematicalItalicCapitalJ UniversalString ::= {0, 1, 212, 61}

-- mathematicalItalicCapitalK UniversalString ::= {0, 1, 212, 62}

-- mathematicalItalicCapitalL UniversalString ::= {0, 1, 212, 63}

-- mathematicalItalicCapitalM UniversalString ::= {0, 1, 212, 64}

-- mathematicalItalicCapitalN UniversalString ::= {0, 1, 212, 65}

-- mathematicalItalicCapitalO UniversalString ::= {0, 1, 212, 66}

-- mathematicalItalicCapitalP UniversalString ::= {0, 1, 212, 67}

-- mathematicalItalicCapitalQ UniversalString ::= {0, 1, 212, 68}

-- mathematicalItalicCapitalR UniversalString ::= {0, 1, 212, 69}

-- mathematicalItalicCapitalS UniversalString ::= {0, 1, 212, 70}

-- mathematicalItalicCapitalT UniversalString ::= {0, 1, 212, 71}

-- mathematicalItalicCapitalU UniversalString ::= {0, 1, 212, 72}

-- mathematicalItalicCapitalV UniversalString ::= {0, 1, 212, 73}

-- mathematicalItalicCapitalW UniversalString ::= {0, 1, 212, 74}

-- mathematicalItalicCapitalX UniversalString ::= {0, 1, 212, 75}

-- mathematicalItalicCapitalY UniversalString ::= {0, 1, 212, 76}

-- mathematicalItalicCapitalZ UniversalString ::= {0, 1, 212, 77}

-- mathematicalItalicSmallA UniversalString ::= {0, 1, 212, 78}

-- mathematicalItalicSmallB UniversalString ::= {0, 1, 212, 79}

-- mathematicalItalicSmallC UniversalString ::= {0, 1, 212, 80}

-- mathematicalItalicSmallD UniversalString ::= {0, 1, 212, 81}

-- mathematicalItalicSmallE UniversalString ::= {0, 1, 212, 82}

-- mathematicalItalicSmallF UniversalString ::= {0, 1, 212, 83}

-- mathematicalItalicSmallG UniversalString ::= {0, 1, 212, 84}

-- mathematicalItalicSmallI UniversalString ::= {0, 1, 212, 86}

-- mathematicalItalicSmallJ UniversalString ::= {0, 1, 212, 87}

-- mathematicalItalicSmallK UniversalString ::= {0, 1, 212, 88}

-- mathematicalItalicSmallL UniversalString ::= {0, 1, 212, 89}

-- mathematicalItalicSmallM UniversalString ::= {0, 1, 212, 90}

-- mathematicalItalicSmallN UniversalString ::= {0, 1, 212, 91}

-- mathematicalItalicSmallO UniversalString ::= {0, 1, 212, 92}

-- mathematicalItalicSmallP UniversalString ::= {0, 1, 212, 93}

-- mathematicalItalicSmallQ UniversalString ::= {0, 1, 212, 94}

-- mathematicalItalicSmallR UniversalString ::= {0, 1, 212, 95}

-- mathematicalItalicSmallS UniversalString ::= {0, 1, 212, 96}

-- mathematicalItalicSmallT UniversalString ::= {0, 1, 212, 97}

-- mathematicalItalicSmallU UniversalString ::= {0, 1, 212, 98}

-- mathematicalItalicSmallV UniversalString ::= {0, 1, 212, 99}

-- mathematicalItalicSmallW UniversalString ::= {0, 1, 212, 100}

-- mathematicalItalicSmallX UniversalString ::= {0, 1, 212, 101}

-- mathematicalItalicSmallY UniversalString ::= {0, 1, 212, 102}

-- mathematicalItalicSmallZ UniversalString ::= {0, 1, 212, 103}

-- mathematicalBoldItalicCapitalA UniversalString ::= {0, 1, 212, 104}

-- mathematicalBoldItalicCapitalB UniversalString ::= {0, 1, 212, 105}

-- mathematicalBoldItalicCapitalC UniversalString ::= {0, 1, 212, 106}

-- mathematicalBoldItalicCapitalD UniversalString ::= {0, 1, 212, 107}

-- mathematicalBoldItalicCapitalE UniversalString ::= {0, 1, 212, 108}

-- mathematicalBoldItalicCapitalF UniversalString ::= {0, 1, 212, 109}

-- mathematicalBoldItalicCapitalG UniversalString ::= {0, 1, 212, 110}

-- mathematicalBoldItalicCapitalH UniversalString ::= {0, 1, 212, 111}

-- mathematicalBoldItalicCapitalI UniversalString ::= {0, 1, 212, 112}

-- mathematicalBoldItalicCapitalJ UniversalString ::= {0, 1, 212, 113}

-- mathematicalBoldItalicCapitalK UniversalString ::= {0, 1, 212, 114}

-- mathematicalBoldItalicCapitalL UniversalString ::= {0, 1, 212, 115}

-- mathematicalBoldItalicCapitalM UniversalString ::= {0, 1, 212, 116}

-- mathematicalBoldItalicCapitalN UniversalString ::= {0, 1, 212, 117}

-- mathematicalBoldItalicCapitalO UniversalString ::= {0, 1, 212, 118}

-- mathematicalBoldItalicCapitalP UniversalString ::= {0, 1, 212, 119}

-- mathematicalBoldItalicCapitalQ UniversalString ::= {0, 1, 212, 120}

-- mathematicalBoldItalicCapitalR UniversalString ::= {0, 1, 212, 121}

-- mathematicalBoldItalicCapitalS UniversalString ::= {0, 1, 212, 122}

-- mathematicalBoldItalicCapitalT UniversalString ::= {0, 1, 212, 123}

-- mathematicalBoldItalicCapitalU UniversalString ::= {0, 1, 212, 124}

-- mathematicalBoldItalicCapitalV UniversalString ::= {0, 1, 212, 125}

-- mathematicalBoldItalicCapitalW UniversalString ::= {0, 1, 212, 126}

-- mathematicalBoldItalicCapitalX UniversalString ::= {0, 1, 212, 127}

-- mathematicalBoldItalicCapitalY UniversalString ::= {0, 1, 212, 128}

-- mathematicalBoldItalicCapitalZ UniversalString ::= {0, 1, 212, 129}

-- mathematicalBoldItalicSmallA UniversalString ::= {0, 1, 212, 130}

-- mathematicalBoldItalicSmallB UniversalString ::= {0, 1, 212, 131}

-- mathematicalBoldItalicSmallC UniversalString ::= {0, 1, 212, 132}

-- mathematicalBoldItalicSmallD UniversalString ::= {0, 1, 212, 133}

-- mathematicalBoldItalicSmallE UniversalString ::= {0, 1, 212, 134}

-- mathematicalBoldItalicSmallF UniversalString ::= {0, 1, 212, 135}

-- mathematicalBoldItalicSmallG UniversalString ::= {0, 1, 212, 136}

-- mathematicalBoldItalicSmallH UniversalString ::= {0, 1, 212, 137}

-- mathematicalBoldItalicSmallI UniversalString ::= {0, 1, 212, 138}

-- mathematicalBoldItalicSmallJ UniversalString ::= {0, 1, 212, 139}

-- mathematicalBoldItalicSmallK UniversalString ::= {0, 1, 212, 140}

-- mathematicalBoldItalicSmallL UniversalString ::= {0, 1, 212, 141}

-- mathematicalBoldItalicSmallM UniversalString ::= {0, 1, 212, 142}

-- mathematicalBoldItalicSmallN UniversalString ::= {0, 1, 212, 143}

-- mathematicalBoldItalicSmallO UniversalString ::= {0, 1, 212, 144}

-- mathematicalBoldItalicSmallP UniversalString ::= {0, 1, 212, 145}

-- mathematicalBoldItalicSmallQ UniversalString ::= {0, 1, 212, 146}

-- mathematicalBoldItalicSmallR UniversalString ::= {0, 1, 212, 147}

-- mathematicalBoldItalicSmallS UniversalString ::= {0, 1, 212, 148}

-- mathematicalBoldItalicSmallT UniversalString ::= {0, 1, 212, 149}

-- mathematicalBoldItalicSmallU UniversalString ::= {0, 1, 212, 150}

-- mathematicalBoldItalicSmallV UniversalString ::= {0, 1, 212, 151}

-- mathematicalBoldItalicSmallW UniversalString ::= {0, 1, 212, 152}

-- mathematicalBoldItalicSmallX UniversalString ::= {0, 1, 212, 153}

-- mathematicalBoldItalicSmallY UniversalString ::= {0, 1, 212, 154}

-- mathematicalBoldItalicSmallZ UniversalString ::= {0, 1, 212, 155}

-- mathematicalScriptCapitalA UniversalString ::= {0, 1, 212, 156}

-- mathematicalScriptCapitalC UniversalString ::= {0, 1, 212, 158}

-- mathematicalScriptCapitalD UniversalString ::= {0, 1, 212, 159}

-- mathematicalScriptCapitalG UniversalString ::= {0, 1, 212, 162}

-- mathematicalScriptCapitalJ UniversalString ::= {0, 1, 212, 165}

-- mathematicalScriptCapitalK UniversalString ::= {0, 1, 212, 166}

-- mathematicalScriptCapitalN UniversalString ::= {0, 1, 212, 169}

-- mathematicalScriptCapitalO UniversalString ::= {0, 1, 212, 170}

-- mathematicalScriptCapitalP UniversalString ::= {0, 1, 212, 171}

-- mathematicalScriptCapitalQ UniversalString ::= {0, 1, 212, 172}

-- mathematicalScriptCapitalS UniversalString ::= {0, 1, 212, 174}

-- mathematicalScriptCapitalT UniversalString ::= {0, 1, 212, 175}

-- mathematicalScriptCapitalU UniversalString ::= {0, 1, 212, 176}

-- mathematicalScriptCapitalV UniversalString ::= {0, 1, 212, 177}

-- mathematicalScriptCapitalW UniversalString ::= {0, 1, 212, 178}

-- mathematicalScriptCapitalX UniversalString ::= {0, 1, 212, 179}

-- mathematicalScriptCapitalY UniversalString ::= {0, 1, 212, 180}

-- mathematicalScriptCapitalZ UniversalString ::= {0, 1, 212, 181}

-- mathematicalScriptSmallA UniversalString ::= {0, 1, 212, 182}

-- mathematicalScriptSmallB UniversalString ::= {0, 1, 212, 183}

-- mathematicalScriptSmallC UniversalString ::= {0, 1, 212, 184}

-- mathematicalScriptSmallD UniversalString ::= {0, 1, 212, 185}

-- mathematicalScriptSmallF UniversalString ::= {0, 1, 212, 187}

-- mathematicalScriptSmallH UniversalString ::= {0, 1, 212, 189}

-- mathematicalScriptSmallI UniversalString ::= {0, 1, 212, 190}

-- mathematicalScriptSmallJ UniversalString ::= {0, 1, 212, 191}

-- mathematicalScriptSmallK UniversalString ::= {0, 1, 212, 192}

-- mathematicalScriptSmallM UniversalString ::= {0, 1, 212, 194}

-- mathematicalScriptSmallN UniversalString ::= {0, 1, 212, 195}

-- mathematicalScriptSmallP UniversalString ::= {0, 1, 212, 197}

-- mathematicalScriptSmallQ UniversalString ::= {0, 1, 212, 198}

-- mathematicalScriptSmallR UniversalString ::= {0, 1, 212, 199}

-- mathematicalScriptSmallS UniversalString ::= {0, 1, 212, 200}

-- mathematicalScriptSmallT UniversalString ::= {0, 1, 212, 201}

-- mathematicalScriptSmallU UniversalString ::= {0, 1, 212, 202}

-- mathematicalScriptSmallV UniversalString ::= {0, 1, 212, 203}

-- mathematicalScriptSmallW UniversalString ::= {0, 1, 212, 204}

-- mathematicalScriptSmallX UniversalString ::= {0, 1, 212, 205}

-- mathematicalScriptSmallY UniversalString ::= {0, 1, 212, 206}

-- mathematicalScriptSmallZ UniversalString ::= {0, 1, 212, 207}

-- mathematicalBoldScriptCapitalA UniversalString ::= {0, 1, 212, 208}

-- mathematicalBoldScriptCapitalB UniversalString ::= {0, 1, 212, 209}

-- mathematicalBoldScriptCapitalC UniversalString ::= {0, 1, 212, 210}

-- mathematicalBoldScriptCapitalD UniversalString ::= {0, 1, 212, 211}

-- mathematicalBoldScriptCapitalE UniversalString ::= {0, 1, 212, 212}

-- mathematicalBoldScriptCapitalF UniversalString ::= {0, 1, 212, 213}

-- mathematicalBoldScriptCapitalG UniversalString ::= {0, 1, 212, 214}

-- mathematicalBoldScriptCapitalH UniversalString ::= {0, 1, 212, 215}

-- mathematicalBoldScriptCapitalI UniversalString ::= {0, 1, 212, 216}

-- mathematicalBoldScriptCapitalJ UniversalString ::= {0, 1, 212, 217}

-- mathematicalBoldScriptCapitalK UniversalString ::= {0, 1, 212, 218}

-- mathematicalBoldScriptCapitalL UniversalString ::= {0, 1, 212, 219}

-- mathematicalBoldScriptCapitalM UniversalString ::= {0, 1, 212, 220}

-- mathematicalBoldScriptCapitalN UniversalString ::= {0, 1, 212, 221}

-- mathematicalBoldScriptCapitalO UniversalString ::= {0, 1, 212, 222}

-- mathematicalBoldScriptCapitalP UniversalString ::= {0, 1, 212, 223}

-- mathematicalBoldScriptCapitalQ UniversalString ::= {0, 1, 212, 224}

-- mathematicalBoldScriptCapitalR UniversalString ::= {0, 1, 212, 225}

-- mathematicalBoldScriptCapitalS UniversalString ::= {0, 1, 212, 226}

-- mathematicalBoldScriptCapitalT UniversalString ::= {0, 1, 212, 227}

-- mathematicalBoldScriptCapitalU UniversalString ::= {0, 1, 212, 228}

-- mathematicalBoldScriptCapitalV UniversalString ::= {0, 1, 212, 229}

-- mathematicalBoldScriptCapitalW UniversalString ::= {0, 1, 212, 230}

-- mathematicalBoldScriptCapitalX UniversalString ::= {0, 1, 212, 231}

-- mathematicalBoldScriptCapitalY UniversalString ::= {0, 1, 212, 232}

-- mathematicalBoldScriptCapitalZ UniversalString ::= {0, 1, 212, 233}

-- mathematicalBoldScriptSmallA UniversalString ::= {0, 1, 212, 234}

-- mathematicalBoldScriptSmallB UniversalString ::= {0, 1, 212, 235}

-- mathematicalBoldScriptSmallC UniversalString ::= {0, 1, 212, 236}

-- mathematicalBoldScriptSmallD UniversalString ::= {0, 1, 212, 237}

-- mathematicalBoldScriptSmallE UniversalString ::= {0, 1, 212, 238}

-- mathematicalBoldScriptSmallF UniversalString ::= {0, 1, 212, 239}

-- mathematicalBoldScriptSmallG UniversalString ::= {0, 1, 212, 240}

-- mathematicalBoldScriptSmallH UniversalString ::= {0, 1, 212, 241}

-- mathematicalBoldScriptSmallI UniversalString ::= {0, 1, 212, 242}

-- mathematicalBoldScriptSmallJ UniversalString ::= {0, 1, 212, 243}

-- mathematicalBoldScriptSmallK UniversalString ::= {0, 1, 212, 244}

-- mathematicalBoldScriptSmallL UniversalString ::= {0, 1, 212, 245}

-- mathematicalBoldScriptSmallM UniversalString ::= {0, 1, 212, 246}

-- mathematicalBoldScriptSmallN UniversalString ::= {0, 1, 212, 247}

-- mathematicalBoldScriptSmallO UniversalString ::= {0, 1, 212, 248}

-- mathematicalBoldScriptSmallP UniversalString ::= {0, 1, 212, 249}

-- mathematicalBoldScriptSmallQ UniversalString ::= {0, 1, 212, 250}

-- mathematicalBoldScriptSmallR UniversalString ::= {0, 1, 212, 251}

-- mathematicalBoldScriptSmallS UniversalString ::= {0, 1, 212, 252}

-- mathematicalBoldScriptSmallT UniversalString ::= {0, 1, 212, 253}

-- mathematicalBoldScriptSmallU UniversalString ::= {0, 1, 212, 254}

-- mathematicalBoldScriptSmallV UniversalString ::= {0, 1, 212, 255}

-- mathematicalBoldScriptSmallW UniversalString ::= {0, 1, 213, 0}

-- mathematicalBoldScriptSmallX UniversalString ::= {0, 1, 213, 1}

-- mathematicalBoldScriptSmallY UniversalString ::= {0, 1, 213, 2}

-- mathematicalBoldScriptSmallZ UniversalString ::= {0, 1, 213, 3}

-- mathematicalFrakturCapitalA UniversalString ::= {0, 1, 213, 4}

-- mathematicalFrakturCapitalB UniversalString ::= {0, 1, 213, 5}

-- mathematicalFrakturCapitalD UniversalString ::= {0, 1, 213, 7}

-- mathematicalFrakturCapitalE UniversalString ::= {0, 1, 213, 8}

-- mathematicalFrakturCapitalF UniversalString ::= {0, 1, 213, 9}

-- mathematicalFrakturCapitalG UniversalString ::= {0, 1, 213, 10}

-- mathematicalFrakturCapitalJ UniversalString ::= {0, 1, 213, 13}

-- mathematicalFrakturCapitalK UniversalString ::= {0, 1, 213, 14}

-- mathematicalFrakturCapitalL UniversalString ::= {0, 1, 213, 15}

-- mathematicalFrakturCapitalM UniversalString ::= {0, 1, 213, 16}

-- mathematicalFrakturCapitalN UniversalString ::= {0, 1, 213, 17}

-- mathematicalFrakturCapitalO UniversalString ::= {0, 1, 213, 18}

-- mathematicalFrakturCapitalP UniversalString ::= {0, 1, 213, 19}

-- mathematicalFrakturCapitalQ UniversalString ::= {0, 1, 213, 20}

-- mathematicalFrakturCapitalS UniversalString ::= {0, 1, 213, 22}

-- mathematicalFrakturCapitalT UniversalString ::= {0, 1, 213, 23}

-- mathematicalFrakturCapitalU UniversalString ::= {0, 1, 213, 24}

-- mathematicalFrakturCapitalV UniversalString ::= {0, 1, 213, 25}

-- mathematicalFrakturCapitalW UniversalString ::= {0, 1, 213, 26}

-- mathematicalFrakturCapitalX UniversalString ::= {0, 1, 213, 27}

-- mathematicalFrakturCapitalY UniversalString ::= {0, 1, 213, 28}

-- mathematicalFrakturSmallA UniversalString ::= {0, 1, 213, 30}

-- mathematicalFrakturSmallB UniversalString ::= {0, 1, 213, 31}

-- mathematicalFrakturSmallC UniversalString ::= {0, 1, 213, 32}

-- mathematicalFrakturSmallD UniversalString ::= {0, 1, 213, 33}

-- mathematicalFrakturSmallE UniversalString ::= {0, 1, 213, 34}

-- mathematicalFrakturSmallF UniversalString ::= {0, 1, 213, 35}

-- mathematicalFrakturSmallG UniversalString ::= {0, 1, 213, 36}

-- mathematicalFrakturSmallH UniversalString ::= {0, 1, 213, 37}

-- mathematicalFrakturSmallI UniversalString ::= {0, 1, 213, 38}

-- mathematicalFrakturSmallJ UniversalString ::= {0, 1, 213, 39}

-- mathematicalFrakturSmallK UniversalString ::= {0, 1, 213, 40}

-- mathematicalFrakturSmallL UniversalString ::= {0, 1, 213, 41}

-- mathematicalFrakturSmallM UniversalString ::= {0, 1, 213, 42}

-- mathematicalFrakturSmallN UniversalString ::= {0, 1, 213, 43}

-- mathematicalFrakturSmallO UniversalString ::= {0, 1, 213, 44}

-- mathematicalFrakturSmallP UniversalString ::= {0, 1, 213, 45}

-- mathematicalFrakturSmallQ UniversalString ::= {0, 1, 213, 46}

-- mathematicalFrakturSmallR UniversalString ::= {0, 1, 213, 47}

-- mathematicalFrakturSmallS UniversalString ::= {0, 1, 213, 48}

-- mathematicalFrakturSmallT UniversalString ::= {0, 1, 213, 49}

-- mathematicalFrakturSmallU UniversalString ::= {0, 1, 213, 50}

-- mathematicalFrakturSmallV UniversalString ::= {0, 1, 213, 51}

-- mathematicalFrakturSmallW UniversalString ::= {0, 1, 213, 52}

-- mathematicalFrakturSmallX UniversalString ::= {0, 1, 213, 53}

-- mathematicalFrakturSmallY UniversalString ::= {0, 1, 213, 54}

-- mathematicalFrakturSmallZ UniversalString ::= {0, 1, 213, 55}

-- mathematicalDouble-struckCapitalA UniversalString ::= {0, 1, 213, 56}

-- mathematicalDouble-struckCapitalB UniversalString ::= {0, 1, 213, 57}

-- mathematicalDouble-struckCapitalD UniversalString ::= {0, 1, 213, 59}

-- mathematicalDouble-struckCapitalE UniversalString ::= {0, 1, 213, 60}

-- mathematicalDouble-struckCapitalF UniversalString ::= {0, 1, 213, 61}

-- mathematicalDouble-struckCapitalG UniversalString ::= {0, 1, 213, 62}

-- mathematicalDouble-struckCapitalI UniversalString ::= {0, 1, 213, 64}

-- mathematicalDouble-struckCapitalJ UniversalString ::= {0, 1, 213, 65}

-- mathematicalDouble-struckCapitalK UniversalString ::= {0, 1, 213, 66}

-- mathematicalDouble-struckCapitalL UniversalString ::= {0, 1, 213, 67}

-- mathematicalDouble-struckCapitalM UniversalString ::= {0, 1, 213, 68}

-- mathematicalDouble-struckCapitalO UniversalString ::= {0, 1, 213, 70}

-- mathematicalDouble-struckCapitalS UniversalString ::= {0, 1, 213, 74}

-- mathematicalDouble-struckCapitalT UniversalString ::= {0, 1, 213, 75}

-- mathematicalDouble-struckCapitalU UniversalString ::= {0, 1, 213, 76}

-- mathematicalDouble-struckCapitalV UniversalString ::= {0, 1, 213, 77}

-- mathematicalDouble-struckCapitalW UniversalString ::= {0, 1, 213, 78}

-- mathematicalDouble-struckCapitalX UniversalString ::= {0, 1, 213, 79}

-- mathematicalDouble-struckCapitalY UniversalString ::= {0, 1, 213, 80}

-- mathematicalDouble-struckSmallA UniversalString ::= {0, 1, 213, 82}

-- mathematicalDouble-struckSmallB UniversalString ::= {0, 1, 213, 83}

-- mathematicalDouble-struckSmallC UniversalString ::= {0, 1, 213, 84}

-- mathematicalDouble-struckSmallD UniversalString ::= {0, 1, 213, 85}

-- mathematicalDouble-struckSmallE UniversalString ::= {0, 1, 213, 86}

-- mathematicalDouble-struckSmallF UniversalString ::= {0, 1, 213, 87}

-- mathematicalDouble-struckSmallG UniversalString ::= {0, 1, 213, 88}

-- mathematicalDouble-struckSmallH UniversalString ::= {0, 1, 213, 89}

-- mathematicalDouble-struckSmallI UniversalString ::= {0, 1, 213, 90}

-- mathematicalDouble-struckSmallJ UniversalString ::= {0, 1, 213, 91}

-- mathematicalDouble-struckSmallK UniversalString ::= {0, 1, 213, 92}

-- mathematicalDouble-struckSmallL UniversalString ::= {0, 1, 213, 93}

-- mathematicalDouble-struckSmallM UniversalString ::= {0, 1, 213, 94}

-- mathematicalDouble-struckSmallN UniversalString ::= {0, 1, 213, 95}

-- mathematicalDouble-struckSmallO UniversalString ::= {0, 1, 213, 96}

-- mathematicalDouble-struckSmallP UniversalString ::= {0, 1, 213, 97}

-- mathematicalDouble-struckSmallQ UniversalString ::= {0, 1, 213, 98}

-- mathematicalDouble-struckSmallR UniversalString ::= {0, 1, 213, 99}

-- mathematicalDouble-struckSmallS UniversalString ::= {0, 1, 213, 100}

-- mathematicalDouble-struckSmallT UniversalString ::= {0, 1, 213, 101}

-- mathematicalDouble-struckSmallU UniversalString ::= {0, 1, 213, 102}

-- mathematicalDouble-struckSmallV UniversalString ::= {0, 1, 213, 103}

-- mathematicalDouble-struckSmallW UniversalString ::= {0, 1, 213, 104}

-- mathematicalDouble-struckSmallX UniversalString ::= {0, 1, 213, 105}

-- mathematicalDouble-struckSmallY UniversalString ::= {0, 1, 213, 106}

-- mathematicalDouble-struckSmallZ UniversalString ::= {0, 1, 213, 107}

-- mathematicalBoldFrakturCapitalA UniversalString ::= {0, 1, 213, 108}

-- mathematicalBoldFrakturCapitalB UniversalString ::= {0, 1, 213, 109}

-- mathematicalBoldFrakturCapitalC UniversalString ::= {0, 1, 213, 110}

-- mathematicalBoldFrakturCapitalD UniversalString ::= {0, 1, 213, 111}

-- mathematicalBoldFrakturCapitalE UniversalString ::= {0, 1, 213, 112}

-- mathematicalBoldFrakturCapitalF UniversalString ::= {0, 1, 213, 113}

-- mathematicalBoldFrakturCapitalG UniversalString ::= {0, 1, 213, 114}

-- mathematicalBoldFrakturCapitalH UniversalString ::= {0, 1, 213, 115}

-- mathematicalBoldFrakturCapitalI UniversalString ::= {0, 1, 213, 116}

-- mathematicalBoldFrakturCapitalJ UniversalString ::= {0, 1, 213, 117}

-- mathematicalBoldFrakturCapitalK UniversalString ::= {0, 1, 213, 118}

-- mathematicalBoldFrakturCapitalL UniversalString ::= {0, 1, 213, 119}

-- mathematicalBoldFrakturCapitalM UniversalString ::= {0, 1, 213, 120}

-- mathematicalBoldFrakturCapitalN UniversalString ::= {0, 1, 213, 121}

-- mathematicalBoldFrakturCapitalO UniversalString ::= {0, 1, 213, 122}

-- mathematicalBoldFrakturCapitalP UniversalString ::= {0, 1, 213, 123}

-- mathematicalBoldFrakturCapitalQ UniversalString ::= {0, 1, 213, 124}

-- mathematicalBoldFrakturCapitalR UniversalString ::= {0, 1, 213, 125}

-- mathematicalBoldFrakturCapitalS UniversalString ::= {0, 1, 213, 126}

-- mathematicalBoldFrakturCapitalT UniversalString ::= {0, 1, 213, 127}

-- mathematicalBoldFrakturCapitalU UniversalString ::= {0, 1, 213, 128}

-- mathematicalBoldFrakturCapitalV UniversalString ::= {0, 1, 213, 129}

-- mathematicalBoldFrakturCapitalW UniversalString ::= {0, 1, 213, 130}

-- mathematicalBoldFrakturCapitalX UniversalString ::= {0, 1, 213, 131}

-- mathematicalBoldFrakturCapitalY UniversalString ::= {0, 1, 213, 132}

-- mathematicalBoldFrakturCapitalZ UniversalString ::= {0, 1, 213, 133}

-- mathematicalBoldFrakturSmallA UniversalString ::= {0, 1, 213, 134}

-- mathematicalBoldFrakturSmallB UniversalString ::= {0, 1, 213, 135}

-- mathematicalBoldFrakturSmallC UniversalString ::= {0, 1, 213, 136}

-- mathematicalBoldFrakturSmallD UniversalString ::= {0, 1, 213, 137}

-- mathematicalBoldFrakturSmallE UniversalString ::= {0, 1, 213, 138}

-- mathematicalBoldFrakturSmallF UniversalString ::= {0, 1, 213, 139}

-- mathematicalBoldFrakturSmallG UniversalString ::= {0, 1, 213, 140}

-- mathematicalBoldFrakturSmallH UniversalString ::= {0, 1, 213, 141}

-- mathematicalBoldFrakturSmallI UniversalString ::= {0, 1, 213, 142}

-- mathematicalBoldFrakturSmallJ UniversalString ::= {0, 1, 213, 143}

-- mathematicalBoldFrakturSmallK UniversalString ::= {0, 1, 213, 144}

-- mathematicalBoldFrakturSmallL UniversalString ::= {0, 1, 213, 145}

-- mathematicalBoldFrakturSmallM UniversalString ::= {0, 1, 213, 146}

-- mathematicalBoldFrakturSmallN UniversalString ::= {0, 1, 213, 147}

-- mathematicalBoldFrakturSmallO UniversalString ::= {0, 1, 213, 148}

-- mathematicalBoldFrakturSmallP UniversalString ::= {0, 1, 213, 149}

-- mathematicalBoldFrakturSmallQ UniversalString ::= {0, 1, 213, 150}

-- mathematicalBoldFrakturSmallR UniversalString ::= {0, 1, 213, 151}

-- mathematicalBoldFrakturSmallS UniversalString ::= {0, 1, 213, 152}

-- mathematicalBoldFrakturSmallT UniversalString ::= {0, 1, 213, 153}

-- mathematicalBoldFrakturSmallU UniversalString ::= {0, 1, 213, 154}

-- mathematicalBoldFrakturSmallV UniversalString ::= {0, 1, 213, 155}

-- mathematicalBoldFrakturSmallW UniversalString ::= {0, 1, 213, 156}

-- mathematicalBoldFrakturSmallX UniversalString ::= {0, 1, 213, 157}

-- mathematicalBoldFrakturSmallY UniversalString ::= {0, 1, 213, 158}

-- mathematicalBoldFrakturSmallZ UniversalString ::= {0, 1, 213, 159}

-- mathematicalSans-serifCapitalA UniversalString ::= {0, 1, 213, 160}

-- mathematicalSans-serifCapitalB UniversalString ::= {0, 1, 213, 161}

-- mathematicalSans-serifCapitalC UniversalString ::= {0, 1, 213, 162}

-- mathematicalSans-serifCapitalD UniversalString ::= {0, 1, 213, 163}

-- mathematicalSans-serifCapitalE UniversalString ::= {0, 1, 213, 164}

-- mathematicalSans-serifCapitalF UniversalString ::= {0, 1, 213, 165}

-- mathematicalSans-serifCapitalG UniversalString ::= {0, 1, 213, 166}

-- mathematicalSans-serifCapitalH UniversalString ::= {0, 1, 213, 167}

-- mathematicalSans-serifCapitalI UniversalString ::= {0, 1, 213, 168}

-- mathematicalSans-serifCapitalJ UniversalString ::= {0, 1, 213, 169}

-- mathematicalSans-serifCapitalK UniversalString ::= {0, 1, 213, 170}

-- mathematicalSans-serifCapitalL UniversalString ::= {0, 1, 213, 171}

-- mathematicalSans-serifCapitalM UniversalString ::= {0, 1, 213, 172}

-- mathematicalSans-serifCapitalN UniversalString ::= {0, 1, 213, 173}

-- mathematicalSans-serifCapitalO UniversalString ::= {0, 1, 213, 174}

-- mathematicalSans-serifCapitalP UniversalString ::= {0, 1, 213, 175}

-- mathematicalSans-serifCapitalQ UniversalString ::= {0, 1, 213, 176}

-- mathematicalSans-serifCapitalR UniversalString ::= {0, 1, 213, 177}

-- mathematicalSans-serifCapitalS UniversalString ::= {0, 1, 213, 178}

-- mathematicalSans-serifCapitalT UniversalString ::= {0, 1, 213, 179}

-- mathematicalSans-serifCapitalU UniversalString ::= {0, 1, 213, 180}

-- mathematicalSans-serifCapitalV UniversalString ::= {0, 1, 213, 181}

-- mathematicalSans-serifCapitalW UniversalString ::= {0, 1, 213, 182}

-- mathematicalSans-serifCapitalX UniversalString ::= {0, 1, 213, 183}

-- mathematicalSans-serifCapitalY UniversalString ::= {0, 1, 213, 184}

-- mathematicalSans-serifCapitalZ UniversalString ::= {0, 1, 213, 185}

-- mathematicalSans-serifSmallA UniversalString ::= {0, 1, 213, 186}

-- mathematicalSans-serifSmallB UniversalString ::= {0, 1, 213, 187}

-- mathematicalSans-serifSmallC UniversalString ::= {0, 1, 213, 188}

-- mathematicalSans-serifSmallD UniversalString ::= {0, 1, 213, 189}

-- mathematicalSans-serifSmallE UniversalString ::= {0, 1, 213, 190}

-- mathematicalSans-serifSmallF UniversalString ::= {0, 1, 213, 191}

-- mathematicalSans-serifSmallG UniversalString ::= {0, 1, 213, 192}

-- mathematicalSans-serifSmallH UniversalString ::= {0, 1, 213, 193}

-- mathematicalSans-serifSmallI UniversalString ::= {0, 1, 213, 194}

-- mathematicalSans-serifSmallJ UniversalString ::= {0, 1, 213, 195}

-- mathematicalSans-serifSmallK UniversalString ::= {0, 1, 213, 196}

-- mathematicalSans-serifSmallL UniversalString ::= {0, 1, 213, 197}

-- mathematicalSans-serifSmallM UniversalString ::= {0, 1, 213, 198}

-- mathematicalSans-serifSmallN UniversalString ::= {0, 1, 213, 199}

-- mathematicalSans-serifSmallO UniversalString ::= {0, 1, 213, 200}

-- mathematicalSans-serifSmallP UniversalString ::= {0, 1, 213, 201}

-- mathematicalSans-serifSmallQ UniversalString ::= {0, 1, 213, 202}

-- mathematicalSans-serifSmallR UniversalString ::= {0, 1, 213, 203}

-- mathematicalSans-serifSmallS UniversalString ::= {0, 1, 213, 204}

-- mathematicalSans-serifSmallT UniversalString ::= {0, 1, 213, 205}

-- mathematicalSans-serifSmallU UniversalString ::= {0, 1, 213, 206}

-- mathematicalSans-serifSmallV UniversalString ::= {0, 1, 213, 207}

-- mathematicalSans-serifSmallW UniversalString ::= {0, 1, 213, 208}

-- mathematicalSans-serifSmallX UniversalString ::= {0, 1, 213, 209}

-- mathematicalSans-serifSmallY UniversalString ::= {0, 1, 213, 210}

-- mathematicalSans-serifSmallZ UniversalString ::= {0, 1, 213, 211}

-- mathematicalSans-serifBoldCapitalA UniversalString ::= {0, 1, 213, 212}

-- mathematicalSans-serifBoldCapitalB UniversalString ::= {0, 1, 213, 213}

-- mathematicalSans-serifBoldCapitalC UniversalString ::= {0, 1, 213, 214}

-- mathematicalSans-serifBoldCapitalD UniversalString ::= {0, 1, 213, 215}

-- mathematicalSans-serifBoldCapitalE UniversalString ::= {0, 1, 213, 216}

-- mathematicalSans-serifBoldCapitalF UniversalString ::= {0, 1, 213, 217}

-- mathematicalSans-serifBoldCapitalG UniversalString ::= {0, 1, 213, 218}

-- mathematicalSans-serifBoldCapitalH UniversalString ::= {0, 1, 213, 219}

-- mathematicalSans-serifBoldCapitalI UniversalString ::= {0, 1, 213, 220}

-- mathematicalSans-serifBoldCapitalJ UniversalString ::= {0, 1, 213, 221}

-- mathematicalSans-serifBoldCapitalK UniversalString ::= {0, 1, 213, 222}

-- mathematicalSans-serifBoldCapitalL UniversalString ::= {0, 1, 213, 223}

-- mathematicalSans-serifBoldCapitalM UniversalString ::= {0, 1, 213, 224}

-- mathematicalSans-serifBoldCapitalN UniversalString ::= {0, 1, 213, 225}

-- mathematicalSans-serifBoldCapitalO UniversalString ::= {0, 1, 213, 226}

-- mathematicalSans-serifBoldCapitalP UniversalString ::= {0, 1, 213, 227}

-- mathematicalSans-serifBoldCapitalQ UniversalString ::= {0, 1, 213, 228}

-- mathematicalSans-serifBoldCapitalR UniversalString ::= {0, 1, 213, 229}

-- mathematicalSans-serifBoldCapitalS UniversalString ::= {0, 1, 213, 230}

-- mathematicalSans-serifBoldCapitalT UniversalString ::= {0, 1, 213, 231}

-- mathematicalSans-serifBoldCapitalU UniversalString ::= {0, 1, 213, 232}

-- mathematicalSans-serifBoldCapitalV UniversalString ::= {0, 1, 213, 233}

-- mathematicalSans-serifBoldCapitalW UniversalString ::= {0, 1, 213, 234}

-- mathematicalSans-serifBoldCapitalX UniversalString ::= {0, 1, 213, 235}

-- mathematicalSans-serifBoldCapitalY UniversalString ::= {0, 1, 213, 236}

-- mathematicalSans-serifBoldCapitalZ UniversalString ::= {0, 1, 213, 237}

-- mathematicalSans-serifBoldSmallA UniversalString ::= {0, 1, 213, 238}

-- mathematicalSans-serifBoldSmallB UniversalString ::= {0, 1, 213, 239}

-- mathematicalSans-serifBoldSmallC UniversalString ::= {0, 1, 213, 240}

-- mathematicalSans-serifBoldSmallD UniversalString ::= {0, 1, 213, 241}

-- mathematicalSans-serifBoldSmallE UniversalString ::= {0, 1, 213, 242}

-- mathematicalSans-serifBoldSmallF UniversalString ::= {0, 1, 213, 243}

-- mathematicalSans-serifBoldSmallG UniversalString ::= {0, 1, 213, 244}

-- mathematicalSans-serifBoldSmallH UniversalString ::= {0, 1, 213, 245}

-- mathematicalSans-serifBoldSmallI UniversalString ::= {0, 1, 213, 246}

-- mathematicalSans-serifBoldSmallJ UniversalString ::= {0, 1, 213, 247}

-- mathematicalSans-serifBoldSmallK UniversalString ::= {0, 1, 213, 248}

-- mathematicalSans-serifBoldSmallL UniversalString ::= {0, 1, 213, 249}

-- mathematicalSans-serifBoldSmallM UniversalString ::= {0, 1, 213, 250}

-- mathematicalSans-serifBoldSmallN UniversalString ::= {0, 1, 213, 251}

-- mathematicalSans-serifBoldSmallO UniversalString ::= {0, 1, 213, 252}

-- mathematicalSans-serifBoldSmallP UniversalString ::= {0, 1, 213, 253}

-- mathematicalSans-serifBoldSmallQ UniversalString ::= {0, 1, 213, 254}

-- mathematicalSans-serifBoldSmallR UniversalString ::= {0, 1, 213, 255}

-- mathematicalSans-serifBoldSmallS UniversalString ::= {0, 1, 214, 0}

-- mathematicalSans-serifBoldSmallT UniversalString ::= {0, 1, 214, 1}

-- mathematicalSans-serifBoldSmallU UniversalString ::= {0, 1, 214, 2}

-- mathematicalSans-serifBoldSmallV UniversalString ::= {0, 1, 214, 3}

-- mathematicalSans-serifBoldSmallW UniversalString ::= {0, 1, 214, 4}

-- mathematicalSans-serifBoldSmallX UniversalString ::= {0, 1, 214, 5}

-- mathematicalSans-serifBoldSmallY UniversalString ::= {0, 1, 214, 6}

-- mathematicalSans-serifBoldSmallZ UniversalString ::= {0, 1, 214, 7}

-- mathematicalSans-serifItalicCapitalA UniversalString ::= {0, 1, 214, 8}

-- mathematicalSans-serifItalicCapitalB UniversalString ::= {0, 1, 214, 9}

-- mathematicalSans-serifItalicCapitalC UniversalString ::= {0, 1, 214, 10}

-- mathematicalSans-serifItalicCapitalD UniversalString ::= {0, 1, 214, 11}

-- mathematicalSans-serifItalicCapitalE UniversalString ::= {0, 1, 214, 12}

-- mathematicalSans-serifItalicCapitalF UniversalString ::= {0, 1, 214, 13}

-- mathematicalSans-serifItalicCapitalG UniversalString ::= {0, 1, 214, 14}

-- mathematicalSans-serifItalicCapitalH UniversalString ::= {0, 1, 214, 15}

-- mathematicalSans-serifItalicCapitalI UniversalString ::= {0, 1, 214, 16}

-- mathematicalSans-serifItalicCapitalJ UniversalString ::= {0, 1, 214, 17}

-- mathematicalSans-serifItalicCapitalK UniversalString ::= {0, 1, 214, 18}

-- mathematicalSans-serifItalicCapitalL UniversalString ::= {0, 1, 214, 19}

-- mathematicalSans-serifItalicCapitalM UniversalString ::= {0, 1, 214, 20}

-- mathematicalSans-serifItalicCapitalN UniversalString ::= {0, 1, 214, 21}

-- mathematicalSans-serifItalicCapitalO UniversalString ::= {0, 1, 214, 22}

-- mathematicalSans-serifItalicCapitalP UniversalString ::= {0, 1, 214, 23}

-- mathematicalSans-serifItalicCapitalQ UniversalString ::= {0, 1, 214, 24}

-- mathematicalSans-serifItalicCapitalR UniversalString ::= {0, 1, 214, 25}

-- mathematicalSans-serifItalicCapitalS UniversalString ::= {0, 1, 214, 26}

-- mathematicalSans-serifItalicCapitalT UniversalString ::= {0, 1, 214, 27}

-- mathematicalSans-serifItalicCapitalU UniversalString ::= {0, 1, 214, 28}

-- mathematicalSans-serifItalicCapitalV UniversalString ::= {0, 1, 214, 29}

-- mathematicalSans-serifItalicCapitalW UniversalString ::= {0, 1, 214, 30}

-- mathematicalSans-serifItalicCapitalX UniversalString ::= {0, 1, 214, 31}

-- mathematicalSans-serifItalicCapitalY UniversalString ::= {0, 1, 214, 32}

-- mathematicalSans-serifItalicCapitalZ UniversalString ::= {0, 1, 214, 33}

-- mathematicalSans-serifItalicSmallA UniversalString ::= {0, 1, 214, 34}

-- mathematicalSans-serifItalicSmallB UniversalString ::= {0, 1, 214, 35}

-- mathematicalSans-serifItalicSmallC UniversalString ::= {0, 1, 214, 36}

-- mathematicalSans-serifItalicSmallD UniversalString ::= {0, 1, 214, 37}

-- mathematicalSans-serifItalicSmallE UniversalString ::= {0, 1, 214, 38}

-- mathematicalSans-serifItalicSmallF UniversalString ::= {0, 1, 214, 39}

-- mathematicalSans-serifItalicSmallG UniversalString ::= {0, 1, 214, 40}

-- mathematicalSans-serifItalicSmallH UniversalString ::= {0, 1, 214, 41}

-- mathematicalSans-serifItalicSmallI UniversalString ::= {0, 1, 214, 42}

-- mathematicalSans-serifItalicSmallJ UniversalString ::= {0, 1, 214, 43}

-- mathematicalSans-serifItalicSmallK UniversalString ::= {0, 1, 214, 44}

-- mathematicalSans-serifItalicSmallL UniversalString ::= {0, 1, 214, 45}

-- mathematicalSans-serifItalicSmallM UniversalString ::= {0, 1, 214, 46}

-- mathematicalSans-serifItalicSmallN UniversalString ::= {0, 1, 214, 47}

-- mathematicalSans-serifItalicSmallO UniversalString ::= {0, 1, 214, 48}

-- mathematicalSans-serifItalicSmallP UniversalString ::= {0, 1, 214, 49}

-- mathematicalSans-serifItalicSmallQ UniversalString ::= {0, 1, 214, 50}

-- mathematicalSans-serifItalicSmallR UniversalString ::= {0, 1, 214, 51}

-- mathematicalSans-serifItalicSmallS UniversalString ::= {0, 1, 214, 52}

-- mathematicalSans-serifItalicSmallT UniversalString ::= {0, 1, 214, 53}

-- mathematicalSans-serifItalicSmallU UniversalString ::= {0, 1, 214, 54}

-- mathematicalSans-serifItalicSmallV UniversalString ::= {0, 1, 214, 55}

-- mathematicalSans-serifItalicSmallW UniversalString ::= {0, 1, 214, 56}

-- mathematicalSans-serifItalicSmallX UniversalString ::= {0, 1, 214, 57}

-- mathematicalSans-serifItalicSmallY UniversalString ::= {0, 1, 214, 58}

-- mathematicalSans-serifItalicSmallZ UniversalString ::= {0, 1, 214, 59}

-- mathematicalSans-serifBoldItalicCapitalA UniversalString ::= {0, 1, 214, 60}

-- mathematicalSans-serifBoldItalicCapitalB UniversalString ::= {0, 1, 214, 61}

-- mathematicalSans-serifBoldItalicCapitalC UniversalString ::= {0, 1, 214, 62}

-- mathematicalSans-serifBoldItalicCapitalD UniversalString ::= {0, 1, 214, 63}

-- mathematicalSans-serifBoldItalicCapitalE UniversalString ::= {0, 1, 214, 64}

-- mathematicalSans-serifBoldItalicCapitalF UniversalString ::= {0, 1, 214, 65}

-- mathematicalSans-serifBoldItalicCapitalG UniversalString ::= {0, 1, 214, 66}

-- mathematicalSans-serifBoldItalicCapitalH UniversalString ::= {0, 1, 214, 67}

-- mathematicalSans-serifBoldItalicCapitalI UniversalString ::= {0, 1, 214, 68}

-- mathematicalSans-serifBoldItalicCapitalJ UniversalString ::= {0, 1, 214, 69}

-- mathematicalSans-serifBoldItalicCapitalK UniversalString ::= {0, 1, 214, 70}

-- mathematicalSans-serifBoldItalicCapitalL UniversalString ::= {0, 1, 214, 71}

-- mathematicalSans-serifBoldItalicCapitalM UniversalString ::= {0, 1, 214, 72}

-- mathematicalSans-serifBoldItalicCapitalN UniversalString ::= {0, 1, 214, 73}

-- mathematicalSans-serifBoldItalicCapitalO UniversalString ::= {0, 1, 214, 74}

-- mathematicalSans-serifBoldItalicCapitalP UniversalString ::= {0, 1, 214, 75}

-- mathematicalSans-serifBoldItalicCapitalQ UniversalString ::= {0, 1, 214, 76}

-- mathematicalSans-serifBoldItalicCapitalR UniversalString ::= {0, 1, 214, 77}

-- mathematicalSans-serifBoldItalicCapitalS UniversalString ::= {0, 1, 214, 78}

-- mathematicalSans-serifBoldItalicCapitalT UniversalString ::= {0, 1, 214, 79}

-- mathematicalSans-serifBoldItalicCapitalU UniversalString ::= {0, 1, 214, 80}

-- mathematicalSans-serifBoldItalicCapitalV UniversalString ::= {0, 1, 214, 81}

-- mathematicalSans-serifBoldItalicCapitalW UniversalString ::= {0, 1, 214, 82}

-- mathematicalSans-serifBoldItalicCapitalX UniversalString ::= {0, 1, 214, 83}

-- mathematicalSans-serifBoldItalicCapitalY UniversalString ::= {0, 1, 214, 84}

-- mathematicalSans-serifBoldItalicCapitalZ UniversalString ::= {0, 1, 214, 85}

-- mathematicalSans-serifBoldItalicSmallA UniversalString ::= {0, 1, 214, 86}

-- mathematicalSans-serifBoldItalicSmallB UniversalString ::= {0, 1, 214, 87}

-- mathematicalSans-serifBoldItalicSmallC UniversalString ::= {0, 1, 214, 88}

-- mathematicalSans-serifBoldItalicSmallD UniversalString ::= {0, 1, 214, 89}

-- mathematicalSans-serifBoldItalicSmallE UniversalString ::= {0, 1, 214, 90}

-- mathematicalSans-serifBoldItalicSmallF UniversalString ::= {0, 1, 214, 91}

-- mathematicalSans-serifBoldItalicSmallG UniversalString ::= {0, 1, 214, 92}

-- mathematicalSans-serifBoldItalicSmallH UniversalString ::= {0, 1, 214, 93}

-- mathematicalSans-serifBoldItalicSmallI UniversalString ::= {0, 1, 214, 94}

-- mathematicalSans-serifBoldItalicSmallJ UniversalString ::= {0, 1, 214, 95}

-- mathematicalSans-serifBoldItalicSmallK UniversalString ::= {0, 1, 214, 96}

-- mathematicalSans-serifBoldItalicSmallL UniversalString ::= {0, 1, 214, 97}

-- mathematicalSans-serifBoldItalicSmallM UniversalString ::= {0, 1, 214, 98}

-- mathematicalSans-serifBoldItalicSmallN UniversalString ::= {0, 1, 214, 99}

-- mathematicalSans-serifBoldItalicSmallO UniversalString ::= {0, 1, 214, 100}

-- mathematicalSans-serifBoldItalicSmallP UniversalString ::= {0, 1, 214, 101}

-- mathematicalSans-serifBoldItalicSmallQ UniversalString ::= {0, 1, 214, 102}

-- mathematicalSans-serifBoldItalicSmallR UniversalString ::= {0, 1, 214, 103}

-- mathematicalSans-serifBoldItalicSmallS UniversalString ::= {0, 1, 214, 104}

-- mathematicalSans-serifBoldItalicSmallT UniversalString ::= {0, 1, 214, 105}

-- mathematicalSans-serifBoldItalicSmallU UniversalString ::= {0, 1, 214, 106}

-- mathematicalSans-serifBoldItalicSmallV UniversalString ::= {0, 1, 214, 107}

-- mathematicalSans-serifBoldItalicSmallW UniversalString ::= {0, 1, 214, 108}

-- mathematicalSans-serifBoldItalicSmallX UniversalString ::= {0, 1, 214, 109}

-- mathematicalSans-serifBoldItalicSmallY UniversalString ::= {0, 1, 214, 110}

-- mathematicalSans-serifBoldItalicSmallZ UniversalString ::= {0, 1, 214, 111}

-- mathematicalMonospaceCapitalA UniversalString ::= {0, 1, 214, 112}

-- mathematicalMonospaceCapitalB UniversalString ::= {0, 1, 214, 113}

-- mathematicalMonospaceCapitalC UniversalString ::= {0, 1, 214, 114}

-- mathematicalMonospaceCapitalD UniversalString ::= {0, 1, 214, 115}

-- mathematicalMonospaceCapitalE UniversalString ::= {0, 1, 214, 116}

-- mathematicalMonospaceCapitalF UniversalString ::= {0, 1, 214, 117}

-- mathematicalMonospaceCapitalG UniversalString ::= {0, 1, 214, 118}

-- mathematicalMonospaceCapitalH UniversalString ::= {0, 1, 214, 119}

-- mathematicalMonospaceCapitalI UniversalString ::= {0, 1, 214, 120}

-- mathematicalMonospaceCapitalJ UniversalString ::= {0, 1, 214, 121}

-- mathematicalMonospaceCapitalK UniversalString ::= {0, 1, 214, 122}

-- mathematicalMonospaceCapitalL UniversalString ::= {0, 1, 214, 123}

-- mathematicalMonospaceCapitalM UniversalString ::= {0, 1, 214, 124}

-- mathematicalMonospaceCapitalN UniversalString ::= {0, 1, 214, 125}

-- mathematicalMonospaceCapitalO UniversalString ::= {0, 1, 214, 126}

-- mathematicalMonospaceCapitalP UniversalString ::= {0, 1, 214, 127}

-- mathematicalMonospaceCapitalQ UniversalString ::= {0, 1, 214, 128}

-- mathematicalMonospaceCapitalR UniversalString ::= {0, 1, 214, 129}

-- mathematicalMonospaceCapitalS UniversalString ::= {0, 1, 214, 130}

-- mathematicalMonospaceCapitalT UniversalString ::= {0, 1, 214, 131}

-- mathematicalMonospaceCapitalU UniversalString ::= {0, 1, 214, 132}

-- mathematicalMonospaceCapitalV UniversalString ::= {0, 1, 214, 133}

-- mathematicalMonospaceCapitalW UniversalString ::= {0, 1, 214, 134}

-- mathematicalMonospaceCapitalX UniversalString ::= {0, 1, 214, 135}

-- mathematicalMonospaceCapitalY UniversalString ::= {0, 1, 214, 136}

-- mathematicalMonospaceCapitalZ UniversalString ::= {0, 1, 214, 137}

-- mathematicalMonospaceSmallA UniversalString ::= {0, 1, 214, 138}

-- mathematicalMonospaceSmallB UniversalString ::= {0, 1, 214, 139}

-- mathematicalMonospaceSmallC UniversalString ::= {0, 1, 214, 140}

-- mathematicalMonospaceSmallD UniversalString ::= {0, 1, 214, 141}

-- mathematicalMonospaceSmallE UniversalString ::= {0, 1, 214, 142}

-- mathematicalMonospaceSmallF UniversalString ::= {0, 1, 214, 143}

-- mathematicalMonospaceSmallG UniversalString ::= {0, 1, 214, 144}

-- mathematicalMonospaceSmallH UniversalString ::= {0, 1, 214, 145}

-- mathematicalMonospaceSmallI UniversalString ::= {0, 1, 214, 146}

-- mathematicalMonospaceSmallJ UniversalString ::= {0, 1, 214, 147}

-- mathematicalMonospaceSmallK UniversalString ::= {0, 1, 214, 148}

-- mathematicalMonospaceSmallL UniversalString ::= {0, 1, 214, 149}

-- mathematicalMonospaceSmallM UniversalString ::= {0, 1, 214, 150}

-- mathematicalMonospaceSmallN UniversalString ::= {0, 1, 214, 151}

-- mathematicalMonospaceSmallO UniversalString ::= {0, 1, 214, 152}

-- mathematicalMonospaceSmallP UniversalString ::= {0, 1, 214, 153}

-- mathematicalMonospaceSmallQ UniversalString ::= {0, 1, 214, 154}

-- mathematicalMonospaceSmallR UniversalString ::= {0, 1, 214, 155}

-- mathematicalMonospaceSmallS UniversalString ::= {0, 1, 214, 156}

-- mathematicalMonospaceSmallT UniversalString ::= {0, 1, 214, 157}

-- mathematicalMonospaceSmallU UniversalString ::= {0, 1, 214, 158}

-- mathematicalMonospaceSmallV UniversalString ::= {0, 1, 214, 159}

-- mathematicalMonospaceSmallW UniversalString ::= {0, 1, 214, 160}

-- mathematicalMonospaceSmallX UniversalString ::= {0, 1, 214, 161}

-- mathematicalMonospaceSmallY UniversalString ::= {0, 1, 214, 162}

-- mathematicalMonospaceSmallZ UniversalString ::= {0, 1, 214, 163}

-- mathematicalBoldCapitalAlpha UniversalString ::= {0, 1, 214, 168}

-- mathematicalBoldCapitalBeta UniversalString ::= {0, 1, 214, 169}

-- mathematicalBoldCapitalGamma UniversalString ::= {0, 1, 214, 170}

-- mathematicalBoldCapitalDelta UniversalString ::= {0, 1, 214, 171}

-- mathematicalBoldCapitalEpsilon UniversalString ::= {0, 1, 214, 172}

-- mathematicalBoldCapitalZeta UniversalString ::= {0, 1, 214, 173}

-- mathematicalBoldCapitalEta UniversalString ::= {0, 1, 214, 174}

-- mathematicalBoldCapitalTheta UniversalString ::= {0, 1, 214, 175}

-- mathematicalBoldCapitalIota UniversalString ::= {0, 1, 214, 176}

-- mathematicalBoldCapitalKappa UniversalString ::= {0, 1, 214, 177}

-- mathematicalBoldCapitalLamda UniversalString ::= {0, 1, 214, 178}

-- mathematicalBoldCapitalMu UniversalString ::= {0, 1, 214, 179}

-- mathematicalBoldCapitalNu UniversalString ::= {0, 1, 214, 180}

-- mathematicalBoldCapitalXi UniversalString ::= {0, 1, 214, 181}

-- mathematicalBoldCapitalOmicron UniversalString ::= {0, 1, 214, 182}

-- mathematicalBoldCapitalPi UniversalString ::= {0, 1, 214, 183}

-- mathematicalBoldCapitalRho UniversalString ::= {0, 1, 214, 184}

-- mathematicalBoldCapitalThetaSymbol UniversalString ::= {0, 1, 214, 185}

-- mathematicalBoldCapitalSigma UniversalString ::= {0, 1, 214, 186}

-- mathematicalBoldCapitalTau UniversalString ::= {0, 1, 214, 187}

-- mathematicalBoldCapitalUpsilon UniversalString ::= {0, 1, 214, 188}

-- mathematicalBoldCapitalPhi UniversalString ::= {0, 1, 214, 189}

-- mathematicalBoldCapitalChi UniversalString ::= {0, 1, 214, 190}

-- mathematicalBoldCapitalPsi UniversalString ::= {0, 1, 214, 191}

-- mathematicalBoldCapitalOmega UniversalString ::= {0, 1, 214, 192}

-- mathematicalBoldNabla UniversalString ::= {0, 1, 214, 193}

-- mathematicalBoldSmallAlpha UniversalString ::= {0, 1, 214, 194}

-- mathematicalBoldSmallBeta UniversalString ::= {0, 1, 214, 195}

-- mathematicalBoldSmallGamma UniversalString ::= {0, 1, 214, 196}

-- mathematicalBoldSmallDelta UniversalString ::= {0, 1, 214, 197}

-- mathematicalBoldSmallEpsilon UniversalString ::= {0, 1, 214, 198}

-- mathematicalBoldSmallZeta UniversalString ::= {0, 1, 214, 199}

-- mathematicalBoldSmallEta UniversalString ::= {0, 1, 214, 200}

-- mathematicalBoldSmallTheta UniversalString ::= {0, 1, 214, 201}

-- mathematicalBoldSmallIota UniversalString ::= {0, 1, 214, 202}

-- mathematicalBoldSmallKappa UniversalString ::= {0, 1, 214, 203}

-- mathematicalBoldSmallLamda UniversalString ::= {0, 1, 214, 204}

-- mathematicalBoldSmallMu UniversalString ::= {0, 1, 214, 205}

-- mathematicalBoldSmallNu UniversalString ::= {0, 1, 214, 206}

-- mathematicalBoldSmallXi UniversalString ::= {0, 1, 214, 207}

-- mathematicalBoldSmallOmicron UniversalString ::= {0, 1, 214, 208}

-- mathematicalBoldSmallPi UniversalString ::= {0, 1, 214, 209}

-- mathematicalBoldSmallRho UniversalString ::= {0, 1, 214, 210}

-- mathematicalBoldSmallFinalSigma UniversalString ::= {0, 1, 214, 211}

-- mathematicalBoldSmallSigma UniversalString ::= {0, 1, 214, 212}

-- mathematicalBoldSmallTau UniversalString ::= {0, 1, 214, 213}

-- mathematicalBoldSmallUpsilon UniversalString ::= {0, 1, 214, 214}

-- mathematicalBoldSmallPhi UniversalString ::= {0, 1, 214, 215}

-- mathematicalBoldSmallChi UniversalString ::= {0, 1, 214, 216}

-- mathematicalBoldSmallPsi UniversalString ::= {0, 1, 214, 217}

-- mathematicalBoldSmallOmega UniversalString ::= {0, 1, 214, 218}

-- mathematicalBoldPartialDifferential UniversalString ::= {0, 1, 214, 219}

-- mathematicalBoldEpsilonSymbol UniversalString ::= {0, 1, 214, 220}

-- mathematicalBoldThetaSymbol UniversalString ::= {0, 1, 214, 221}

-- mathematicalBoldKappaSymbol UniversalString ::= {0, 1, 214, 222}

-- mathematicalBoldPhiSymbol UniversalString ::= {0, 1, 214, 223}

-- mathematicalBoldRhoSymbol UniversalString ::= {0, 1, 214, 224}

-- mathematicalBoldPiSymbol UniversalString ::= {0, 1, 214, 225}

-- mathematicalItalicCapitalAlpha UniversalString ::= {0, 1, 214, 226}

-- mathematicalItalicCapitalBeta UniversalString ::= {0, 1, 214, 227}

-- mathematicalItalicCapitalGamma UniversalString ::= {0, 1, 214, 228}

-- mathematicalItalicCapitalDelta UniversalString ::= {0, 1, 214, 229}

-- mathematicalItalicCapitalEpsilon UniversalString ::= {0, 1, 214, 230}

-- mathematicalItalicCapitalZeta UniversalString ::= {0, 1, 214, 231}

-- mathematicalItalicCapitalEta UniversalString ::= {0, 1, 214, 232}

-- mathematicalItalicCapitalTheta UniversalString ::= {0, 1, 214, 233}

-- mathematicalItalicCapitalIota UniversalString ::= {0, 1, 214, 234}

-- mathematicalItalicCapitalKappa UniversalString ::= {0, 1, 214, 235}

-- mathematicalItalicCapitalLamda UniversalString ::= {0, 1, 214, 236}

-- mathematicalItalicCapitalMu UniversalString ::= {0, 1, 214, 237}

-- mathematicalItalicCapitalNu UniversalString ::= {0, 1, 214, 238}

-- mathematicalItalicCapitalXi UniversalString ::= {0, 1, 214, 239}

-- mathematicalItalicCapitalOmicron UniversalString ::= {0, 1, 214, 240}

-- mathematicalItalicCapitalPi UniversalString ::= {0, 1, 214, 241}

-- mathematicalItalicCapitalRho UniversalString ::= {0, 1, 214, 242}

-- mathematicalItalicCapitalThetaSymbol UniversalString ::= {0, 1, 214, 243}

-- mathematicalItalicCapitalSigma UniversalString ::= {0, 1, 214, 244}

-- mathematicalItalicCapitalTau UniversalString ::= {0, 1, 214, 245}

-- mathematicalItalicCapitalUpsilon UniversalString ::= {0, 1, 214, 246}

-- mathematicalItalicCapitalPhi UniversalString ::= {0, 1, 214, 247}

-- mathematicalItalicCapitalChi UniversalString ::= {0, 1, 214, 248}

-- mathematicalItalicCapitalPsi UniversalString ::= {0, 1, 214, 249}

-- mathematicalItalicCapitalOmega UniversalString ::= {0, 1, 214, 250}

-- mathematicalItalicNabla UniversalString ::= {0, 1, 214, 251}

-- mathematicalItalicSmallAlpha UniversalString ::= {0, 1, 214, 252}

-- mathematicalItalicSmallBeta UniversalString ::= {0, 1, 214, 253}

-- mathematicalItalicSmallGamma UniversalString ::= {0, 1, 214, 254}

-- mathematicalItalicSmallDelta UniversalString ::= {0, 1, 214, 255}

-- mathematicalItalicSmallEpsilon UniversalString ::= {0, 1, 215, 0}

-- mathematicalItalicSmallZeta UniversalString ::= {0, 1, 215, 1}

-- mathematicalItalicSmallEta UniversalString ::= {0, 1, 215, 2}

-- mathematicalItalicSmallTheta UniversalString ::= {0, 1, 215, 3}

-- mathematicalItalicSmallIota UniversalString ::= {0, 1, 215, 4}

-- mathematicalItalicSmallKappa UniversalString ::= {0, 1, 215, 5}

-- mathematicalItalicSmallLamda UniversalString ::= {0, 1, 215, 6}

-- mathematicalItalicSmallMu UniversalString ::= {0, 1, 215, 7}

-- mathematicalItalicSmallNu UniversalString ::= {0, 1, 215, 8}

-- mathematicalItalicSmallXi UniversalString ::= {0, 1, 215, 9}

-- mathematicalItalicSmallOmicron UniversalString ::= {0, 1, 215, 10}

-- mathematicalItalicSmallPi UniversalString ::= {0, 1, 215, 11}

-- mathematicalItalicSmallRho UniversalString ::= {0, 1, 215, 12}

-- mathematicalItalicSmallFinalSigma UniversalString ::= {0, 1, 215, 13}

-- mathematicalItalicSmallSigma UniversalString ::= {0, 1, 215, 14}

-- mathematicalItalicSmallTau UniversalString ::= {0, 1, 215, 15}

-- mathematicalItalicSmallUpsilon UniversalString ::= {0, 1, 215, 16}

-- mathematicalItalicSmallPhi UniversalString ::= {0, 1, 215, 17}

-- mathematicalItalicSmallChi UniversalString ::= {0, 1, 215, 18}

-- mathematicalItalicSmallPsi UniversalString ::= {0, 1, 215, 19}

-- mathematicalItalicSmallOmega UniversalString ::= {0, 1, 215, 20}

-- mathematicalItalicPartialDifferential UniversalString ::= {0, 1, 215, 21}

-- mathematicalItalicEpsilonSymbol UniversalString ::= {0, 1, 215, 22}

-- mathematicalItalicThetaSymbol UniversalString ::= {0, 1, 215, 23}

-- mathematicalItalicKappaSymbol UniversalString ::= {0, 1, 215, 24}

-- mathematicalItalicPhiSymbol UniversalString ::= {0, 1, 215, 25}

-- mathematicalItalicRhoSymbol UniversalString ::= {0, 1, 215, 26}

-- mathematicalItalicPiSymbol UniversalString ::= {0, 1, 215, 27}

-- mathematicalBoldItalicCapitalAlpha UniversalString ::= {0, 1, 215, 28}

-- mathematicalBoldItalicCapitalBeta UniversalString ::= {0, 1, 215, 29}

-- mathematicalBoldItalicCapitalGamma UniversalString ::= {0, 1, 215, 30}

-- mathematicalBoldItalicCapitalDelta UniversalString ::= {0, 1, 215, 31}

-- mathematicalBoldItalicCapitalEpsilon UniversalString ::= {0, 1, 215, 32}

-- mathematicalBoldItalicCapitalZeta UniversalString ::= {0, 1, 215, 33}

-- mathematicalBoldItalicCapitalEta UniversalString ::= {0, 1, 215, 34}

-- mathematicalBoldItalicCapitalTheta UniversalString ::= {0, 1, 215, 35}

-- mathematicalBoldItalicCapitalIota UniversalString ::= {0, 1, 215, 36}

-- mathematicalBoldItalicCapitalKappa UniversalString ::= {0, 1, 215, 37}

-- mathematicalBoldItalicCapitalLamda UniversalString ::= {0, 1, 215, 38}

-- mathematicalBoldItalicCapitalMu UniversalString ::= {0, 1, 215, 39}

-- mathematicalBoldItalicCapitalNu UniversalString ::= {0, 1, 215, 40}

-- mathematicalBoldItalicCapitalXi UniversalString ::= {0, 1, 215, 41}

-- mathematicalBoldItalicCapitalOmicron UniversalString ::= {0, 1, 215, 42}

-- mathematicalBoldItalicCapitalPi UniversalString ::= {0, 1, 215, 43}

-- mathematicalBoldItalicCapitalRho UniversalString ::= {0, 1, 215, 44}

-- mathematicalBoldItalicCapitalThetaSymbol UniversalString ::= {0, 1, 215, 45}

-- mathematicalBoldItalicCapitalSigma UniversalString ::= {0, 1, 215, 46}

-- mathematicalBoldItalicCapitalTau UniversalString ::= {0, 1, 215, 47}

-- mathematicalBoldItalicCapitalUpsilon UniversalString ::= {0, 1, 215, 48}

-- mathematicalBoldItalicCapitalPhi UniversalString ::= {0, 1, 215, 49}

-- mathematicalBoldItalicCapitalChi UniversalString ::= {0, 1, 215, 50}

-- mathematicalBoldItalicCapitalPsi UniversalString ::= {0, 1, 215, 51}

-- mathematicalBoldItalicCapitalOmega UniversalString ::= {0, 1, 215, 52}

-- mathematicalBoldItalicNabla UniversalString ::= {0, 1, 215, 53}

-- mathematicalBoldItalicSmallAlpha UniversalString ::= {0, 1, 215, 54}

-- mathematicalBoldItalicSmallBeta UniversalString ::= {0, 1, 215, 55}

-- mathematicalBoldItalicSmallGamma UniversalString ::= {0, 1, 215, 56}

-- mathematicalBoldItalicSmallDelta UniversalString ::= {0, 1, 215, 57}

-- mathematicalBoldItalicSmallEpsilon UniversalString ::= {0, 1, 215, 58}

-- mathematicalBoldItalicSmallZeta UniversalString ::= {0, 1, 215, 59}

-- mathematicalBoldItalicSmallEta UniversalString ::= {0, 1, 215, 60}

-- mathematicalBoldItalicSmallTheta UniversalString ::= {0, 1, 215, 61}

-- mathematicalBoldItalicSmallIota UniversalString ::= {0, 1, 215, 62}

-- mathematicalBoldItalicSmallKappa UniversalString ::= {0, 1, 215, 63}

-- mathematicalBoldItalicSmallLamda UniversalString ::= {0, 1, 215, 64}

-- mathematicalBoldItalicSmallMu UniversalString ::= {0, 1, 215, 65}

-- mathematicalBoldItalicSmallNu UniversalString ::= {0, 1, 215, 66}

-- mathematicalBoldItalicSmallXi UniversalString ::= {0, 1, 215, 67}

-- mathematicalBoldItalicSmallOmicron UniversalString ::= {0, 1, 215, 68}

-- mathematicalBoldItalicSmallPi UniversalString ::= {0, 1, 215, 69}

-- mathematicalBoldItalicSmallRho UniversalString ::= {0, 1, 215, 70}

-- mathematicalBoldItalicSmallFinalSigma UniversalString ::= {0, 1, 215, 71}

-- mathematicalBoldItalicSmallSigma UniversalString ::= {0, 1, 215, 72}

-- mathematicalBoldItalicSmallTau UniversalString ::= {0, 1, 215, 73}

-- mathematicalBoldItalicSmallUpsilon UniversalString ::= {0, 1, 215, 74}

-- mathematicalBoldItalicSmallPhi UniversalString ::= {0, 1, 215, 75}

-- mathematicalBoldItalicSmallChi UniversalString ::= {0, 1, 215, 76}

-- mathematicalBoldItalicSmallPsi UniversalString ::= {0, 1, 215, 77}

-- mathematicalBoldItalicSmallOmega UniversalString ::= {0, 1, 215, 78}

-- mathematicalBoldItalicPartialDifferential UniversalString ::= {0, 1, 215, 79}

-- mathematicalBoldItalicEpsilonSymbol UniversalString ::= {0, 1, 215, 80}

-- mathematicalBoldItalicThetaSymbol UniversalString ::= {0, 1, 215, 81}

-- mathematicalBoldItalicKappaSymbol UniversalString ::= {0, 1, 215, 82}

-- mathematicalBoldItalicPhiSymbol UniversalString ::= {0, 1, 215, 83}

-- mathematicalBoldItalicRhoSymbol UniversalString ::= {0, 1, 215, 84}

-- mathematicalBoldItalicPiSymbol UniversalString ::= {0, 1, 215, 85}

-- mathematicalSans-serifBoldCapitalAlpha UniversalString ::= {0, 1, 215, 86}

-- mathematicalSans-serifBoldCapitalBeta UniversalString ::= {0, 1, 215, 87}

-- mathematicalSans-serifBoldCapitalGamma UniversalString ::= {0, 1, 215, 88}

-- mathematicalSans-serifBoldCapitalDelta UniversalString ::= {0, 1, 215, 89}

-- mathematicalSans-serifBoldCapitalEpsilon UniversalString ::= {0, 1, 215, 90}

-- mathematicalSans-serifBoldCapitalZeta UniversalString ::= {0, 1, 215, 91}

-- mathematicalSans-serifBoldCapitalEta UniversalString ::= {0, 1, 215, 92}

-- mathematicalSans-serifBoldCapitalTheta UniversalString ::= {0, 1, 215, 93}

-- mathematicalSans-serifBoldCapitalIota UniversalString ::= {0, 1, 215, 94}

-- mathematicalSans-serifBoldCapitalKappa UniversalString ::= {0, 1, 215, 95}

-- mathematicalSans-serifBoldCapitalLamda UniversalString ::= {0, 1, 215, 96}

-- mathematicalSans-serifBoldCapitalMu UniversalString ::= {0, 1, 215, 97}

-- mathematicalSans-serifBoldCapitalNu UniversalString ::= {0, 1, 215, 98}

-- mathematicalSans-serifBoldCapitalXi UniversalString ::= {0, 1, 215, 99}

-- mathematicalSans-serifBoldCapitalOmicron UniversalString ::= {0, 1, 215, 100}

-- mathematicalSans-serifBoldCapitalPi UniversalString ::= {0, 1, 215, 101}

-- mathematicalSans-serifBoldCapitalRho UniversalString ::= {0, 1, 215, 102}

-- mathematicalSans-serifBoldCapitalThetaSymbol UniversalString ::=
--   {0, 1, 215, 103}

-- mathematicalSans-serifBoldCapitalSigma UniversalString ::= {0, 1, 215, 104}

-- mathematicalSans-serifBoldCapitalTau UniversalString ::= {0, 1, 215, 105}

-- mathematicalSans-serifBoldCapitalUpsilon UniversalString ::= {0, 1, 215, 106}

-- mathematicalSans-serifBoldCapitalPhi UniversalString ::= {0, 1, 215, 107}

-- mathematicalSans-serifBoldCapitalChi UniversalString ::= {0, 1, 215, 108}

-- mathematicalSans-serifBoldCapitalPsi UniversalString ::= {0, 1, 215, 109}

-- mathematicalSans-serifBoldCapitalOmega UniversalString ::= {0, 1, 215, 110}

-- mathematicalSans-serifBoldNabla UniversalString ::= {0, 1, 215, 111}

-- mathematicalSans-serifBoldSmallAlpha UniversalString ::= {0, 1, 215, 112}

-- mathematicalSans-serifBoldSmallBeta UniversalString ::= {0, 1, 215, 113}

-- mathematicalSans-serifBoldSmallGamma UniversalString ::= {0, 1, 215, 114}

-- mathematicalSans-serifBoldSmallDelta UniversalString ::= {0, 1, 215, 115}

-- mathematicalSans-serifBoldSmallEpsilon UniversalString ::= {0, 1, 215, 116}

-- mathematicalSans-serifBoldSmallZeta UniversalString ::= {0, 1, 215, 117}

-- mathematicalSans-serifBoldSmallEta UniversalString ::= {0, 1, 215, 118}

-- mathematicalSans-serifBoldSmallTheta UniversalString ::= {0, 1, 215, 119}

-- mathematicalSans-serifBoldSmallIota UniversalString ::= {0, 1, 215, 120}

-- mathematicalSans-serifBoldSmallKappa UniversalString ::= {0, 1, 215, 121}

-- mathematicalSans-serifBoldSmallLamda UniversalString ::= {0, 1, 215, 122}

-- mathematicalSans-serifBoldSmallMu UniversalString ::= {0, 1, 215, 123}

-- mathematicalSans-serifBoldSmallNu UniversalString ::= {0, 1, 215, 124}

-- mathematicalSans-serifBoldSmallXi UniversalString ::= {0, 1, 215, 125}

-- mathematicalSans-serifBoldSmallOmicron UniversalString ::= {0, 1, 215, 126}

-- mathematicalSans-serifBoldSmallPi UniversalString ::= {0, 1, 215, 127}

-- mathematicalSans-serifBoldSmallRho UniversalString ::= {0, 1, 215, 128}

-- mathematicalSans-serifBoldSmallFinalSigma UniversalString ::= {0, 1, 215, 129}

-- mathematicalSans-serifBoldSmallSigma UniversalString ::= {0, 1, 215, 130}

-- mathematicalSans-serifBoldSmallTau UniversalString ::= {0, 1, 215, 131}

-- mathematicalSans-serifBoldSmallUpsilon UniversalString ::= {0, 1, 215, 132}

-- mathematicalSans-serifBoldSmallPhi UniversalString ::= {0, 1, 215, 133}

-- mathematicalSans-serifBoldSmallChi UniversalString ::= {0, 1, 215, 134}

-- mathematicalSans-serifBoldSmallPsi UniversalString ::= {0, 1, 215, 135}

-- mathematicalSans-serifBoldSmallOmega UniversalString ::= {0, 1, 215, 136}

-- mathematicalSans-serifBoldPartialDifferential UniversalString ::=
--   {0, 1, 215, 137}

-- mathematicalSans-serifBoldEpsilonSymbol UniversalString ::= {0, 1, 215, 138}

-- mathematicalSans-serifBoldThetaSymbol UniversalString ::= {0, 1, 215, 139}

-- mathematicalSans-serifBoldKappaSymbol UniversalString ::= {0, 1, 215, 140}

-- mathematicalSans-serifBoldPhiSymbol UniversalString ::= {0, 1, 215, 141}

-- mathematicalSans-serifBoldRhoSymbol UniversalString ::= {0, 1, 215, 142}

-- mathematicalSans-serifBoldPiSymbol UniversalString ::= {0, 1, 215, 143}

-- mathematicalSans-serifBoldItalicCapitalAlpha UniversalString ::=
--   {0, 1, 215, 144}

-- mathematicalSans-serifBoldItalicCapitalBeta UniversalString ::=
--   {0, 1, 215, 145}

-- mathematicalSans-serifBoldItalicCapitalGamma UniversalString ::=
--   {0, 1, 215, 146}

-- mathematicalSans-serifBoldItalicCapitalDelta UniversalString ::=
--   {0, 1, 215, 147}

-- mathematicalSans-serifBoldItalicCapitalEpsilon UniversalString ::=
--   {0, 1, 215, 148}

-- mathematicalSans-serifBoldItalicCapitalZeta UniversalString ::=
--   {0, 1, 215, 149}

-- mathematicalSans-serifBoldItalicCapitalEta UniversalString ::= {0, 1, 215, 150}

-- mathematicalSans-serifBoldItalicCapitalTheta UniversalString ::=
--   {0, 1, 215, 151}

-- mathematicalSans-serifBoldItalicCapitalIota UniversalString ::=
--   {0, 1, 215, 152}

-- mathematicalSans-serifBoldItalicCapitalKappa UniversalString ::=
--   {0, 1, 215, 153}

-- mathematicalSans-serifBoldItalicCapitalLamda UniversalString ::=
--   {0, 1, 215, 154}

-- mathematicalSans-serifBoldItalicCapitalMu UniversalString ::= {0, 1, 215, 155}

-- mathematicalSans-serifBoldItalicCapitalNu UniversalString ::= {0, 1, 215, 156}

-- mathematicalSans-serifBoldItalicCapitalXi UniversalString ::= {0, 1, 215, 157}

-- mathematicalSans-serifBoldItalicCapitalOmicron UniversalString ::=
--   {0, 1, 215, 158}

-- mathematicalSans-serifBoldItalicCapitalPi UniversalString ::= {0, 1, 215, 159}

-- mathematicalSans-serifBoldItalicCapitalRho UniversalString ::= {0, 1, 215, 160}

-- mathematicalSans-serifBoldItalicCapitalThetaSymbol UniversalString ::=
--   {0, 1, 215, 161}

-- mathematicalSans-serifBoldItalicCapitalSigma UniversalString ::=
--   {0, 1, 215, 162}

-- mathematicalSans-serifBoldItalicCapitalTau UniversalString ::= {0, 1, 215, 163}

-- mathematicalSans-serifBoldItalicCapitalUpsilon UniversalString ::=
--   {0, 1, 215, 164}

-- mathematicalSans-serifBoldItalicCapitalPhi UniversalString ::= {0, 1, 215, 165}

-- mathematicalSans-serifBoldItalicCapitalChi UniversalString ::= {0, 1, 215, 166}

-- mathematicalSans-serifBoldItalicCapitalPsi UniversalString ::= {0, 1, 215, 167}

-- mathematicalSans-serifBoldItalicCapitalOmega UniversalString ::=
--   {0, 1, 215, 168}

-- mathematicalSans-serifBoldItalicNabla UniversalString ::= {0, 1, 215, 169}

-- mathematicalSans-serifBoldItalicSmallAlpha UniversalString ::= {0, 1, 215, 170}

-- mathematicalSans-serifBoldItalicSmallBeta UniversalString ::= {0, 1, 215, 171}

-- mathematicalSans-serifBoldItalicSmallGamma UniversalString ::= {0, 1, 215, 172}

-- mathematicalSans-serifBoldItalicSmallDelta UniversalString ::= {0, 1, 215, 173}

-- mathematicalSans-serifBoldItalicSmallEpsilon UniversalString ::=
--   {0, 1, 215, 174}

-- mathematicalSans-serifBoldItalicSmallZeta UniversalString ::= {0, 1, 215, 175}

-- mathematicalSans-serifBoldItalicSmallEta UniversalString ::= {0, 1, 215, 176}

-- mathematicalSans-serifBoldItalicSmallTheta UniversalString ::= {0, 1, 215, 177}

-- mathematicalSans-serifBoldItalicSmallIota UniversalString ::= {0, 1, 215, 178}

-- mathematicalSans-serifBoldItalicSmallKappa UniversalString ::= {0, 1, 215, 179}

-- mathematicalSans-serifBoldItalicSmallLamda UniversalString ::= {0, 1, 215, 180}

-- mathematicalSans-serifBoldItalicSmallMu UniversalString ::= {0, 1, 215, 181}

-- mathematicalSans-serifBoldItalicSmallNu UniversalString ::= {0, 1, 215, 182}

-- mathematicalSans-serifBoldItalicSmallXi UniversalString ::= {0, 1, 215, 183}

-- mathematicalSans-serifBoldItalicSmallOmicron UniversalString ::=
--   {0, 1, 215, 184}

-- mathematicalSans-serifBoldItalicSmallPi UniversalString ::= {0, 1, 215, 185}

-- mathematicalSans-serifBoldItalicSmallRho UniversalString ::= {0, 1, 215, 186}

-- mathematicalSans-serifBoldItalicSmallFinalSigma UniversalString ::=
--   {0, 1, 215, 187}

-- mathematicalSans-serifBoldItalicSmallSigma UniversalString ::= {0, 1, 215, 188}

-- mathematicalSans-serifBoldItalicSmallTau UniversalString ::= {0, 1, 215, 189}

-- mathematicalSans-serifBoldItalicSmallUpsilon UniversalString ::=
--   {0, 1, 215, 190}

-- mathematicalSans-serifBoldItalicSmallPhi UniversalString ::= {0, 1, 215, 191}

-- mathematicalSans-serifBoldItalicSmallChi UniversalString ::= {0, 1, 215, 192}

-- mathematicalSans-serifBoldItalicSmallPsi UniversalString ::= {0, 1, 215, 193}

-- mathematicalSans-serifBoldItalicSmallOmega UniversalString ::= {0, 1, 215, 194}

-- mathematicalSans-serifBoldItalicPartialDifferential UniversalString ::=
--   {0, 1, 215, 195}

-- mathematicalSans-serifBoldItalicEpsilonSymbol UniversalString ::=
--   {0, 1, 215, 196}

-- mathematicalSans-serifBoldItalicThetaSymbol UniversalString ::=
--   {0, 1, 215, 197}

-- mathematicalSans-serifBoldItalicKappaSymbol UniversalString ::=
--   {0, 1, 215, 198}

-- mathematicalSans-serifBoldItalicPhiSymbol UniversalString ::= {0, 1, 215, 199}

-- mathematicalSans-serifBoldItalicRhoSymbol UniversalString ::= {0, 1, 215, 200}

-- mathematicalSans-serifBoldItalicPiSymbol UniversalString ::= {0, 1, 215, 201}

-- mathematicalBoldDigitZero UniversalString ::= {0, 1, 215, 206}

-- mathematicalBoldDigitOne UniversalString ::= {0, 1, 215, 207}

-- mathematicalBoldDigitTwo UniversalString ::= {0, 1, 215, 208}

-- mathematicalBoldDigitThree UniversalString ::= {0, 1, 215, 209}

-- mathematicalBoldDigitFour UniversalString ::= {0, 1, 215, 210}

-- mathematicalBoldDigitFive UniversalString ::= {0, 1, 215, 211}

-- mathematicalBoldDigitSix UniversalString ::= {0, 1, 215, 212}

-- mathematicalBoldDigitSeven UniversalString ::= {0, 1, 215, 213}

-- mathematicalBoldDigitEight UniversalString ::= {0, 1, 215, 214}

-- mathematicalBoldDigitNine UniversalString ::= {0, 1, 215, 215}

-- mathematicalDouble-struckDigitZero UniversalString ::= {0, 1, 215, 216}

-- mathematicalDouble-struckDigitOne UniversalString ::= {0, 1, 215, 217}

-- mathematicalDouble-struckDigitTwo UniversalString ::= {0, 1, 215, 218}

-- mathematicalDouble-struckDigitThree UniversalString ::= {0, 1, 215, 219}

-- mathematicalDouble-struckDigitFour UniversalString ::= {0, 1, 215, 220}

-- mathematicalDouble-struckDigitFive UniversalString ::= {0, 1, 215, 221}

-- mathematicalDouble-struckDigitSix UniversalString ::= {0, 1, 215, 222}

-- mathematicalDouble-struckDigitSeven UniversalString ::= {0, 1, 215, 223}

-- mathematicalDouble-struckDigitEight UniversalString ::= {0, 1, 215, 224}

-- mathematicalDouble-struckDigitNine UniversalString ::= {0, 1, 215, 225}

-- mathematicalSans-serifDigitZero UniversalString ::= {0, 1, 215, 226}

-- mathematicalSans-serifDigitOne UniversalString ::= {0, 1, 215, 227}

-- mathematicalSans-serifDigitTwo UniversalString ::= {0, 1, 215, 228}

-- mathematicalSans-serifDigitThree UniversalString ::= {0, 1, 215, 229}

-- mathematicalSans-serifDigitFour UniversalString ::= {0, 1, 215, 230}

-- mathematicalSans-serifDigitFive UniversalString ::= {0, 1, 215, 231}

-- mathematicalSans-serifDigitSix UniversalString ::= {0, 1, 215, 232}

-- mathematicalSans-serifDigitSeven UniversalString ::= {0, 1, 215, 233}

-- mathematicalSans-serifDigitEight UniversalString ::= {0, 1, 215, 234}

-- mathematicalSans-serifDigitNine UniversalString ::= {0, 1, 215, 235}

-- mathematicalSans-serifBoldDigitZero UniversalString ::= {0, 1, 215, 236}

-- mathematicalSans-serifBoldDigitOne UniversalString ::= {0, 1, 215, 237}

-- mathematicalSans-serifBoldDigitTwo UniversalString ::= {0, 1, 215, 238}

-- mathematicalSans-serifBoldDigitThree UniversalString ::= {0, 1, 215, 239}

-- mathematicalSans-serifBoldDigitFour UniversalString ::= {0, 1, 215, 240}

-- mathematicalSans-serifBoldDigitFive UniversalString ::= {0, 1, 215, 241}

-- mathematicalSans-serifBoldDigitSix UniversalString ::= {0, 1, 215, 242}

-- mathematicalSans-serifBoldDigitSeven UniversalString ::= {0, 1, 215, 243}

-- mathematicalSans-serifBoldDigitEight UniversalString ::= {0, 1, 215, 244}

-- mathematicalSans-serifBoldDigitNine UniversalString ::= {0, 1, 215, 245}

-- mathematicalMonospaceDigitZero UniversalString ::= {0, 1, 215, 246}

-- mathematicalMonospaceDigitOne UniversalString ::= {0, 1, 215, 247}

-- mathematicalMonospaceDigitTwo UniversalString ::= {0, 1, 215, 248}

-- mathematicalMonospaceDigitThree UniversalString ::= {0, 1, 215, 249}

-- mathematicalMonospaceDigitFour UniversalString ::= {0, 1, 215, 250}

-- mathematicalMonospaceDigitFive UniversalString ::= {0, 1, 215, 251}

-- mathematicalMonospaceDigitSix UniversalString ::= {0, 1, 215, 252}

-- mathematicalMonospaceDigitSeven UniversalString ::= {0, 1, 215, 253}

-- mathematicalMonospaceDigitEight UniversalString ::= {0, 1, 215, 254}

-- mathematicalMonospaceDigitNine UniversalString ::= {0, 1, 215, 255}

-- cjkCompatibilityIdeograph-2f800 UniversalString ::= {0, 2, 248, 0}

-- cjkCompatibilityIdeograph-2f801 UniversalString ::= {0, 2, 248, 1}

-- cjkCompatibilityIdeograph-2f802 UniversalString ::= {0, 2, 248, 2}

-- cjkCompatibilityIdeograph-2f803 UniversalString ::= {0, 2, 248, 3}

-- cjkCompatibilityIdeograph-2f804 UniversalString ::= {0, 2, 248, 4}

-- cjkCompatibilityIdeograph-2f805 UniversalString ::= {0, 2, 248, 5}

-- cjkCompatibilityIdeograph-2f806 UniversalString ::= {0, 2, 248, 6}

-- cjkCompatibilityIdeograph-2f807 UniversalString ::= {0, 2, 248, 7}

-- cjkCompatibilityIdeograph-2f808 UniversalString ::= {0, 2, 248, 8}

-- cjkCompatibilityIdeograph-2f809 UniversalString ::= {0, 2, 248, 9}

-- cjkCompatibilityIdeograph-2f80a UniversalString ::= {0, 2, 248, 10}

-- cjkCompatibilityIdeograph-2f80b UniversalString ::= {0, 2, 248, 11}

-- cjkCompatibilityIdeograph-2f80c UniversalString ::= {0, 2, 248, 12}

-- cjkCompatibilityIdeograph-2f80d UniversalString ::= {0, 2, 248, 13}

-- cjkCompatibilityIdeograph-2f80e UniversalString ::= {0, 2, 248, 14}

-- cjkCompatibilityIdeograph-2f80f UniversalString ::= {0, 2, 248, 15}

-- cjkCompatibilityIdeograph-2f810 UniversalString ::= {0, 2, 248, 16}

-- cjkCompatibilityIdeograph-2f811 UniversalString ::= {0, 2, 248, 17}

-- cjkCompatibilityIdeograph-2f812 UniversalString ::= {0, 2, 248, 18}

-- cjkCompatibilityIdeograph-2f813 UniversalString ::= {0, 2, 248, 19}

-- cjkCompatibilityIdeograph-2f814 UniversalString ::= {0, 2, 248, 20}

-- cjkCompatibilityIdeograph-2f815 UniversalString ::= {0, 2, 248, 21}

-- cjkCompatibilityIdeograph-2f816 UniversalString ::= {0, 2, 248, 22}

-- cjkCompatibilityIdeograph-2f817 UniversalString ::= {0, 2, 248, 23}

-- cjkCompatibilityIdeograph-2f818 UniversalString ::= {0, 2, 248, 24}

-- cjkCompatibilityIdeograph-2f819 UniversalString ::= {0, 2, 248, 25}

-- cjkCompatibilityIdeograph-2f81a UniversalString ::= {0, 2, 248, 26}

-- cjkCompatibilityIdeograph-2f81b UniversalString ::= {0, 2, 248, 27}

-- cjkCompatibilityIdeograph-2f81c UniversalString ::= {0, 2, 248, 28}

-- cjkCompatibilityIdeograph-2f81d UniversalString ::= {0, 2, 248, 29}

-- cjkCompatibilityIdeograph-2f81e UniversalString ::= {0, 2, 248, 30}

-- cjkCompatibilityIdeograph-2f81f UniversalString ::= {0, 2, 248, 31}

-- cjkCompatibilityIdeograph-2f820 UniversalString ::= {0, 2, 248, 32}

-- cjkCompatibilityIdeograph-2f821 UniversalString ::= {0, 2, 248, 33}

-- cjkCompatibilityIdeograph-2f822 UniversalString ::= {0, 2, 248, 34}

-- cjkCompatibilityIdeograph-2f823 UniversalString ::= {0, 2, 248, 35}

-- cjkCompatibilityIdeograph-2f824 UniversalString ::= {0, 2, 248, 36}

-- cjkCompatibilityIdeograph-2f825 UniversalString ::= {0, 2, 248, 37}

-- cjkCompatibilityIdeograph-2f826 UniversalString ::= {0, 2, 248, 38}

-- cjkCompatibilityIdeograph-2f827 UniversalString ::= {0, 2, 248, 39}

-- cjkCompatibilityIdeograph-2f828 UniversalString ::= {0, 2, 248, 40}

-- cjkCompatibilityIdeograph-2f829 UniversalString ::= {0, 2, 248, 41}

-- cjkCompatibilityIdeograph-2f82a UniversalString ::= {0, 2, 248, 42}

-- cjkCompatibilityIdeograph-2f82b UniversalString ::= {0, 2, 248, 43}

-- cjkCompatibilityIdeograph-2f82c UniversalString ::= {0, 2, 248, 44}

-- cjkCompatibilityIdeograph-2f82d UniversalString ::= {0, 2, 248, 45}

-- cjkCompatibilityIdeograph-2f82e UniversalString ::= {0, 2, 248, 46}

-- cjkCompatibilityIdeograph-2f82f UniversalString ::= {0, 2, 248, 47}

-- cjkCompatibilityIdeograph-2f830 UniversalString ::= {0, 2, 248, 48}

-- cjkCompatibilityIdeograph-2f831 UniversalString ::= {0, 2, 248, 49}

-- cjkCompatibilityIdeograph-2f832 UniversalString ::= {0, 2, 248, 50}

-- cjkCompatibilityIdeograph-2f833 UniversalString ::= {0, 2, 248, 51}

-- cjkCompatibilityIdeograph-2f834 UniversalString ::= {0, 2, 248, 52}

-- cjkCompatibilityIdeograph-2f835 UniversalString ::= {0, 2, 248, 53}

-- cjkCompatibilityIdeograph-2f836 UniversalString ::= {0, 2, 248, 54}

-- cjkCompatibilityIdeograph-2f837 UniversalString ::= {0, 2, 248, 55}

-- cjkCompatibilityIdeograph-2f838 UniversalString ::= {0, 2, 248, 56}

-- cjkCompatibilityIdeograph-2f839 UniversalString ::= {0, 2, 248, 57}

-- cjkCompatibilityIdeograph-2f83a UniversalString ::= {0, 2, 248, 58}

-- cjkCompatibilityIdeograph-2f83b UniversalString ::= {0, 2, 248, 59}

-- cjkCompatibilityIdeograph-2f83c UniversalString ::= {0, 2, 248, 60}

-- cjkCompatibilityIdeograph-2f83d UniversalString ::= {0, 2, 248, 61}

-- cjkCompatibilityIdeograph-2f83e UniversalString ::= {0, 2, 248, 62}

-- cjkCompatibilityIdeograph-2f83f UniversalString ::= {0, 2, 248, 63}

-- cjkCompatibilityIdeograph-2f840 UniversalString ::= {0, 2, 248, 64}

-- cjkCompatibilityIdeograph-2f841 UniversalString ::= {0, 2, 248, 65}

-- cjkCompatibilityIdeograph-2f842 UniversalString ::= {0, 2, 248, 66}

-- cjkCompatibilityIdeograph-2f843 UniversalString ::= {0, 2, 248, 67}

-- cjkCompatibilityIdeograph-2f844 UniversalString ::= {0, 2, 248, 68}

-- cjkCompatibilityIdeograph-2f845 UniversalString ::= {0, 2, 248, 69}

-- cjkCompatibilityIdeograph-2f846 UniversalString ::= {0, 2, 248, 70}

-- cjkCompatibilityIdeograph-2f847 UniversalString ::= {0, 2, 248, 71}

-- cjkCompatibilityIdeograph-2f848 UniversalString ::= {0, 2, 248, 72}

-- cjkCompatibilityIdeograph-2f849 UniversalString ::= {0, 2, 248, 73}

-- cjkCompatibilityIdeograph-2f84a UniversalString ::= {0, 2, 248, 74}

-- cjkCompatibilityIdeograph-2f84b UniversalString ::= {0, 2, 248, 75}

-- cjkCompatibilityIdeograph-2f84c UniversalString ::= {0, 2, 248, 76}

-- cjkCompatibilityIdeograph-2f84d UniversalString ::= {0, 2, 248, 77}

-- cjkCompatibilityIdeograph-2f84e UniversalString ::= {0, 2, 248, 78}

-- cjkCompatibilityIdeograph-2f84f UniversalString ::= {0, 2, 248, 79}

-- cjkCompatibilityIdeograph-2f850 UniversalString ::= {0, 2, 248, 80}

-- cjkCompatibilityIdeograph-2f851 UniversalString ::= {0, 2, 248, 81}

-- cjkCompatibilityIdeograph-2f852 UniversalString ::= {0, 2, 248, 82}

-- cjkCompatibilityIdeograph-2f853 UniversalString ::= {0, 2, 248, 83}

-- cjkCompatibilityIdeograph-2f854 UniversalString ::= {0, 2, 248, 84}

-- cjkCompatibilityIdeograph-2f855 UniversalString ::= {0, 2, 248, 85}

-- cjkCompatibilityIdeograph-2f856 UniversalString ::= {0, 2, 248, 86}

-- cjkCompatibilityIdeograph-2f857 UniversalString ::= {0, 2, 248, 87}

-- cjkCompatibilityIdeograph-2f858 UniversalString ::= {0, 2, 248, 88}

-- cjkCompatibilityIdeograph-2f859 UniversalString ::= {0, 2, 248, 89}

-- cjkCompatibilityIdeograph-2f85a UniversalString ::= {0, 2, 248, 90}

-- cjkCompatibilityIdeograph-2f85b UniversalString ::= {0, 2, 248, 91}

-- cjkCompatibilityIdeograph-2f85c UniversalString ::= {0, 2, 248, 92}

-- cjkCompatibilityIdeograph-2f85d UniversalString ::= {0, 2, 248, 93}

-- cjkCompatibilityIdeograph-2f85e UniversalString ::= {0, 2, 248, 94}

-- cjkCompatibilityIdeograph-2f85f UniversalString ::= {0, 2, 248, 95}

-- cjkCompatibilityIdeograph-2f860 UniversalString ::= {0, 2, 248, 96}

-- cjkCompatibilityIdeograph-2f861 UniversalString ::= {0, 2, 248, 97}

-- cjkCompatibilityIdeograph-2f862 UniversalString ::= {0, 2, 248, 98}

-- cjkCompatibilityIdeograph-2f863 UniversalString ::= {0, 2, 248, 99}

-- cjkCompatibilityIdeograph-2f864 UniversalString ::= {0, 2, 248, 100}

-- cjkCompatibilityIdeograph-2f865 UniversalString ::= {0, 2, 248, 101}

-- cjkCompatibilityIdeograph-2f866 UniversalString ::= {0, 2, 248, 102}

-- cjkCompatibilityIdeograph-2f867 UniversalString ::= {0, 2, 248, 103}

-- cjkCompatibilityIdeograph-2f868 UniversalString ::= {0, 2, 248, 104}

-- cjkCompatibilityIdeograph-2f869 UniversalString ::= {0, 2, 248, 105}

-- cjkCompatibilityIdeograph-2f86a UniversalString ::= {0, 2, 248, 106}

-- cjkCompatibilityIdeograph-2f86b UniversalString ::= {0, 2, 248, 107}

-- cjkCompatibilityIdeograph-2f86c UniversalString ::= {0, 2, 248, 108}

-- cjkCompatibilityIdeograph-2f86d UniversalString ::= {0, 2, 248, 109}

-- cjkCompatibilityIdeograph-2f86e UniversalString ::= {0, 2, 248, 110}

-- cjkCompatibilityIdeograph-2f86f UniversalString ::= {0, 2, 248, 111}

-- cjkCompatibilityIdeograph-2f870 UniversalString ::= {0, 2, 248, 112}

-- cjkCompatibilityIdeograph-2f871 UniversalString ::= {0, 2, 248, 113}

-- cjkCompatibilityIdeograph-2f872 UniversalString ::= {0, 2, 248, 114}

-- cjkCompatibilityIdeograph-2f873 UniversalString ::= {0, 2, 248, 115}

-- cjkCompatibilityIdeograph-2f874 UniversalString ::= {0, 2, 248, 116}

-- cjkCompatibilityIdeograph-2f875 UniversalString ::= {0, 2, 248, 117}

-- cjkCompatibilityIdeograph-2f876 UniversalString ::= {0, 2, 248, 118}

-- cjkCompatibilityIdeograph-2f877 UniversalString ::= {0, 2, 248, 119}

-- cjkCompatibilityIdeograph-2f878 UniversalString ::= {0, 2, 248, 120}

-- cjkCompatibilityIdeograph-2f879 UniversalString ::= {0, 2, 248, 121}

-- cjkCompatibilityIdeograph-2f87a UniversalString ::= {0, 2, 248, 122}

-- cjkCompatibilityIdeograph-2f87b UniversalString ::= {0, 2, 248, 123}

-- cjkCompatibilityIdeograph-2f87c UniversalString ::= {0, 2, 248, 124}

-- cjkCompatibilityIdeograph-2f87d UniversalString ::= {0, 2, 248, 125}

-- cjkCompatibilityIdeograph-2f87e UniversalString ::= {0, 2, 248, 126}

-- cjkCompatibilityIdeograph-2f87f UniversalString ::= {0, 2, 248, 127}

-- cjkCompatibilityIdeograph-2f880 UniversalString ::= {0, 2, 248, 128}

-- cjkCompatibilityIdeograph-2f881 UniversalString ::= {0, 2, 248, 129}

-- cjkCompatibilityIdeograph-2f882 UniversalString ::= {0, 2, 248, 130}

-- cjkCompatibilityIdeograph-2f883 UniversalString ::= {0, 2, 248, 131}

-- cjkCompatibilityIdeograph-2f884 UniversalString ::= {0, 2, 248, 132}

-- cjkCompatibilityIdeograph-2f885 UniversalString ::= {0, 2, 248, 133}

-- cjkCompatibilityIdeograph-2f886 UniversalString ::= {0, 2, 248, 134}

-- cjkCompatibilityIdeograph-2f887 UniversalString ::= {0, 2, 248, 135}

-- cjkCompatibilityIdeograph-2f888 UniversalString ::= {0, 2, 248, 136}

-- cjkCompatibilityIdeograph-2f889 UniversalString ::= {0, 2, 248, 137}

-- cjkCompatibilityIdeograph-2f88a UniversalString ::= {0, 2, 248, 138}

-- cjkCompatibilityIdeograph-2f88b UniversalString ::= {0, 2, 248, 139}

-- cjkCompatibilityIdeograph-2f88c UniversalString ::= {0, 2, 248, 140}

-- cjkCompatibilityIdeograph-2f88d UniversalString ::= {0, 2, 248, 141}

-- cjkCompatibilityIdeograph-2f88e UniversalString ::= {0, 2, 248, 142}

-- cjkCompatibilityIdeograph-2f88f UniversalString ::= {0, 2, 248, 143}

-- cjkCompatibilityIdeograph-2f890 UniversalString ::= {0, 2, 248, 144}

-- cjkCompatibilityIdeograph-2f891 UniversalString ::= {0, 2, 248, 145}

-- cjkCompatibilityIdeograph-2f892 UniversalString ::= {0, 2, 248, 146}

-- cjkCompatibilityIdeograph-2f893 UniversalString ::= {0, 2, 248, 147}

-- cjkCompatibilityIdeograph-2f894 UniversalString ::= {0, 2, 248, 148}

-- cjkCompatibilityIdeograph-2f895 UniversalString ::= {0, 2, 248, 149}

-- cjkCompatibilityIdeograph-2f896 UniversalString ::= {0, 2, 248, 150}

-- cjkCompatibilityIdeograph-2f897 UniversalString ::= {0, 2, 248, 151}

-- cjkCompatibilityIdeograph-2f898 UniversalString ::= {0, 2, 248, 152}

-- cjkCompatibilityIdeograph-2f899 UniversalString ::= {0, 2, 248, 153}

-- cjkCompatibilityIdeograph-2f89a UniversalString ::= {0, 2, 248, 154}

-- cjkCompatibilityIdeograph-2f89b UniversalString ::= {0, 2, 248, 155}

-- cjkCompatibilityIdeograph-2f89c UniversalString ::= {0, 2, 248, 156}

-- cjkCompatibilityIdeograph-2f89d UniversalString ::= {0, 2, 248, 157}

-- cjkCompatibilityIdeograph-2f89e UniversalString ::= {0, 2, 248, 158}

-- cjkCompatibilityIdeograph-2f89f UniversalString ::= {0, 2, 248, 159}

-- cjkCompatibilityIdeograph-2f8a0 UniversalString ::= {0, 2, 248, 160}

-- cjkCompatibilityIdeograph-2f8a1 UniversalString ::= {0, 2, 248, 161}

-- cjkCompatibilityIdeograph-2f8a2 UniversalString ::= {0, 2, 248, 162}

-- cjkCompatibilityIdeograph-2f8a3 UniversalString ::= {0, 2, 248, 163}

-- cjkCompatibilityIdeograph-2f8a4 UniversalString ::= {0, 2, 248, 164}

-- cjkCompatibilityIdeograph-2f8a5 UniversalString ::= {0, 2, 248, 165}

-- cjkCompatibilityIdeograph-2f8a6 UniversalString ::= {0, 2, 248, 166}

-- cjkCompatibilityIdeograph-2f8a7 UniversalString ::= {0, 2, 248, 167}

-- cjkCompatibilityIdeograph-2f8a8 UniversalString ::= {0, 2, 248, 168}

-- cjkCompatibilityIdeograph-2f8a9 UniversalString ::= {0, 2, 248, 169}

-- cjkCompatibilityIdeograph-2f8aa UniversalString ::= {0, 2, 248, 170}

-- cjkCompatibilityIdeograph-2f8ab UniversalString ::= {0, 2, 248, 171}

-- cjkCompatibilityIdeograph-2f8ac UniversalString ::= {0, 2, 248, 172}

-- cjkCompatibilityIdeograph-2f8ad UniversalString ::= {0, 2, 248, 173}

-- cjkCompatibilityIdeograph-2f8ae UniversalString ::= {0, 2, 248, 174}

-- cjkCompatibilityIdeograph-2f8af UniversalString ::= {0, 2, 248, 175}

-- cjkCompatibilityIdeograph-2f8b0 UniversalString ::= {0, 2, 248, 176}

-- cjkCompatibilityIdeograph-2f8b1 UniversalString ::= {0, 2, 248, 177}

-- cjkCompatibilityIdeograph-2f8b2 UniversalString ::= {0, 2, 248, 178}

-- cjkCompatibilityIdeograph-2f8b3 UniversalString ::= {0, 2, 248, 179}

-- cjkCompatibilityIdeograph-2f8b4 UniversalString ::= {0, 2, 248, 180}

-- cjkCompatibilityIdeograph-2f8b5 UniversalString ::= {0, 2, 248, 181}

-- cjkCompatibilityIdeograph-2f8b6 UniversalString ::= {0, 2, 248, 182}

-- cjkCompatibilityIdeograph-2f8b7 UniversalString ::= {0, 2, 248, 183}

-- cjkCompatibilityIdeograph-2f8b8 UniversalString ::= {0, 2, 248, 184}

-- cjkCompatibilityIdeograph-2f8b9 UniversalString ::= {0, 2, 248, 185}

-- cjkCompatibilityIdeograph-2f8ba UniversalString ::= {0, 2, 248, 186}

-- cjkCompatibilityIdeograph-2f8bb UniversalString ::= {0, 2, 248, 187}

-- cjkCompatibilityIdeograph-2f8bc UniversalString ::= {0, 2, 248, 188}

-- cjkCompatibilityIdeograph-2f8bd UniversalString ::= {0, 2, 248, 189}

-- cjkCompatibilityIdeograph-2f8be UniversalString ::= {0, 2, 248, 190}

-- cjkCompatibilityIdeograph-2f8bf UniversalString ::= {0, 2, 248, 191}

-- cjkCompatibilityIdeograph-2f8c0 UniversalString ::= {0, 2, 248, 192}

-- cjkCompatibilityIdeograph-2f8c1 UniversalString ::= {0, 2, 248, 193}

-- cjkCompatibilityIdeograph-2f8c2 UniversalString ::= {0, 2, 248, 194}

-- cjkCompatibilityIdeograph-2f8c3 UniversalString ::= {0, 2, 248, 195}

-- cjkCompatibilityIdeograph-2f8c4 UniversalString ::= {0, 2, 248, 196}

-- cjkCompatibilityIdeograph-2f8c5 UniversalString ::= {0, 2, 248, 197}

-- cjkCompatibilityIdeograph-2f8c6 UniversalString ::= {0, 2, 248, 198}

-- cjkCompatibilityIdeograph-2f8c7 UniversalString ::= {0, 2, 248, 199}

-- cjkCompatibilityIdeograph-2f8c8 UniversalString ::= {0, 2, 248, 200}

-- cjkCompatibilityIdeograph-2f8c9 UniversalString ::= {0, 2, 248, 201}

-- cjkCompatibilityIdeograph-2f8ca UniversalString ::= {0, 2, 248, 202}

-- cjkCompatibilityIdeograph-2f8cb UniversalString ::= {0, 2, 248, 203}

-- cjkCompatibilityIdeograph-2f8cc UniversalString ::= {0, 2, 248, 204}

-- cjkCompatibilityIdeograph-2f8cd UniversalString ::= {0, 2, 248, 205}

-- cjkCompatibilityIdeograph-2f8ce UniversalString ::= {0, 2, 248, 206}

-- cjkCompatibilityIdeograph-2f8cf UniversalString ::= {0, 2, 248, 207}

-- cjkCompatibilityIdeograph-2f8d0 UniversalString ::= {0, 2, 248, 208}

-- cjkCompatibilityIdeograph-2f8d1 UniversalString ::= {0, 2, 248, 209}

-- cjkCompatibilityIdeograph-2f8d2 UniversalString ::= {0, 2, 248, 210}

-- cjkCompatibilityIdeograph-2f8d3 UniversalString ::= {0, 2, 248, 211}

-- cjkCompatibilityIdeograph-2f8d4 UniversalString ::= {0, 2, 248, 212}

-- cjkCompatibilityIdeograph-2f8d5 UniversalString ::= {0, 2, 248, 213}

-- cjkCompatibilityIdeograph-2f8d6 UniversalString ::= {0, 2, 248, 214}

-- cjkCompatibilityIdeograph-2f8d7 UniversalString ::= {0, 2, 248, 215}

-- cjkCompatibilityIdeograph-2f8d8 UniversalString ::= {0, 2, 248, 216}

-- cjkCompatibilityIdeograph-2f8d9 UniversalString ::= {0, 2, 248, 217}

-- cjkCompatibilityIdeograph-2f8da UniversalString ::= {0, 2, 248, 218}

-- cjkCompatibilityIdeograph-2f8db UniversalString ::= {0, 2, 248, 219}

-- cjkCompatibilityIdeograph-2f8dc UniversalString ::= {0, 2, 248, 220}

-- cjkCompatibilityIdeograph-2f8dd UniversalString ::= {0, 2, 248, 221}

-- cjkCompatibilityIdeograph-2f8de UniversalString ::= {0, 2, 248, 222}

-- cjkCompatibilityIdeograph-2f8df UniversalString ::= {0, 2, 248, 223}

-- cjkCompatibilityIdeograph-2f8e0 UniversalString ::= {0, 2, 248, 224}

-- cjkCompatibilityIdeograph-2f8e1 UniversalString ::= {0, 2, 248, 225}

-- cjkCompatibilityIdeograph-2f8e2 UniversalString ::= {0, 2, 248, 226}

-- cjkCompatibilityIdeograph-2f8e3 UniversalString ::= {0, 2, 248, 227}

-- cjkCompatibilityIdeograph-2f8e4 UniversalString ::= {0, 2, 248, 228}

-- cjkCompatibilityIdeograph-2f8e5 UniversalString ::= {0, 2, 248, 229}

-- cjkCompatibilityIdeograph-2f8e6 UniversalString ::= {0, 2, 248, 230}

-- cjkCompatibilityIdeograph-2f8e7 UniversalString ::= {0, 2, 248, 231}

-- cjkCompatibilityIdeograph-2f8e8 UniversalString ::= {0, 2, 248, 232}

-- cjkCompatibilityIdeograph-2f8e9 UniversalString ::= {0, 2, 248, 233}

-- cjkCompatibilityIdeograph-2f8ea UniversalString ::= {0, 2, 248, 234}

-- cjkCompatibilityIdeograph-2f8eb UniversalString ::= {0, 2, 248, 235}

-- cjkCompatibilityIdeograph-2f8ec UniversalString ::= {0, 2, 248, 236}

-- cjkCompatibilityIdeograph-2f8ed UniversalString ::= {0, 2, 248, 237}

-- cjkCompatibilityIdeograph-2f8ee UniversalString ::= {0, 2, 248, 238}

-- cjkCompatibilityIdeograph-2f8ef UniversalString ::= {0, 2, 248, 239}

-- cjkCompatibilityIdeograph-2f8f0 UniversalString ::= {0, 2, 248, 240}

-- cjkCompatibilityIdeograph-2f8f1 UniversalString ::= {0, 2, 248, 241}

-- cjkCompatibilityIdeograph-2f8f2 UniversalString ::= {0, 2, 248, 242}

-- cjkCompatibilityIdeograph-2f8f3 UniversalString ::= {0, 2, 248, 243}

-- cjkCompatibilityIdeograph-2f8f4 UniversalString ::= {0, 2, 248, 244}

-- cjkCompatibilityIdeograph-2f8f5 UniversalString ::= {0, 2, 248, 245}

-- cjkCompatibilityIdeograph-2f8f6 UniversalString ::= {0, 2, 248, 246}

-- cjkCompatibilityIdeograph-2f8f7 UniversalString ::= {0, 2, 248, 247}

-- cjkCompatibilityIdeograph-2f8f8 UniversalString ::= {0, 2, 248, 248}

-- cjkCompatibilityIdeograph-2f8f9 UniversalString ::= {0, 2, 248, 249}

-- cjkCompatibilityIdeograph-2f8fa UniversalString ::= {0, 2, 248, 250}

-- cjkCompatibilityIdeograph-2f8fb UniversalString ::= {0, 2, 248, 251}

-- cjkCompatibilityIdeograph-2f8fc UniversalString ::= {0, 2, 248, 252}

-- cjkCompatibilityIdeograph-2f8fd UniversalString ::= {0, 2, 248, 253}

-- cjkCompatibilityIdeograph-2f8fe UniversalString ::= {0, 2, 248, 254}

-- cjkCompatibilityIdeograph-2f8ff UniversalString ::= {0, 2, 248, 255}

-- cjkCompatibilityIdeograph-2f900 UniversalString ::= {0, 2, 249, 0}

-- cjkCompatibilityIdeograph-2f901 UniversalString ::= {0, 2, 249, 1}

-- cjkCompatibilityIdeograph-2f902 UniversalString ::= {0, 2, 249, 2}

-- cjkCompatibilityIdeograph-2f903 UniversalString ::= {0, 2, 249, 3}

-- cjkCompatibilityIdeograph-2f904 UniversalString ::= {0, 2, 249, 4}

-- cjkCompatibilityIdeograph-2f905 UniversalString ::= {0, 2, 249, 5}

-- cjkCompatibilityIdeograph-2f906 UniversalString ::= {0, 2, 249, 6}

-- cjkCompatibilityIdeograph-2f907 UniversalString ::= {0, 2, 249, 7}

-- cjkCompatibilityIdeograph-2f908 UniversalString ::= {0, 2, 249, 8}

-- cjkCompatibilityIdeograph-2f909 UniversalString ::= {0, 2, 249, 9}

-- cjkCompatibilityIdeograph-2f90a UniversalString ::= {0, 2, 249, 10}

-- cjkCompatibilityIdeograph-2f90b UniversalString ::= {0, 2, 249, 11}

-- cjkCompatibilityIdeograph-2f90c UniversalString ::= {0, 2, 249, 12}

-- cjkCompatibilityIdeograph-2f90d UniversalString ::= {0, 2, 249, 13}

-- cjkCompatibilityIdeograph-2f90e UniversalString ::= {0, 2, 249, 14}

-- cjkCompatibilityIdeograph-2f90f UniversalString ::= {0, 2, 249, 15}

-- cjkCompatibilityIdeograph-2f910 UniversalString ::= {0, 2, 249, 16}

-- cjkCompatibilityIdeograph-2f911 UniversalString ::= {0, 2, 249, 17}

-- cjkCompatibilityIdeograph-2f912 UniversalString ::= {0, 2, 249, 18}

-- cjkCompatibilityIdeograph-2f913 UniversalString ::= {0, 2, 249, 19}

-- cjkCompatibilityIdeograph-2f914 UniversalString ::= {0, 2, 249, 20}

-- cjkCompatibilityIdeograph-2f915 UniversalString ::= {0, 2, 249, 21}

-- cjkCompatibilityIdeograph-2f916 UniversalString ::= {0, 2, 249, 22}

-- cjkCompatibilityIdeograph-2f917 UniversalString ::= {0, 2, 249, 23}

-- cjkCompatibilityIdeograph-2f918 UniversalString ::= {0, 2, 249, 24}

-- cjkCompatibilityIdeograph-2f919 UniversalString ::= {0, 2, 249, 25}

-- cjkCompatibilityIdeograph-2f91a UniversalString ::= {0, 2, 249, 26}

-- cjkCompatibilityIdeograph-2f91b UniversalString ::= {0, 2, 249, 27}

-- cjkCompatibilityIdeograph-2f91c UniversalString ::= {0, 2, 249, 28}

-- cjkCompatibilityIdeograph-2f91d UniversalString ::= {0, 2, 249, 29}

-- cjkCompatibilityIdeograph-2f91e UniversalString ::= {0, 2, 249, 30}

-- cjkCompatibilityIdeograph-2f91f UniversalString ::= {0, 2, 249, 31}

-- cjkCompatibilityIdeograph-2f920 UniversalString ::= {0, 2, 249, 32}

-- cjkCompatibilityIdeograph-2f921 UniversalString ::= {0, 2, 249, 33}

-- cjkCompatibilityIdeograph-2f922 UniversalString ::= {0, 2, 249, 34}

-- cjkCompatibilityIdeograph-2f923 UniversalString ::= {0, 2, 249, 35}

-- cjkCompatibilityIdeograph-2f924 UniversalString ::= {0, 2, 249, 36}

-- cjkCompatibilityIdeograph-2f925 UniversalString ::= {0, 2, 249, 37}

-- cjkCompatibilityIdeograph-2f926 UniversalString ::= {0, 2, 249, 38}

-- cjkCompatibilityIdeograph-2f927 UniversalString ::= {0, 2, 249, 39}

-- cjkCompatibilityIdeograph-2f928 UniversalString ::= {0, 2, 249, 40}

-- cjkCompatibilityIdeograph-2f929 UniversalString ::= {0, 2, 249, 41}

-- cjkCompatibilityIdeograph-2f92a UniversalString ::= {0, 2, 249, 42}

-- cjkCompatibilityIdeograph-2f92b UniversalString ::= {0, 2, 249, 43}

-- cjkCompatibilityIdeograph-2f92c UniversalString ::= {0, 2, 249, 44}

-- cjkCompatibilityIdeograph-2f92d UniversalString ::= {0, 2, 249, 45}

-- cjkCompatibilityIdeograph-2f92e UniversalString ::= {0, 2, 249, 46}

-- cjkCompatibilityIdeograph-2f92f UniversalString ::= {0, 2, 249, 47}

-- cjkCompatibilityIdeograph-2f930 UniversalString ::= {0, 2, 249, 48}

-- cjkCompatibilityIdeograph-2f931 UniversalString ::= {0, 2, 249, 49}

-- cjkCompatibilityIdeograph-2f932 UniversalString ::= {0, 2, 249, 50}

-- cjkCompatibilityIdeograph-2f933 UniversalString ::= {0, 2, 249, 51}

-- cjkCompatibilityIdeograph-2f934 UniversalString ::= {0, 2, 249, 52}

-- cjkCompatibilityIdeograph-2f935 UniversalString ::= {0, 2, 249, 53}

-- cjkCompatibilityIdeograph-2f936 UniversalString ::= {0, 2, 249, 54}

-- cjkCompatibilityIdeograph-2f937 UniversalString ::= {0, 2, 249, 55}

-- cjkCompatibilityIdeograph-2f938 UniversalString ::= {0, 2, 249, 56}

-- cjkCompatibilityIdeograph-2f939 UniversalString ::= {0, 2, 249, 57}

-- cjkCompatibilityIdeograph-2f93a UniversalString ::= {0, 2, 249, 58}

-- cjkCompatibilityIdeograph-2f93b UniversalString ::= {0, 2, 249, 59}

-- cjkCompatibilityIdeograph-2f93c UniversalString ::= {0, 2, 249, 60}

-- cjkCompatibilityIdeograph-2f93d UniversalString ::= {0, 2, 249, 61}

-- cjkCompatibilityIdeograph-2f93e UniversalString ::= {0, 2, 249, 62}

-- cjkCompatibilityIdeograph-2f93f UniversalString ::= {0, 2, 249, 63}

-- cjkCompatibilityIdeograph-2f940 UniversalString ::= {0, 2, 249, 64}

-- cjkCompatibilityIdeograph-2f941 UniversalString ::= {0, 2, 249, 65}

-- cjkCompatibilityIdeograph-2f942 UniversalString ::= {0, 2, 249, 66}

-- cjkCompatibilityIdeograph-2f943 UniversalString ::= {0, 2, 249, 67}

-- cjkCompatibilityIdeograph-2f944 UniversalString ::= {0, 2, 249, 68}

-- cjkCompatibilityIdeograph-2f945 UniversalString ::= {0, 2, 249, 69}

-- cjkCompatibilityIdeograph-2f946 UniversalString ::= {0, 2, 249, 70}

-- cjkCompatibilityIdeograph-2f947 UniversalString ::= {0, 2, 249, 71}

-- cjkCompatibilityIdeograph-2f948 UniversalString ::= {0, 2, 249, 72}

-- cjkCompatibilityIdeograph-2f949 UniversalString ::= {0, 2, 249, 73}

-- cjkCompatibilityIdeograph-2f94a UniversalString ::= {0, 2, 249, 74}

-- cjkCompatibilityIdeograph-2f94b UniversalString ::= {0, 2, 249, 75}

-- cjkCompatibilityIdeograph-2f94c UniversalString ::= {0, 2, 249, 76}

-- cjkCompatibilityIdeograph-2f94d UniversalString ::= {0, 2, 249, 77}

-- cjkCompatibilityIdeograph-2f94e UniversalString ::= {0, 2, 249, 78}

-- cjkCompatibilityIdeograph-2f94f UniversalString ::= {0, 2, 249, 79}

-- cjkCompatibilityIdeograph-2f950 UniversalString ::= {0, 2, 249, 80}

-- cjkCompatibilityIdeograph-2f951 UniversalString ::= {0, 2, 249, 81}

-- cjkCompatibilityIdeograph-2f952 UniversalString ::= {0, 2, 249, 82}

-- cjkCompatibilityIdeograph-2f953 UniversalString ::= {0, 2, 249, 83}

-- cjkCompatibilityIdeograph-2f954 UniversalString ::= {0, 2, 249, 84}

-- cjkCompatibilityIdeograph-2f955 UniversalString ::= {0, 2, 249, 85}

-- cjkCompatibilityIdeograph-2f956 UniversalString ::= {0, 2, 249, 86}

-- cjkCompatibilityIdeograph-2f957 UniversalString ::= {0, 2, 249, 87}

-- cjkCompatibilityIdeograph-2f958 UniversalString ::= {0, 2, 249, 88}

-- cjkCompatibilityIdeograph-2f959 UniversalString ::= {0, 2, 249, 89}

-- cjkCompatibilityIdeograph-2f95a UniversalString ::= {0, 2, 249, 90}

-- cjkCompatibilityIdeograph-2f95b UniversalString ::= {0, 2, 249, 91}

-- cjkCompatibilityIdeograph-2f95c UniversalString ::= {0, 2, 249, 92}

-- cjkCompatibilityIdeograph-2f95d UniversalString ::= {0, 2, 249, 93}

-- cjkCompatibilityIdeograph-2f95e UniversalString ::= {0, 2, 249, 94}

-- cjkCompatibilityIdeograph-2f95f UniversalString ::= {0, 2, 249, 95}

-- cjkCompatibilityIdeograph-2f960 UniversalString ::= {0, 2, 249, 96}

-- cjkCompatibilityIdeograph-2f961 UniversalString ::= {0, 2, 249, 97}

-- cjkCompatibilityIdeograph-2f962 UniversalString ::= {0, 2, 249, 98}

-- cjkCompatibilityIdeograph-2f963 UniversalString ::= {0, 2, 249, 99}

-- cjkCompatibilityIdeograph-2f964 UniversalString ::= {0, 2, 249, 100}

-- cjkCompatibilityIdeograph-2f965 UniversalString ::= {0, 2, 249, 101}

-- cjkCompatibilityIdeograph-2f966 UniversalString ::= {0, 2, 249, 102}

-- cjkCompatibilityIdeograph-2f967 UniversalString ::= {0, 2, 249, 103}

-- cjkCompatibilityIdeograph-2f968 UniversalString ::= {0, 2, 249, 104}

-- cjkCompatibilityIdeograph-2f969 UniversalString ::= {0, 2, 249, 105}

-- cjkCompatibilityIdeograph-2f96a UniversalString ::= {0, 2, 249, 106}

-- cjkCompatibilityIdeograph-2f96b UniversalString ::= {0, 2, 249, 107}

-- cjkCompatibilityIdeograph-2f96c UniversalString ::= {0, 2, 249, 108}

-- cjkCompatibilityIdeograph-2f96d UniversalString ::= {0, 2, 249, 109}

-- cjkCompatibilityIdeograph-2f96e UniversalString ::= {0, 2, 249, 110}

-- cjkCompatibilityIdeograph-2f96f UniversalString ::= {0, 2, 249, 111}

-- cjkCompatibilityIdeograph-2f970 UniversalString ::= {0, 2, 249, 112}

-- cjkCompatibilityIdeograph-2f971 UniversalString ::= {0, 2, 249, 113}

-- cjkCompatibilityIdeograph-2f972 UniversalString ::= {0, 2, 249, 114}

-- cjkCompatibilityIdeograph-2f973 UniversalString ::= {0, 2, 249, 115}

-- cjkCompatibilityIdeograph-2f974 UniversalString ::= {0, 2, 249, 116}

-- cjkCompatibilityIdeograph-2f975 UniversalString ::= {0, 2, 249, 117}

-- cjkCompatibilityIdeograph-2f976 UniversalString ::= {0, 2, 249, 118}

-- cjkCompatibilityIdeograph-2f977 UniversalString ::= {0, 2, 249, 119}

-- cjkCompatibilityIdeograph-2f978 UniversalString ::= {0, 2, 249, 120}

-- cjkCompatibilityIdeograph-2f979 UniversalString ::= {0, 2, 249, 121}

-- cjkCompatibilityIdeograph-2f97a UniversalString ::= {0, 2, 249, 122}

-- cjkCompatibilityIdeograph-2f97b UniversalString ::= {0, 2, 249, 123}

-- cjkCompatibilityIdeograph-2f97c UniversalString ::= {0, 2, 249, 124}

-- cjkCompatibilityIdeograph-2f97d UniversalString ::= {0, 2, 249, 125}

-- cjkCompatibilityIdeograph-2f97e UniversalString ::= {0, 2, 249, 126}

-- cjkCompatibilityIdeograph-2f97f UniversalString ::= {0, 2, 249, 127}

-- cjkCompatibilityIdeograph-2f980 UniversalString ::= {0, 2, 249, 128}

-- cjkCompatibilityIdeograph-2f981 UniversalString ::= {0, 2, 249, 129}

-- cjkCompatibilityIdeograph-2f982 UniversalString ::= {0, 2, 249, 130}

-- cjkCompatibilityIdeograph-2f983 UniversalString ::= {0, 2, 249, 131}

-- cjkCompatibilityIdeograph-2f984 UniversalString ::= {0, 2, 249, 132}

-- cjkCompatibilityIdeograph-2f985 UniversalString ::= {0, 2, 249, 133}

-- cjkCompatibilityIdeograph-2f986 UniversalString ::= {0, 2, 249, 134}

-- cjkCompatibilityIdeograph-2f987 UniversalString ::= {0, 2, 249, 135}

-- cjkCompatibilityIdeograph-2f988 UniversalString ::= {0, 2, 249, 136}

-- cjkCompatibilityIdeograph-2f989 UniversalString ::= {0, 2, 249, 137}

-- cjkCompatibilityIdeograph-2f98a UniversalString ::= {0, 2, 249, 138}

-- cjkCompatibilityIdeograph-2f98b UniversalString ::= {0, 2, 249, 139}

-- cjkCompatibilityIdeograph-2f98c UniversalString ::= {0, 2, 249, 140}

-- cjkCompatibilityIdeograph-2f98d UniversalString ::= {0, 2, 249, 141}

-- cjkCompatibilityIdeograph-2f98e UniversalString ::= {0, 2, 249, 142}

-- cjkCompatibilityIdeograph-2f98f UniversalString ::= {0, 2, 249, 143}

-- cjkCompatibilityIdeograph-2f990 UniversalString ::= {0, 2, 249, 144}

-- cjkCompatibilityIdeograph-2f991 UniversalString ::= {0, 2, 249, 145}

-- cjkCompatibilityIdeograph-2f992 UniversalString ::= {0, 2, 249, 146}

-- cjkCompatibilityIdeograph-2f993 UniversalString ::= {0, 2, 249, 147}

-- cjkCompatibilityIdeograph-2f994 UniversalString ::= {0, 2, 249, 148}

-- cjkCompatibilityIdeograph-2f995 UniversalString ::= {0, 2, 249, 149}

-- cjkCompatibilityIdeograph-2f996 UniversalString ::= {0, 2, 249, 150}

-- cjkCompatibilityIdeograph-2f997 UniversalString ::= {0, 2, 249, 151}

-- cjkCompatibilityIdeograph-2f998 UniversalString ::= {0, 2, 249, 152}

-- cjkCompatibilityIdeograph-2f999 UniversalString ::= {0, 2, 249, 153}

-- cjkCompatibilityIdeograph-2f99a UniversalString ::= {0, 2, 249, 154}

-- cjkCompatibilityIdeograph-2f99b UniversalString ::= {0, 2, 249, 155}

-- cjkCompatibilityIdeograph-2f99c UniversalString ::= {0, 2, 249, 156}

-- cjkCompatibilityIdeograph-2f99d UniversalString ::= {0, 2, 249, 157}

-- cjkCompatibilityIdeograph-2f99e UniversalString ::= {0, 2, 249, 158}

-- cjkCompatibilityIdeograph-2f99f UniversalString ::= {0, 2, 249, 159}

-- cjkCompatibilityIdeograph-2f9a0 UniversalString ::= {0, 2, 249, 160}

-- cjkCompatibilityIdeograph-2f9a1 UniversalString ::= {0, 2, 249, 161}

-- cjkCompatibilityIdeograph-2f9a2 UniversalString ::= {0, 2, 249, 162}

-- cjkCompatibilityIdeograph-2f9a3 UniversalString ::= {0, 2, 249, 163}

-- cjkCompatibilityIdeograph-2f9a4 UniversalString ::= {0, 2, 249, 164}

-- cjkCompatibilityIdeograph-2f9a5 UniversalString ::= {0, 2, 249, 165}

-- cjkCompatibilityIdeograph-2f9a6 UniversalString ::= {0, 2, 249, 166}

-- cjkCompatibilityIdeograph-2f9a7 UniversalString ::= {0, 2, 249, 167}

-- cjkCompatibilityIdeograph-2f9a8 UniversalString ::= {0, 2, 249, 168}

-- cjkCompatibilityIdeograph-2f9a9 UniversalString ::= {0, 2, 249, 169}

-- cjkCompatibilityIdeograph-2f9aa UniversalString ::= {0, 2, 249, 170}

-- cjkCompatibilityIdeograph-2f9ab UniversalString ::= {0, 2, 249, 171}

-- cjkCompatibilityIdeograph-2f9ac UniversalString ::= {0, 2, 249, 172}

-- cjkCompatibilityIdeograph-2f9ad UniversalString ::= {0, 2, 249, 173}

-- cjkCompatibilityIdeograph-2f9ae UniversalString ::= {0, 2, 249, 174}

-- cjkCompatibilityIdeograph-2f9af UniversalString ::= {0, 2, 249, 175}

-- cjkCompatibilityIdeograph-2f9b0 UniversalString ::= {0, 2, 249, 176}

-- cjkCompatibilityIdeograph-2f9b1 UniversalString ::= {0, 2, 249, 177}

-- cjkCompatibilityIdeograph-2f9b2 UniversalString ::= {0, 2, 249, 178}

-- cjkCompatibilityIdeograph-2f9b3 UniversalString ::= {0, 2, 249, 179}

-- cjkCompatibilityIdeograph-2f9b4 UniversalString ::= {0, 2, 249, 180}

-- cjkCompatibilityIdeograph-2f9b5 UniversalString ::= {0, 2, 249, 181}

-- cjkCompatibilityIdeograph-2f9b6 UniversalString ::= {0, 2, 249, 182}

-- cjkCompatibilityIdeograph-2f9b7 UniversalString ::= {0, 2, 249, 183}

-- cjkCompatibilityIdeograph-2f9b8 UniversalString ::= {0, 2, 249, 184}

-- cjkCompatibilityIdeograph-2f9b9 UniversalString ::= {0, 2, 249, 185}

-- cjkCompatibilityIdeograph-2f9ba UniversalString ::= {0, 2, 249, 186}

-- cjkCompatibilityIdeograph-2f9bb UniversalString ::= {0, 2, 249, 187}

-- cjkCompatibilityIdeograph-2f9bc UniversalString ::= {0, 2, 249, 188}

-- cjkCompatibilityIdeograph-2f9bd UniversalString ::= {0, 2, 249, 189}

-- cjkCompatibilityIdeograph-2f9be UniversalString ::= {0, 2, 249, 190}

-- cjkCompatibilityIdeograph-2f9bf UniversalString ::= {0, 2, 249, 191}

-- cjkCompatibilityIdeograph-2f9c0 UniversalString ::= {0, 2, 249, 192}

-- cjkCompatibilityIdeograph-2f9c1 UniversalString ::= {0, 2, 249, 193}

-- cjkCompatibilityIdeograph-2f9c2 UniversalString ::= {0, 2, 249, 194}

-- cjkCompatibilityIdeograph-2f9c3 UniversalString ::= {0, 2, 249, 195}

-- cjkCompatibilityIdeograph-2f9c4 UniversalString ::= {0, 2, 249, 196}

-- cjkCompatibilityIdeograph-2f9c5 UniversalString ::= {0, 2, 249, 197}

-- cjkCompatibilityIdeograph-2f9c6 UniversalString ::= {0, 2, 249, 198}

-- cjkCompatibilityIdeograph-2f9c7 UniversalString ::= {0, 2, 249, 199}

-- cjkCompatibilityIdeograph-2f9c8 UniversalString ::= {0, 2, 249, 200}

-- cjkCompatibilityIdeograph-2f9c9 UniversalString ::= {0, 2, 249, 201}

-- cjkCompatibilityIdeograph-2f9ca UniversalString ::= {0, 2, 249, 202}

-- cjkCompatibilityIdeograph-2f9cb UniversalString ::= {0, 2, 249, 203}

-- cjkCompatibilityIdeograph-2f9cc UniversalString ::= {0, 2, 249, 204}

-- cjkCompatibilityIdeograph-2f9cd UniversalString ::= {0, 2, 249, 205}

-- cjkCompatibilityIdeograph-2f9ce UniversalString ::= {0, 2, 249, 206}

-- cjkCompatibilityIdeograph-2f9cf UniversalString ::= {0, 2, 249, 207}

-- cjkCompatibilityIdeograph-2f9d0 UniversalString ::= {0, 2, 249, 208}

-- cjkCompatibilityIdeograph-2f9d1 UniversalString ::= {0, 2, 249, 209}

-- cjkCompatibilityIdeograph-2f9d2 UniversalString ::= {0, 2, 249, 210}

-- cjkCompatibilityIdeograph-2f9d3 UniversalString ::= {0, 2, 249, 211}

-- cjkCompatibilityIdeograph-2f9d4 UniversalString ::= {0, 2, 249, 212}

-- cjkCompatibilityIdeograph-2f9d5 UniversalString ::= {0, 2, 249, 213}

-- cjkCompatibilityIdeograph-2f9d6 UniversalString ::= {0, 2, 249, 214}

-- cjkCompatibilityIdeograph-2f9d7 UniversalString ::= {0, 2, 249, 215}

-- cjkCompatibilityIdeograph-2f9d8 UniversalString ::= {0, 2, 249, 216}

-- cjkCompatibilityIdeograph-2f9d9 UniversalString ::= {0, 2, 249, 217}

-- cjkCompatibilityIdeograph-2f9da UniversalString ::= {0, 2, 249, 218}

-- cjkCompatibilityIdeograph-2f9db UniversalString ::= {0, 2, 249, 219}

-- cjkCompatibilityIdeograph-2f9dc UniversalString ::= {0, 2, 249, 220}

-- cjkCompatibilityIdeograph-2f9dd UniversalString ::= {0, 2, 249, 221}

-- cjkCompatibilityIdeograph-2f9de UniversalString ::= {0, 2, 249, 222}

-- cjkCompatibilityIdeograph-2f9df UniversalString ::= {0, 2, 249, 223}

-- cjkCompatibilityIdeograph-2f9e0 UniversalString ::= {0, 2, 249, 224}

-- cjkCompatibilityIdeograph-2f9e1 UniversalString ::= {0, 2, 249, 225}

-- cjkCompatibilityIdeograph-2f9e2 UniversalString ::= {0, 2, 249, 226}

-- cjkCompatibilityIdeograph-2f9e3 UniversalString ::= {0, 2, 249, 227}

-- cjkCompatibilityIdeograph-2f9e4 UniversalString ::= {0, 2, 249, 228}

-- cjkCompatibilityIdeograph-2f9e5 UniversalString ::= {0, 2, 249, 229}

-- cjkCompatibilityIdeograph-2f9e6 UniversalString ::= {0, 2, 249, 230}

-- cjkCompatibilityIdeograph-2f9e7 UniversalString ::= {0, 2, 249, 231}

-- cjkCompatibilityIdeograph-2f9e8 UniversalString ::= {0, 2, 249, 232}

-- cjkCompatibilityIdeograph-2f9e9 UniversalString ::= {0, 2, 249, 233}

-- cjkCompatibilityIdeograph-2f9ea UniversalString ::= {0, 2, 249, 234}

-- cjkCompatibilityIdeograph-2f9eb UniversalString ::= {0, 2, 249, 235}

-- cjkCompatibilityIdeograph-2f9ec UniversalString ::= {0, 2, 249, 236}

-- cjkCompatibilityIdeograph-2f9ed UniversalString ::= {0, 2, 249, 237}

-- cjkCompatibilityIdeograph-2f9ee UniversalString ::= {0, 2, 249, 238}

-- cjkCompatibilityIdeograph-2f9ef UniversalString ::= {0, 2, 249, 239}

-- cjkCompatibilityIdeograph-2f9f0 UniversalString ::= {0, 2, 249, 240}

-- cjkCompatibilityIdeograph-2f9f1 UniversalString ::= {0, 2, 249, 241}

-- cjkCompatibilityIdeograph-2f9f2 UniversalString ::= {0, 2, 249, 242}

-- cjkCompatibilityIdeograph-2f9f3 UniversalString ::= {0, 2, 249, 243}

-- cjkCompatibilityIdeograph-2f9f4 UniversalString ::= {0, 2, 249, 244}

-- cjkCompatibilityIdeograph-2f9f5 UniversalString ::= {0, 2, 249, 245}

-- cjkCompatibilityIdeograph-2f9f6 UniversalString ::= {0, 2, 249, 246}

-- cjkCompatibilityIdeograph-2f9f7 UniversalString ::= {0, 2, 249, 247}

-- cjkCompatibilityIdeograph-2f9f8 UniversalString ::= {0, 2, 249, 248}

-- cjkCompatibilityIdeograph-2f9f9 UniversalString ::= {0, 2, 249, 249}

-- cjkCompatibilityIdeograph-2f9fa UniversalString ::= {0, 2, 249, 250}

-- cjkCompatibilityIdeograph-2f9fb UniversalString ::= {0, 2, 249, 251}

-- cjkCompatibilityIdeograph-2f9fc UniversalString ::= {0, 2, 249, 252}

-- cjkCompatibilityIdeograph-2f9fd UniversalString ::= {0, 2, 249, 253}

-- cjkCompatibilityIdeograph-2f9fe UniversalString ::= {0, 2, 249, 254}

-- cjkCompatibilityIdeograph-2f9ff UniversalString ::= {0, 2, 249, 255}

-- cjkCompatibilityIdeograph-2fa00 UniversalString ::= {0, 2, 250, 0}

-- cjkCompatibilityIdeograph-2fa01 UniversalString ::= {0, 2, 250, 1}

-- cjkCompatibilityIdeograph-2fa02 UniversalString ::= {0, 2, 250, 2}

-- cjkCompatibilityIdeograph-2fa03 UniversalString ::= {0, 2, 250, 3}

-- cjkCompatibilityIdeograph-2fa04 UniversalString ::= {0, 2, 250, 4}

-- cjkCompatibilityIdeograph-2fa05 UniversalString ::= {0, 2, 250, 5}

-- cjkCompatibilityIdeograph-2fa06 UniversalString ::= {0, 2, 250, 6}

-- cjkCompatibilityIdeograph-2fa07 UniversalString ::= {0, 2, 250, 7}

-- cjkCompatibilityIdeograph-2fa08 UniversalString ::= {0, 2, 250, 8}

-- cjkCompatibilityIdeograph-2fa09 UniversalString ::= {0, 2, 250, 9}

-- cjkCompatibilityIdeograph-2fa0a UniversalString ::= {0, 2, 250, 10}

-- cjkCompatibilityIdeograph-2fa0b UniversalString ::= {0, 2, 250, 11}

-- cjkCompatibilityIdeograph-2fa0c UniversalString ::= {0, 2, 250, 12}

-- cjkCompatibilityIdeograph-2fa0d UniversalString ::= {0, 2, 250, 13}

-- cjkCompatibilityIdeograph-2fa0e UniversalString ::= {0, 2, 250, 14}

-- cjkCompatibilityIdeograph-2fa0f UniversalString ::= {0, 2, 250, 15}

-- cjkCompatibilityIdeograph-2fa10 UniversalString ::= {0, 2, 250, 16}

-- cjkCompatibilityIdeograph-2fa11 UniversalString ::= {0, 2, 250, 17}

-- cjkCompatibilityIdeograph-2fa12 UniversalString ::= {0, 2, 250, 18}

-- cjkCompatibilityIdeograph-2fa13 UniversalString ::= {0, 2, 250, 19}

-- cjkCompatibilityIdeograph-2fa14 UniversalString ::= {0, 2, 250, 20}

-- cjkCompatibilityIdeograph-2fa15 UniversalString ::= {0, 2, 250, 21}

-- cjkCompatibilityIdeograph-2fa16 UniversalString ::= {0, 2, 250, 22}

-- cjkCompatibilityIdeograph-2fa17 UniversalString ::= {0, 2, 250, 23}

-- cjkCompatibilityIdeograph-2fa18 UniversalString ::= {0, 2, 250, 24}

-- cjkCompatibilityIdeograph-2fa19 UniversalString ::= {0, 2, 250, 25}

-- cjkCompatibilityIdeograph-2fa1a UniversalString ::= {0, 2, 250, 26}

-- cjkCompatibilityIdeograph-2fa1b UniversalString ::= {0, 2, 250, 27}

-- cjkCompatibilityIdeograph-2fa1c UniversalString ::= {0, 2, 250, 28}

-- cjkCompatibilityIdeograph-2fa1d UniversalString ::= {0, 2, 250, 29}

-- languageTag UniversalString ::= {0, 14, 0, 1}

-- tagSpace UniversalString ::= {0, 14, 0, 32}

-- tagExclamationMark UniversalString ::= {0, 14, 0, 33}

-- tagQuotationMark UniversalString ::= {0, 14, 0, 34}

-- tagNumberSign UniversalString ::= {0, 14, 0, 35}

-- tagDollarSign UniversalString ::= {0, 14, 0, 36}

-- tagPercentSign UniversalString ::= {0, 14, 0, 37}

-- tagAmpersand UniversalString ::= {0, 14, 0, 38}

-- tagApostrophe UniversalString ::= {0, 14, 0, 39}

-- tagLeftParenthesis UniversalString ::= {0, 14, 0, 40}

-- tagRightParenthesis UniversalString ::= {0, 14, 0, 41}

-- tagAsterisk UniversalString ::= {0, 14, 0, 42}

-- tagPlusSign UniversalString ::= {0, 14, 0, 43}

-- tagComma UniversalString ::= {0, 14, 0, 44}

-- tagHyphen-minus UniversalString ::= {0, 14, 0, 45}

-- tagFullStop UniversalString ::= {0, 14, 0, 46}

-- tagSolidus UniversalString ::= {0, 14, 0, 47}

-- tagDigitZero UniversalString ::= {0, 14, 0, 48}

-- tagDigitOne UniversalString ::= {0, 14, 0, 49}

-- tagDigitTwo UniversalString ::= {0, 14, 0, 50}

-- tagDigitThree UniversalString ::= {0, 14, 0, 51}

-- tagDigitFour UniversalString ::= {0, 14, 0, 52}

-- tagDigitFive UniversalString ::= {0, 14, 0, 53}

-- tagDigitSix UniversalString ::= {0, 14, 0, 54}

-- tagDigitSeven UniversalString ::= {0, 14, 0, 55}

-- tagDigitEight UniversalString ::= {0, 14, 0, 56}

-- tagDigitNine UniversalString ::= {0, 14, 0, 57}

-- tagColon UniversalString ::= {0, 14, 0, 58}

-- tagSemicolon UniversalString ::= {0, 14, 0, 59}

-- tagLess-thanSign UniversalString ::= {0, 14, 0, 60}

-- tagEqualsSign UniversalString ::= {0, 14, 0, 61}

-- tagGreater-thanSign UniversalString ::= {0, 14, 0, 62}

-- tagQuestionMark UniversalString ::= {0, 14, 0, 63}

-- tagCommercialAt UniversalString ::= {0, 14, 0, 64}

-- tagLatinCapitalLetterA UniversalString ::= {0, 14, 0, 65}

-- tagLatinCapitalLetterB UniversalString ::= {0, 14, 0, 66}

-- tagLatinCapitalLetterC UniversalString ::= {0, 14, 0, 67}

-- tagLatinCapitalLetterD UniversalString ::= {0, 14, 0, 68}

-- tagLatinCapitalLetterE UniversalString ::= {0, 14, 0, 69}

-- tagLatinCapitalLetterF UniversalString ::= {0, 14, 0, 70}

-- tagLatinCapitalLetterG UniversalString ::= {0, 14, 0, 71}

-- tagLatinCapitalLetterH UniversalString ::= {0, 14, 0, 72}

-- tagLatinCapitalLetterI UniversalString ::= {0, 14, 0, 73}

-- tagLatinCapitalLetterJ UniversalString ::= {0, 14, 0, 74}

-- tagLatinCapitalLetterK UniversalString ::= {0, 14, 0, 75}

-- tagLatinCapitalLetterL UniversalString ::= {0, 14, 0, 76}

-- tagLatinCapitalLetterM UniversalString ::= {0, 14, 0, 77}

-- tagLatinCapitalLetterN UniversalString ::= {0, 14, 0, 78}

-- tagLatinCapitalLetterO UniversalString ::= {0, 14, 0, 79}

-- tagLatinCapitalLetterP UniversalString ::= {0, 14, 0, 80}

-- tagLatinCapitalLetterQ UniversalString ::= {0, 14, 0, 81}

-- tagLatinCapitalLetterR UniversalString ::= {0, 14, 0, 82}

-- tagLatinCapitalLetterS UniversalString ::= {0, 14, 0, 83}

-- tagLatinCapitalLetterT UniversalString ::= {0, 14, 0, 84}

-- tagLatinCapitalLetterU UniversalString ::= {0, 14, 0, 85}

-- tagLatinCapitalLetterV UniversalString ::= {0, 14, 0, 86}

-- tagLatinCapitalLetterW UniversalString ::= {0, 14, 0, 87}

-- tagLatinCapitalLetterX UniversalString ::= {0, 14, 0, 88}

-- tagLatinCapitalLetterY UniversalString ::= {0, 14, 0, 89}

-- tagLatinCapitalLetterZ UniversalString ::= {0, 14, 0, 90}

-- tagLeftSquareBracket UniversalString ::= {0, 14, 0, 91}

-- tagReverseSolidus UniversalString ::= {0, 14, 0, 92}

-- tagRightSquareBracket UniversalString ::= {0, 14, 0, 93}

-- tagCircumflexAccent UniversalString ::= {0, 14, 0, 94}

-- tagLowLine UniversalString ::= {0, 14, 0, 95}

-- tagGraveAccent UniversalString ::= {0, 14, 0, 96}

-- tagLatinSmallLetterA UniversalString ::= {0, 14, 0, 97}

-- tagLatinSmallLetterB UniversalString ::= {0, 14, 0, 98}

-- tagLatinSmallLetterC UniversalString ::= {0, 14, 0, 99}

-- tagLatinSmallLetterD UniversalString ::= {0, 14, 0, 100}

-- tagLatinSmallLetterE UniversalString ::= {0, 14, 0, 101}

-- tagLatinSmallLetterF UniversalString ::= {0, 14, 0, 102}

-- tagLatinSmallLetterG UniversalString ::= {0, 14, 0, 103}

-- tagLatinSmallLetterH UniversalString ::= {0, 14, 0, 104}

-- tagLatinSmallLetterI UniversalString ::= {0, 14, 0, 105}

-- tagLatinSmallLetterJ UniversalString ::= {0, 14, 0, 106}

-- tagLatinSmallLetterK UniversalString ::= {0, 14, 0, 107}

-- tagLatinSmallLetterL UniversalString ::= {0, 14, 0, 108}

-- tagLatinSmallLetterM UniversalString ::= {0, 14, 0, 109}

-- tagLatinSmallLetterN UniversalString ::= {0, 14, 0, 110}

-- tagLatinSmallLetterO UniversalString ::= {0, 14, 0, 111}

-- tagLatinSmallLetterP UniversalString ::= {0, 14, 0, 112}

-- tagLatinSmallLetterQ UniversalString ::= {0, 14, 0, 113}

-- tagLatinSmallLetterR UniversalString ::= {0, 14, 0, 114}

-- tagLatinSmallLetterS UniversalString ::= {0, 14, 0, 115}

-- tagLatinSmallLetterT UniversalString ::= {0, 14, 0, 116}

-- tagLatinSmallLetterU UniversalString ::= {0, 14, 0, 117}

-- tagLatinSmallLetterV UniversalString ::= {0, 14, 0, 118}

-- tagLatinSmallLetterW UniversalString ::= {0, 14, 0, 119}

-- tagLatinSmallLetterX UniversalString ::= {0, 14, 0, 120}

-- tagLatinSmallLetterY UniversalString ::= {0, 14, 0, 121}

-- tagLatinSmallLetterZ UniversalString ::= {0, 14, 0, 122}

-- tagLeftCurlyBracket UniversalString ::= {0, 14, 0, 123}

-- tagVerticalLine UniversalString ::= {0, 14, 0, 124}

-- tagRightCurlyBracket UniversalString ::= {0, 14, 0, 125}

-- tagTilde UniversalString ::= {0, 14, 0, 126}

-- cancelTag UniversalString ::= {0, 14, 0, 127}

-- -- In the following assignment statements a Quadruple value
-- -- is used whenever there is no name assigned to that value
-- -- in the code table.  If there is a name assigned to the value
-- -- in the code table then that name is used instead of the Quadruple.
-- -- For instance, in
-- --
-- --   BasicArabic ::= BMPString (FROM({0, 0, 6, 0}..arabicSukun))
-- --
-- -- the Quadruple {0, 0, 6, 0} is used because there is no name for it,
-- -- and arabicSukun is used because the upper bound of the BasicArabic
-- -- alphabet, {0, 0, 6, 82}, is given the name arabicSukun in the code
-- -- table.
-- -- Collections of characters
-- BasicLatin ::= BMPString(FROM (space..tilde))

-- Latin-1Supplement ::=
--   BMPString(FROM (no-breakSpace..latinSmallLetterYWithDiaeresis))

-- LatinExtended-a ::=
--   BMPString(FROM (latinCapitalLetterAWithMacron..latinSmallLetterLongS))

-- LatinExtended-b ::=
--   BMPString(FROM (latinSmallLetterBWithStroke..{0, 0, 2, 79}))

-- IpaExtensions ::= BMPString(FROM (latinSmallLetterTurnedA..{0, 0, 2, 175}))

-- SpacingModifierLetters ::=
--   BMPString(FROM (modifierLetterSmallH..{0, 0, 2, 255}))

-- CombiningDiacriticalMarks ::=
--   BMPString(FROM (combiningGraveAccent..combiningLatinSmallLetterX))

-- BasicGreek ::= BMPString(FROM ({0,
--                                 0,
--                                 3,
--                                 112}..{0, 0, 3, 207}))

-- GreekSymbolsAndCoptic ::= BMPString(FROM (greekBetaSymbol..{0, 0, 3, 255}))

-- Cyrillic ::= BMPString(FROM (cyrillicCapitalLetterIeWithGrave..{0, 0, 4, 255}))

-- Armenian ::= BMPString(FROM ({0,
--                               0,
--                               5,
--                               48}..{0, 0, 5, 143}))

-- BasicHebrew ::= BMPString(FROM (hebrewLetterAlef..hebrewLetterTav))

-- HebrewExtended ::=
--   BMPString
--     (FROM ({0,
--             0,
--             5,
--             144}..{0, 0, 5, 207} | {0, 0, 5, 235}..{0, 0, 5, 255}))

-- BasicArabic ::= BMPString(FROM ({0,
--                                  0,
--                                  6,
--                                  0}..arabicSukun))

-- ArabicExtended ::= BMPString(FROM (arabicMaddahAbove..{0, 0, 6, 255}))

-- Syriac ::= BMPString(FROM (syriacEndOfParagraph..{0, 0, 7, 79}))

-- Thaana ::= BMPString(FROM (thaanaLetterHaa..{0, 0, 7, 191}))

-- Devanagari ::=
--   BMPString
--     (FROM ({0,
--             0,
--             9,
--             0}..{0, 0, 9, 127} | zeroWidthNon-joiner | zeroWidthJoiner))

-- Bengali ::=
--   BMPString
--     (FROM ({0,
--             0,
--             9,
--             128}..{0, 0, 9, 255} | zeroWidthNon-joiner | zeroWidthJoiner))

-- Gurmukhi ::=
--   BMPString
--     (FROM ({0,
--             0,
--             10,
--             0}..{0, 0, 10, 127} | zeroWidthNon-joiner | zeroWidthJoiner))

-- Gujarati ::=
--   BMPString
--     (FROM ({0,
--             0,
--             10,
--             128}..{0, 0, 10, 255} | zeroWidthNon-joiner | zeroWidthJoiner))

-- Oriya ::=
--   BMPString
--     (FROM ({0,
--             0,
--             11,
--             0}..{0, 0, 11, 127} | zeroWidthNon-joiner | zeroWidthJoiner))

-- Tamil ::=
--   BMPString
--     (FROM ({0,
--             0,
--             11,
--             128}..{0, 0, 11, 255} | zeroWidthNon-joiner | zeroWidthJoiner))

-- Telugu ::=
--   BMPString
--     (FROM ({0,
--             0,
--             12,
--             0}..{0, 0, 12, 127} | zeroWidthNon-joiner | zeroWidthJoiner))

-- Kannada ::=
--   BMPString
--     (FROM ({0,
--             0,
--             12,
--             128}..{0, 0, 12, 255} | zeroWidthNon-joiner | zeroWidthJoiner))

-- Malayalam ::=
--   BMPString
--     (FROM ({0,
--             0,
--             13,
--             0}..{0, 0, 13, 127} | zeroWidthNon-joiner | zeroWidthJoiner))

-- Sinhala ::= BMPString(FROM ({0,
--                              0,
--                              13,
--                              128}..{0, 0, 13, 255}))

-- Thai ::= BMPString(FROM ({0,
--                           0,
--                           14,
--                           0}..{0, 0, 14, 127}))

-- Lao ::= BMPString(FROM ({0,
--                          0,
--                          14,
--                          128}..{0, 0, 14, 255}))

-- Tibetan ::= BMPString(FROM (tibetanSyllableOm..{0, 0, 15, 255}))

-- Myanmar ::= BMPString(FROM (myanmarLetterKa..{0, 0, 16, 159}))

-- BasicGeorgian ::= BMPString(FROM (georgianLetterAn..{0, 0, 16, 255}))

-- GeorgianExtended ::= BMPString(FROM (georgianCapitalLetterAn..{0, 0, 16, 207}))

-- HangulJamo ::= BMPString(FROM (hangulChoseongKiyeok..{0, 0, 17, 255}))

-- Ethiopic ::= BMPString(FROM (ethiopicSyllableHa..{0, 0, 19, 127}))

-- Cherokee ::= BMPString(FROM (cherokeeLetterA..{0, 0, 19, 255}))

-- UnifiedCanadianAboriginalSyllabics ::=
--   BMPString(FROM ({0,
--                    0,
--                    20,
--                    0}..{0, 0, 22, 127}))

-- Ogham ::= BMPString(FROM (oghamSpaceMark..{0, 0, 22, 159}))

-- Runic ::= BMPString(FROM (runicLetterFehuFeohFeF..{0, 0, 22, 255}))

-- Khmer ::= BMPString(FROM (khmerLetterKa..{0, 0, 23, 255}))

-- Mongolian ::= BMPString(FROM (mongolianBirga..{0, 0, 24, 175}))

-- LatinExtendedAdditional ::=
--   BMPString(FROM (latinCapitalLetterAWithRingBelow..{0, 0, 30, 255}))

-- GreekExtended ::=
--   BMPString(FROM (greekSmallLetterAlphaWithPsili..{0, 0, 31, 255}))

-- GeneralPunctuation ::= BMPString(FROM (enQuad..nominalDigitShapes))

-- SuperscriptsAndSubscripts ::=
--   BMPString(FROM (superscriptZero..{0, 0, 32, 159}))

-- CurrencySymbols ::= BMPString(FROM (euro-currencySign..{0, 0, 32, 207}))

-- CombiningDiacriticalMarksForSymbols ::=
--   BMPString(FROM (combiningLeftHarpoonAbove..{0, 0, 32, 255}))

-- LetterlikeSymbols ::= BMPString(FROM (accountOf..{0, 0, 33, 79}))

-- NumberForms ::= BMPString(FROM ({0,
--                                  0,
--                                  33,
--                                  80}..{0, 0, 33, 143}))

-- Arrows ::= BMPString(FROM (leftwardsArrow..leftRightOpen-headedArrow))

-- MathematicalOperators ::= BMPString(FROM (forAll..zNotationBagMembership))

-- MiscellaneousTechnical ::= BMPString(FROM (diameterSign..{0, 0, 35, 255}))

-- ControlPictures ::= BMPString(FROM (symbolForNull..{0, 0, 36, 63}))

-- OpticalCharacterRecognition ::= BMPString(FROM (ocrHook..{0, 0, 36, 95}))

-- EnclosedAlphanumerics ::= BMPString(FROM (circledDigitOne..{0, 0, 36, 255}))

-- BoxDrawing ::=
--   BMPString(FROM (boxDrawingsLightHorizontal..boxDrawingsHeavyUpAndLightDown))

-- BlockElements ::=
--   BMPString(FROM (upperHalfBlock..quadrantUpperRightAndLowerLeftAndLowerRight))

-- GeometricShapes ::= BMPString(FROM (blackSquare..lowerRightTriangle))

-- MiscellaneousSymbols ::= BMPString(FROM (blackSunWithRays..{0, 0, 38, 255}))

-- Dingbats ::= BMPString(FROM ({0,
--                               0,
--                               39,
--                               0}..{0, 0, 39, 191}))

-- BraillePatterns ::=
--   BMPString(FROM (braillePatternBlank..braillePatternDots-12345678))

-- CjkRadicalsSupplement ::= BMPString(FROM (cjkRadicalRepeat..{0, 0, 46, 255}))

-- KangxiRadicals ::= BMPString(FROM (kangxiRadicalOne..{0, 0, 47, 223}))

-- IdeographicDescriptionCharacters ::=
--   BMPString(FROM (ideographicDescriptionCharacterLeftToRight..{0, 0, 47, 255}))

-- CjkSymbolsAndPunctation ::=
--   BMPString(FROM (ideographicSpace..ideographicHalfFillSpace))

-- Hiragana ::= BMPString(FROM ({0,
--                               0,
--                               48,
--                               64}..hiraganaDigraphYori))

-- Katakana ::=
--   BMPString(FROM (katakana-hiraganaDoubleHyphen..katakanaDigraphKoto))

-- Bopomofo ::= BMPString(FROM ({0,
--                               0,
--                               49,
--                               0}..{0, 0, 49, 47}))

-- HangulCompatibilityJamo ::= BMPString(FROM ({0,
--                                              0,
--                                              49,
--                                              48}..{0, 0, 49, 143}))

-- CjkMiscellaneous ::=
--   BMPString
--     (FROM (ideographicAnnotationLinkingMark..ideographicAnnotationManMark))

-- Kanbun ::=
--   BMPString
--     (FROM (ideographicAnnotationLinkingMark..ideographicAnnotationManMark))

-- BopomofoExtended ::= BMPString(FROM (bopomofoLetterBu..{0, 0, 49, 191}))

-- EnclosedLettersAndMonths ::=
--   BMPString(FROM (parenthesizedHangulKiyeok..{0, 0, 50, 255}))

-- CjkCompatibility ::= BMPString(FROM (squareApaato..{0, 0, 51, 255}))

-- Hangul ::= BMPString(FROM ({0,
--                             0,
--                             52,
--                             0}..{0, 0, 61, 45}))

-- HangulSupplementary-a ::= BMPString(FROM ({0,
--                                            0,
--                                            61,
--                                            46}..{0, 0, 68, 183}))

-- HangulSupplementary-b ::= BMPString(FROM ({0,
--                                            0,
--                                            68,
--                                            184}..{0, 0, 77, 255}))

-- CjkUnifiedIdeographs ::= BMPString(FROM ({0,
--                                           0,
--                                           78,
--                                           0}..{0, 0, 159, 255}))

-- YiSyllables ::= BMPString(FROM (yiSyllableIt..{0, 0, 164, 143}))

-- YiRadicals ::= BMPString(FROM (yiRadicalQot..{0, 0, 164, 207}))

-- HangulSyllables ::= BMPString(FROM ({0,
--                                      0,
--                                      172,
--                                      0}..{0, 0, 215, 163}))

-- HighSurrogates ::= BMPString(FROM ({0,
--                                     0,
--                                     216,
--                                     0}..{0, 0, 219, 127}))

-- HighPrivateUseSurrogates ::=
--   BMPString(FROM ({0,
--                    0,
--                    219,
--                    128}..{0, 0, 219, 255}))

-- LowSurrogates ::= BMPString(FROM ({0,
--                                    0,
--                                    220,
--                                    0}..{0, 0, 223, 255}))

-- PrivateUseArea ::= BMPString(FROM ({0,
--                                     0,
--                                     224,
--                                     0}..{0, 0, 248, 255}))

-- CjkCompatibilityIdeographs ::=
--   BMPString(FROM (cjkCompatibilityIdeograph-f900..{0, 0, 250, 255}))

-- AlphabeticPresentationForms ::=
--   BMPString(FROM (latinSmallLigatureFf..hebrewLigatureAlefLamed))

-- ArabicPresentationForms-a ::=
--   BMPString(FROM (arabicLetterAlefWaslaIsolatedForm..{0, 0, 253, 255}))

-- CombiningHalfMarks ::=
--   BMPString(FROM (combiningLigatureLeftHalf..{0, 0, 254, 47}))

-- CjkCompatibilityForms ::=
--   BMPString(FROM (presentationFormForVerticalTwoDotLeader..wavyLowLine))

-- SmallFormVariants ::= BMPString(FROM (smallComma..{0, 0, 254, 111}))

-- ArabicPresentationForms-b ::=
--   BMPString(FROM (arabicFathatanIsolatedForm..{0, 0, 254, 254}))

-- HalfwidthAndFullwidthForms ::=
--   BMPString(FROM ({0,
--                    0,
--                    255,
--                    0}..{0, 0, 255, 239}))

-- Specials ::=
--   BMPString
--     (FROM ({0,
--             0,
--             255,
--             240}..replacementCharacter | zeroWidthNo-breakSpace))

-- Zero-widthBoundaryIndicators ::=
--   BMPString(FROM (zeroWidthSpace..zeroWidthJoiner | zeroWidthNo-breakSpace))

-- FormatSeparators ::= BMPString(FROM (lineSeparator..paragraphSeparator))

-- Bi-directionalFormatMarks ::=
--   BMPString(FROM (left-to-rightMark..right-to-leftMark))

-- Bi-directionalFormatEmbeddings ::=
--   BMPString(FROM (left-to-rightEmbedding..right-to-leftOverride))

-- HangulFillCharacters ::= BMPString(FROM (hangulFiller..halfwidthHangulFiller))

-- CharacterShapingSelectors ::=
--   BMPString(FROM (inhibitSymmetricSwapping..activateArabicFormShaping))

-- NumericShapeSelectors ::=
--   BMPString(FROM (nationalDigitShapes..nominalDigitShapes))

-- Bmp ::= BMPString(FROM (null..replacementCharacter))

-- OldItalic ::= UniversalString(FROM (oldItalicLetterA..{0, 1, 3, 47}))

-- Gothic ::= UniversalString(FROM (gothicLetterAhsa..{0, 1, 3, 79}))

-- Deseret ::= UniversalString(FROM (deseretCapitalLetterLongI..{0, 1, 4, 79}))

-- ByzantineMusicalSymbols ::=
--   UniversalString
--     (FROM (byzantineMusicalSymbolPsili..byzantineMusicalSymbolArktikoNi))

-- MusicalSymbols ::=
--   UniversalString(FROM (musicalSymbolSingleBarline..{0, 1, 209, 239}))

-- MathematicalAlphanumericSymbols ::=
--   UniversalString
--     (FROM (mathematicalBoldCapitalA..mathematicalMonospaceDigitNine))

-- CjkUnifiedIdeographsExtensionB ::=
--   UniversalString(FROM ({0,
--                          2,
--                          0,
--                          0}..{0, 2, 166, 214}))

-- CjkCompatibilityIdeographsSupplements ::=
--   UniversalString(FROM (cjkCompatibilityIdeograph-2f800..{0, 2, 250, 31}))

-- Tags ::= UniversalString(FROM ({0,
--                                 14,
--                                 0,
--                                 0}..cancelTag))

-- -- Combining characters
-- CombiningCharacters ::=
--   BMPString
--     (FROM (CombiningDiacriticalMarks | CombiningDiacriticalMarksForSymbols |
--            CombiningHalfMarks | combiningCyrillicTitlo |
--            combiningCyrillicPalatalization | combiningCyrillicDasiaPneumata |
--            combiningCyrillicPsiliPneumata | hebrewPointSheva |
--            hebrewPointHatafSegol | hebrewPointHatafPatah |
--            hebrewPointHatafQamats | hebrewPointHiriq | hebrewPointTsere |
--            hebrewPointSegol | hebrewPointPatah | hebrewPointQamats |
--            hebrewPointHolam | hebrewPointQubuts | hebrewPointDageshOrMapiq |
--            hebrewPointMeteg | hebrewPointRafe | hebrewPointShinDot |
--            hebrewPointSinDot | arabicFathatan | arabicDammatan | arabicKasratan
--            | arabicFatha | arabicDamma | arabicKasra | arabicShadda |
--            arabicSukun | arabicLetterSuperscriptAlef |
--            arabicSmallHighLigatureSadWithLamWithAlefMaksura |
--            arabicSmallHighLigatureQafWithLamWithAlefMaksura |
--            arabicSmallHighMeemInitialForm | arabicSmallHighLamAlef |
--            arabicSmallHighJeem | arabicSmallHighThreeDots | arabicSmallHighSeen
--            | arabicEndOfAyah | arabicStartOfRubElHizb |
--            arabicSmallHighRoundedZero | arabicSmallHighUprightRectangularZero |
--            arabicSmallHighDotlessHeadOfKhah | arabicSmallHighMeemIsolatedForm |
--            arabicSmallLowSeen | arabicSmallHighMadda | arabicSmallHighYeh |
--            arabicSmallHighNoon | arabicEmptyCentreLowStop |
--            arabicEmptyCentreHighStop | arabicRoundedHighStopWithFilledCentre |
--            arabicSmallLowMeem | devanagariSignCandrabindu |
--            devanagariSignAnusvara | devanagariSignVisarga | devanagariSignNukta
--            | devanagariSignAvagraha | devanagariSignAvagraha |
--            devanagariVowelSignAa | devanagariVowelSignI | devanagariVowelSignIi
--            | devanagariVowelSignU | devanagariVowelSignUu |
--            devanagariVowelSignVocalicR | devanagariVowelSignVocalicRr |
--            devanagariVowelSignCandraE | devanagariVowelSignShortE |
--            devanagariVowelSignE | devanagariVowelSignAi |
--            devanagariVowelSignCandraO | devanagariVowelSignShortO |
--            devanagariVowelSignO | devanagariVowelSignAu | devanagariSignVirama
--            | devanagariStressSignUdatta | devanagariStressSignAnudatta |
--            devanagariGraveAccent | devanagariAcuteAccent |
--            devanagariVowelSignVocalicL | devanagariVowelSignVocalicLl |
--            bengaliSignCandrabindu | bengaliSignAnusvara | bengaliSignVisarga |
--            bengaliSignNukta | bengaliVowelSignAa | bengaliVowelSignI |
--            bengaliVowelSignIi | bengaliVowelSignU | bengaliVowelSignUu |
--            bengaliVowelSignVocalicR | bengaliVowelSignVocalicRr |
--            bengaliVowelSignE | bengaliVowelSignAi | bengaliVowelSignO |
--            bengaliVowelSignAu | bengaliSignVirama | bengaliAuLengthMark |
--            bengaliVowelSignVocalicL | bengaliVowelSignVocalicLl |
--            gurmukhiSignBindi | gurmukhiSignNukta | gurmukhiVowelSignAa |
--            gurmukhiVowelSignI | gurmukhiVowelSignIi | gurmukhiVowelSignU |
--            gurmukhiVowelSignUu | gurmukhiVowelSignEe | gurmukhiVowelSignAi |
--            gurmukhiVowelSignOo | gurmukhiVowelSignAu | gurmukhiSignVirama |
--            gurmukhiTippi | gurmukhiAddak | gujaratiSignCandrabindu |
--            gujaratiSignAnusvara | gujaratiSignVisarga | gujaratiSignNukta |
--            gujaratiVowelSignAa | gujaratiVowelSignI | gujaratiVowelSignIi |
--            gujaratiVowelSignU | gujaratiVowelSignUu | gujaratiVowelSignVocalicR
--            | gujaratiVowelSignVocalicRr | gujaratiVowelSignCandraE |
--            gujaratiVowelSignE | gujaratiVowelSignAi | gujaratiVowelSignCandraO
--            | gujaratiVowelSignO | gujaratiVowelSignAu | gujaratiSignVirama |
--            oriyaSignCandrabindu | oriyaSignAnusvara | oriyaSignVisarga |
--            oriyaSignNukta | oriyaVowelSignAa | oriyaVowelSignI |
--            oriyaVowelSignIi | oriyaVowelSignU | oriyaVowelSignUu |
--            oriyaVowelSignVocalicR | oriyaVowelSignE | oriyaVowelSignAi |
--            oriyaVowelSignAu | oriyaSignVirama | oriyaAiLengthMark |
--            oriyaAuLengthMark | tamilSignAnusvara | tamilSignVisarga |
--            tamilVowelSignAa | tamilVowelSignI | tamilVowelSignIi |
--            tamilVowelSignU | tamilVowelSignUu | tamilVowelSignE |
--            tamilVowelSignEe | tamilVowelSignAi | tamilVowelSignO |
--            tamilVowelSignOo | tamilVowelSignAu | tamilSignVirama |
--            tamilAuLengthMark | teluguSignCandrabindu | teluguSignAnusvara |
--            teluguSignVisarga | teluguVowelSignAa | teluguVowelSignI |
--            teluguVowelSignIi | teluguVowelSignU | teluguVowelSignUu |
--            teluguVowelSignVocalicR | teluguVowelSignVocalicRr |
--            teluguVowelSignE | teluguVowelSignEe | teluguVowelSignAi |
--            teluguVowelSignO | teluguVowelSignOo | teluguVowelSignAu |
--            teluguSignVirama | teluguLengthMark | teluguAiLengthMark |
--            kannadaSignAnusvara | kannadaSignVisarga | kannadaVowelSignAa |
--            kannadaVowelSignI | kannadaVowelSignIi | kannadaVowelSignU |
--            kannadaVowelSignUu | kannadaVowelSignVocalicR |
--            kannadaVowelSignVocalicRr | kannadaVowelSignE | kannadaVowelSignEe |
--            kannadaVowelSignAi | kannadaVowelSignO | kannadaVowelSignOo |
--            kannadaVowelSignAu | kannadaSignVirama | kannadaLengthMark |
--            kannadaAiLengthMark | malayalamSignAnusvara | malayalamSignVisarga |
--            malayalamVowelSignAa | malayalamVowelSignI | malayalamVowelSignIi |
--            malayalamVowelSignU | malayalamVowelSignUu |
--            malayalamVowelSignVocalicR | malayalamVowelSignE |
--            malayalamVowelSignEe | malayalamVowelSignAi | malayalamVowelSignO |
--            malayalamVowelSignOo | malayalamVowelSignAu | malayalamSignVirama |
--            malayalamAuLengthMark | thaiCharacterMaiHan-akat |
--            thaiCharacterSaraI | thaiCharacterSaraIi | thaiCharacterSaraUe |
--            thaiCharacterSaraUee | thaiCharacterSaraU | thaiCharacterSaraUu |
--            thaiCharacterPhinthu | thaiCharacterMaitaikhu | thaiCharacterMaiEk |
--            thaiCharacterMaiTho | thaiCharacterMaiTri | thaiCharacterMaiChattawa
--            | thaiCharacterThanthakhat | thaiCharacterNikhahit |
--            thaiCharacterYamakkan | laoVowelSignMaiKan | laoVowelSignI |
--            laoVowelSignIi | laoVowelSignY | laoVowelSignYy | laoVowelSignU |
--            laoVowelSignUu | laoVowelSignMaiKon | laoSemivowelSignLo |
--            laoToneMaiEk | laoToneMaiTho | laoToneMaiTi | laoToneMaiCatawa |
--            laoCancellationMark | laoNiggahita | ideographicLevelToneMark |
--            ideographicRisingToneMark | ideographicDepartingToneMark |
--            ideographicEnteringToneMark | hangulSingleDotToneMark |
--            hangulDoubleDotToneMark | combiningKatakana-hiraganaVoicedSoundMark
--            | combiningKatakana-hiraganaSemi-voicedSoundMark |
--            hebrewPointJudeo-spanishVarika))

-- CombiningCharactersType-2 ::=
--   BMPString
--     (FROM (CombiningDiacriticalMarks | CombiningDiacriticalMarksForSymbols |
--            HangulJamo | CombiningHalfMarks | combiningCyrillicTitlo |
--            combiningCyrillicPalatalization | combiningCyrillicDasiaPneumata |
--            combiningCyrillicPsiliPneumata | devanagariSignNukta |
--            devanagariGraveAccent | devanagariAcuteAccent | bengaliSignNukta |
--            bengaliAuLengthMark | gurmukhiSignNukta | gurmukhiTippi |
--            gurmukhiAddak | gujaratiSignNukta | oriyaSignNukta |
--            oriyaAiLengthMark | oriyaAuLengthMark | tamilAuLengthMark |
--            teluguLengthMark | teluguAiLengthMark | kannadaLengthMark |
--            kannadaAiLengthMark | malayalamAuLengthMark |
--            ideographicLevelToneMark | ideographicRisingToneMark |
--            ideographicDepartingToneMark | ideographicEnteringToneMark |
--            hangulSingleDotToneMark | hangulDoubleDotToneMark |
--            combiningKatakana-hiraganaVoicedSoundMark |
--            combiningKatakana-hiraganaSemi-voicedSoundMark))

-- Level1 ::= BMPString(FROM (ALL EXCEPT CombiningCharacters))

-- Level2 ::= BMPString(FROM (ALL EXCEPT CombiningCharactersType-2))

-- Level3 ::= BMPString

-- -- Unicode General Category definitions
-- OtherControl ::= Cc

-- Cc ::=
--   BMPString
--     (FROM (null..informationSeparatorOne | delete |
--            breakPermittedHere..noBreakHere | nextLine..startOfString |
--            singleCharacterIntroducer..applicationProgramCommand))

-- OtherFormat ::= Cf

-- Cf ::=
--   UniversalString
--     (FROM (arabicEndOfAyah | syriacAbbreviationMark | mongolianVowelSeparator |
--            zeroWidthNon-joiner..right-to-leftMark |
--            left-to-rightEmbedding..right-to-leftOverride |
--            wordJoiner..invisibleSeparator |
--            inhibitSymmetricSwapping..nominalDigitShapes |
--            zeroWidthNo-breakSpace |
--            interlinearAnnotationAnchor..interlinearAnnotationTerminator |
--            musicalSymbolBeginBeam..musicalSymbolEndPhrase | languageTag |
--            tagSpace..cancelTag))

-- LetterLowercase ::= Ll

-- Ll ::=
--   UniversalString
--     (FROM (latinSmallLetterA..latinSmallLetterZ | feminineOrdinalIndicator |
--            microSign | masculineOrdinalIndicator |
--            latinSmallLetterSharpS..latinSmallLetterOWithDiaeresis |
--            latinSmallLetterOWithStroke..latinSmallLetterYWithDiaeresis |
--            latinSmallLetterAWithMacron | latinSmallLetterAWithBreve |
--            latinSmallLetterAWithOgonek | latinSmallLetterCWithAcute |
--            latinSmallLetterCWithCircumflex | latinSmallLetterCWithDotAbove |
--            latinSmallLetterCWithCaron | latinSmallLetterDWithCaron |
--            latinSmallLetterDWithStroke | latinSmallLetterEWithMacron |
--            latinSmallLetterEWithBreve | latinSmallLetterEWithDotAbove |
--            latinSmallLetterEWithOgonek | latinSmallLetterEWithCaron |
--            latinSmallLetterGWithCircumflex | latinSmallLetterGWithBreve |
--            latinSmallLetterGWithDotAbove | latinSmallLetterGWithCedilla |
--            latinSmallLetterHWithCircumflex | latinSmallLetterHWithStroke |
--            latinSmallLetterIWithTilde | latinSmallLetterIWithMacron |
--            latinSmallLetterIWithBreve | latinSmallLetterIWithOgonek |
--            latinSmallLetterDotlessI | latinSmallLigatureIj |
--            latinSmallLetterJWithCircumflex |
--            latinSmallLetterKWithCedilla..latinSmallLetterKra |
--            latinSmallLetterLWithAcute | latinSmallLetterLWithCedilla |
--            latinSmallLetterLWithCaron | latinSmallLetterLWithMiddleDot |
--            latinSmallLetterLWithStroke | latinSmallLetterNWithAcute |
--            latinSmallLetterNWithCedilla |
--            latinSmallLetterNWithCaron..latinSmallLetterNPrecededByApostrophe |
--            latinSmallLetterEng | latinSmallLetterOWithMacron |
--            latinSmallLetterOWithBreve | latinSmallLetterOWithDoubleAcute |
--            latinSmallLigatureOe | latinSmallLetterRWithAcute |
--            latinSmallLetterRWithCedilla | latinSmallLetterRWithCaron |
--            latinSmallLetterSWithAcute | latinSmallLetterSWithCircumflex |
--            latinSmallLetterSWithCedilla | latinSmallLetterSWithCaron |
--            latinSmallLetterTWithCedilla | latinSmallLetterTWithCaron |
--            latinSmallLetterTWithStroke | latinSmallLetterUWithTilde |
--            latinSmallLetterUWithMacron | latinSmallLetterUWithBreve |
--            latinSmallLetterUWithRingAbove | latinSmallLetterUWithDoubleAcute |
--            latinSmallLetterUWithOgonek | latinSmallLetterWWithCircumflex |
--            latinSmallLetterYWithCircumflex | latinSmallLetterZWithAcute |
--            latinSmallLetterZWithDotAbove |
--            latinSmallLetterZWithCaron..latinSmallLetterBWithStroke |
--            latinSmallLetterBWithTopbar | latinSmallLetterToneSix |
--            latinSmallLetterCWithHook |
--            latinSmallLetterDWithTopbar..latinSmallLetterTurnedDelta |
--            latinSmallLetterFWithHook | latinSmallLetterHv |
--            latinSmallLetterKWithHook..latinSmallLetterLambdaWithStroke |
--            latinSmallLetterNWithLongRightLeg | latinSmallLetterOWithHorn |
--            latinSmallLetterOi | latinSmallLetterPWithHook |
--            latinSmallLetterToneTwo |
--            latinLetterReversedEshLoop..latinSmallLetterTWithPalatalHook |
--            latinSmallLetterTWithHook | latinSmallLetterUWithHorn |
--            latinSmallLetterYWithHook | latinSmallLetterZWithStroke |
--            latinSmallLetterEzhReversed..latinSmallLetterEzhWithTail |
--            latinSmallLetterToneFive..latinLetterWynn |
--            latinSmallLetterDzWithCaron | latinSmallLetterLj |
--            latinSmallLetterNj | latinSmallLetterAWithCaron |
--            latinSmallLetterIWithCaron | latinSmallLetterOWithCaron |
--            latinSmallLetterUWithCaron | latinSmallLetterUWithDiaeresisAndMacron
--            | latinSmallLetterUWithDiaeresisAndAcute |
--            latinSmallLetterUWithDiaeresisAndCaron |
--            latinSmallLetterUWithDiaeresisAndGrave..latinSmallLetterTurnedE |
--            latinSmallLetterAWithDiaeresisAndMacron |
--            latinSmallLetterAWithDotAboveAndMacron |
--            latinSmallLetterAeWithMacron | latinSmallLetterGWithStroke |
--            latinSmallLetterGWithCaron | latinSmallLetterKWithCaron |
--            latinSmallLetterOWithOgonek | latinSmallLetterOWithOgonekAndMacron |
--            latinSmallLetterEzhWithCaron..latinSmallLetterJWithCaron |
--            latinSmallLetterDz | latinSmallLetterGWithAcute |
--            latinSmallLetterNWithGrave | latinSmallLetterAWithRingAboveAndAcute
--            | latinSmallLetterAeWithAcute | latinSmallLetterOWithStrokeAndAcute
--            | latinSmallLetterAWithDoubleGrave |
--            latinSmallLetterAWithInvertedBreve |
--            latinSmallLetterEWithDoubleGrave |
--            latinSmallLetterEWithInvertedBreve |
--            latinSmallLetterIWithDoubleGrave |
--            latinSmallLetterIWithInvertedBreve |
--            latinSmallLetterOWithDoubleGrave |
--            latinSmallLetterOWithInvertedBreve |
--            latinSmallLetterRWithDoubleGrave |
--            latinSmallLetterRWithInvertedBreve |
--            latinSmallLetterUWithDoubleGrave |
--            latinSmallLetterUWithInvertedBreve | latinSmallLetterSWithCommaBelow
--            | latinSmallLetterTWithCommaBelow | latinSmallLetterYogh |
--            latinSmallLetterHWithCaron | latinSmallLetterOu |
--            latinSmallLetterZWithHook | latinSmallLetterAWithDotAbove |
--            latinSmallLetterEWithCedilla |
--            latinSmallLetterOWithDiaeresisAndMacron |
--            latinSmallLetterOWithTildeAndMacron | latinSmallLetterOWithDotAbove
--            | latinSmallLetterOWithDotAboveAndMacron |
--            latinSmallLetterYWithMacron |
--            latinSmallLetterTurnedA..latinLetterBidentalPercussive |
--            greekSmallLetterIotaWithDialytikaAndTonos |
--            greekSmallLetterAlphaWithTonos..greekSmallLetterOmegaWithTonos |
--            greekBetaSymbol..greekThetaSymbol | greekPhiSymbol..greekKaiSymbol |
--            greekSmallLetterArchaicKoppa | greekSmallLetterStigma |
--            greekSmallLetterDigamma | greekSmallLetterKoppa |
--            greekSmallLetterSampi | copticSmallLetterShei | copticSmallLetterFei
--            | copticSmallLetterKhei | copticSmallLetterHori |
--            copticSmallLetterGangia | copticSmallLetterShima |
--            copticSmallLetterDei..greekLetterYot | greekLunateEpsilonSymbol |
--            cyrillicSmallLetterA..cyrillicSmallLetterDzhe |
--            cyrillicSmallLetterOmega | cyrillicSmallLetterYat |
--            cyrillicSmallLetterIotifiedE | cyrillicSmallLetterLittleYus |
--            cyrillicSmallLetterIotifiedLittleYus | cyrillicSmallLetterBigYus |
--            cyrillicSmallLetterIotifiedBigYus | cyrillicSmallLetterKsi |
--            cyrillicSmallLetterPsi | cyrillicSmallLetterFita |
--            cyrillicSmallLetterIzhitsa |
--            cyrillicSmallLetterIzhitsaWithDoubleGraveAccent |
--            cyrillicSmallLetterUk | cyrillicSmallLetterRoundOmega |
--            cyrillicSmallLetterOmegaWithTitlo | cyrillicSmallLetterOt |
--            cyrillicSmallLetterKoppa | cyrillicSmallLetterShortIWithTail |
--            cyrillicSmallLetterSemisoftSign | cyrillicSmallLetterErWithTick |
--            cyrillicSmallLetterGheWithUpturn | cyrillicSmallLetterGheWithStroke
--            | cyrillicSmallLetterGheWithMiddleHook |
--            cyrillicSmallLetterZheWithDescender |
--            cyrillicSmallLetterZeWithDescender |
--            cyrillicSmallLetterKaWithDescender |
--            cyrillicSmallLetterKaWithVerticalStroke |
--            cyrillicSmallLetterKaWithStroke | cyrillicSmallLetterBashkirKa |
--            cyrillicSmallLetterEnWithDescender | cyrillicSmallLigatureEnGhe |
--            cyrillicSmallLetterPeWithMiddleHook | cyrillicSmallLetterAbkhasianHa
--            | cyrillicSmallLetterEsWithDescender |
--            cyrillicSmallLetterTeWithDescender | cyrillicSmallLetterStraightU |
--            cyrillicSmallLetterStraightUWithStroke |
--            cyrillicSmallLetterHaWithDescender | cyrillicSmallLigatureTeTse |
--            cyrillicSmallLetterCheWithDescender |
--            cyrillicSmallLetterCheWithVerticalStroke | cyrillicSmallLetterShha |
--            cyrillicSmallLetterAbkhasianChe |
--            cyrillicSmallLetterAbkhasianCheWithDescender |
--            cyrillicSmallLetterZheWithBreve | cyrillicSmallLetterKaWithHook |
--            cyrillicSmallLetterElWithTail | cyrillicSmallLetterEnWithHook |
--            cyrillicSmallLetterEnWithTail | cyrillicSmallLetterKhakassianChe |
--            cyrillicSmallLetterEmWithTail | cyrillicSmallLetterAWithBreve |
--            cyrillicSmallLetterAWithDiaeresis | cyrillicSmallLigatureAIe |
--            cyrillicSmallLetterIeWithBreve | cyrillicSmallLetterSchwa |
--            cyrillicSmallLetterSchwaWithDiaeresis |
--            cyrillicSmallLetterZheWithDiaeresis |
--            cyrillicSmallLetterZeWithDiaeresis | cyrillicSmallLetterAbkhasianDze
--            | cyrillicSmallLetterIWithMacron | cyrillicSmallLetterIWithDiaeresis
--            | cyrillicSmallLetterOWithDiaeresis | cyrillicSmallLetterBarredO |
--            cyrillicSmallLetterBarredOWithDiaeresis |
--            cyrillicSmallLetterEWithDiaeresis | cyrillicSmallLetterUWithMacron |
--            cyrillicSmallLetterUWithDiaeresis |
--            cyrillicSmallLetterUWithDoubleAcute |
--            cyrillicSmallLetterCheWithDiaeresis |
--            cyrillicSmallLetterYeruWithDiaeresis | cyrillicSmallLetterKomiDe |
--            cyrillicSmallLetterKomiDje | cyrillicSmallLetterKomiZje |
--            cyrillicSmallLetterKomiDzje | cyrillicSmallLetterKomiLje |
--            cyrillicSmallLetterKomiNje | cyrillicSmallLetterKomiSje |
--            cyrillicSmallLetterKomiTje |
--            armenianSmallLetterAyb..armenianSmallLigatureEchYiwn |
--            latinSmallLetterAWithRingBelow | latinSmallLetterBWithDotAbove |
--            latinSmallLetterBWithDotBelow | latinSmallLetterBWithLineBelow |
--            latinSmallLetterCWithCedillaAndAcute | latinSmallLetterDWithDotAbove
--            | latinSmallLetterDWithDotBelow | latinSmallLetterDWithLineBelow |
--            latinSmallLetterDWithCedilla | latinSmallLetterDWithCircumflexBelow
--            | latinSmallLetterEWithMacronAndGrave |
--            latinSmallLetterEWithMacronAndAcute |
--            latinSmallLetterEWithCircumflexBelow |
--            latinSmallLetterEWithTildeBelow |
--            latinSmallLetterEWithCedillaAndBreve | latinSmallLetterFWithDotAbove
--            | latinSmallLetterGWithMacron | latinSmallLetterHWithDotAbove |
--            latinSmallLetterHWithDotBelow | latinSmallLetterHWithDiaeresis |
--            latinSmallLetterHWithCedilla | latinSmallLetterHWithBreveBelow |
--            latinSmallLetterIWithTildeBelow |
--            latinSmallLetterIWithDiaeresisAndAcute | latinSmallLetterKWithAcute
--            | latinSmallLetterKWithDotBelow | latinSmallLetterKWithLineBelow |
--            latinSmallLetterLWithDotBelow |
--            latinSmallLetterLWithDotBelowAndMacron |
--            latinSmallLetterLWithLineBelow |
--            latinSmallLetterLWithCircumflexBelow | latinSmallLetterMWithAcute |
--            latinSmallLetterMWithDotAbove | latinSmallLetterMWithDotBelow |
--            latinSmallLetterNWithDotAbove | latinSmallLetterNWithDotBelow |
--            latinSmallLetterNWithLineBelow |
--            latinSmallLetterNWithCircumflexBelow |
--            latinSmallLetterOWithTildeAndAcute |
--            latinSmallLetterOWithTildeAndDiaeresis |
--            latinSmallLetterOWithMacronAndGrave |
--            latinSmallLetterOWithMacronAndAcute | latinSmallLetterPWithAcute |
--            latinSmallLetterPWithDotAbove | latinSmallLetterRWithDotAbove |
--            latinSmallLetterRWithDotBelow |
--            latinSmallLetterRWithDotBelowAndMacron |
--            latinSmallLetterRWithLineBelow | latinSmallLetterSWithDotAbove |
--            latinSmallLetterSWithDotBelow |
--            latinSmallLetterSWithAcuteAndDotAbove |
--            latinSmallLetterSWithCaronAndDotAbove |
--            latinSmallLetterSWithDotBelowAndDotAbove |
--            latinSmallLetterTWithDotAbove | latinSmallLetterTWithDotBelow |
--            latinSmallLetterTWithLineBelow |
--            latinSmallLetterTWithCircumflexBelow |
--            latinSmallLetterUWithDiaeresisBelow |
--            latinSmallLetterUWithTildeBelow |
--            latinSmallLetterUWithCircumflexBelow |
--            latinSmallLetterUWithTildeAndAcute |
--            latinSmallLetterUWithMacronAndDiaeresis | latinSmallLetterVWithTilde
--            | latinSmallLetterVWithDotBelow | latinSmallLetterWWithGrave |
--            latinSmallLetterWWithAcute | latinSmallLetterWWithDiaeresis |
--            latinSmallLetterWWithDotAbove | latinSmallLetterWWithDotBelow |
--            latinSmallLetterXWithDotAbove | latinSmallLetterXWithDiaeresis |
--            latinSmallLetterYWithDotAbove | latinSmallLetterZWithCircumflex |
--            latinSmallLetterZWithDotBelow |
--            latinSmallLetterZWithLineBelow..latinSmallLetterLongSWithDotAbove |
--            latinSmallLetterAWithDotBelow | latinSmallLetterAWithHookAbove |
--            latinSmallLetterAWithCircumflexAndAcute |
--            latinSmallLetterAWithCircumflexAndGrave |
--            latinSmallLetterAWithCircumflexAndHookAbove |
--            latinSmallLetterAWithCircumflexAndTilde |
--            latinSmallLetterAWithCircumflexAndDotBelow |
--            latinSmallLetterAWithBreveAndAcute |
--            latinSmallLetterAWithBreveAndGrave |
--            latinSmallLetterAWithBreveAndHookAbove |
--            latinSmallLetterAWithBreveAndTilde |
--            latinSmallLetterAWithBreveAndDotBelow |
--            latinSmallLetterEWithDotBelow | latinSmallLetterEWithHookAbove |
--            latinSmallLetterEWithTilde | latinSmallLetterEWithCircumflexAndAcute
--            | latinSmallLetterEWithCircumflexAndGrave |
--            latinSmallLetterEWithCircumflexAndHookAbove |
--            latinSmallLetterEWithCircumflexAndTilde |
--            latinSmallLetterEWithCircumflexAndDotBelow |
--            latinSmallLetterIWithHookAbove | latinSmallLetterIWithDotBelow |
--            latinSmallLetterOWithDotBelow | latinSmallLetterOWithHookAbove |
--            latinSmallLetterOWithCircumflexAndAcute |
--            latinSmallLetterOWithCircumflexAndGrave |
--            latinSmallLetterOWithCircumflexAndHookAbove |
--            latinSmallLetterOWithCircumflexAndTilde |
--            latinSmallLetterOWithCircumflexAndDotBelow |
--            latinSmallLetterOWithHornAndAcute |
--            latinSmallLetterOWithHornAndGrave |
--            latinSmallLetterOWithHornAndHookAbove |
--            latinSmallLetterOWithHornAndTilde |
--            latinSmallLetterOWithHornAndDotBelow | latinSmallLetterUWithDotBelow
--            | latinSmallLetterUWithHookAbove | latinSmallLetterUWithHornAndAcute
--            | latinSmallLetterUWithHornAndGrave |
--            latinSmallLetterUWithHornAndHookAbove |
--            latinSmallLetterUWithHornAndTilde |
--            latinSmallLetterUWithHornAndDotBelow | latinSmallLetterYWithGrave |
--            latinSmallLetterYWithDotBelow | latinSmallLetterYWithHookAbove |
--            latinSmallLetterYWithTilde |
--            greekSmallLetterAlphaWithPsili..
--              greekSmallLetterAlphaWithDasiaAndPerispomeni |
--            greekSmallLetterEpsilonWithPsili..
--              greekSmallLetterEpsilonWithDasiaAndOxia |
--            greekSmallLetterEtaWithPsili..
--              greekSmallLetterEtaWithDasiaAndPerispomeni |
--            greekSmallLetterIotaWithPsili..
--              greekSmallLetterIotaWithDasiaAndPerispomeni |
--            greekSmallLetterOmicronWithPsili..
--              greekSmallLetterOmicronWithDasiaAndOxia |
--            greekSmallLetterUpsilonWithPsili..
--              greekSmallLetterUpsilonWithDasiaAndPerispomeni |
--            greekSmallLetterOmegaWithPsili..
--              greekSmallLetterOmegaWithDasiaAndPerispomeni |
--            greekSmallLetterAlphaWithVaria..greekSmallLetterOmegaWithOxia |
--            greekSmallLetterAlphaWithPsiliAndYpogegrammeni..
--              greekSmallLetterAlphaWithDasiaAndPerispomeniAndYpogegrammeni |
--            greekSmallLetterEtaWithPsiliAndYpogegrammeni..
--              greekSmallLetterEtaWithDasiaAndPerispomeniAndYpogegrammeni |
--            greekSmallLetterOmegaWithPsiliAndYpogegrammeni..
--              greekSmallLetterOmegaWithDasiaAndPerispomeniAndYpogegrammeni |
--            greekSmallLetterAlphaWithVrachy..
--              greekSmallLetterAlphaWithOxiaAndYpogegrammeni |
--            greekSmallLetterAlphaWithPerispomeni..
--              greekSmallLetterAlphaWithPerispomeniAndYpogegrammeni |
--            greekProsgegrammeni |
--            greekSmallLetterEtaWithVariaAndYpogegrammeni..
--              greekSmallLetterEtaWithOxiaAndYpogegrammeni |
--            greekSmallLetterEtaWithPerispomeni..
--              greekSmallLetterEtaWithPerispomeniAndYpogegrammeni |
--            greekSmallLetterIotaWithVrachy..
--              greekSmallLetterIotaWithDialytikaAndOxia |
--            greekSmallLetterIotaWithPerispomeni..
--              greekSmallLetterIotaWithDialytikaAndPerispomeni |
--            greekSmallLetterUpsilonWithVrachy..
--              greekSmallLetterUpsilonWithDialytikaAndPerispomeni |
--            greekSmallLetterOmegaWithVariaAndYpogegrammeni..
--              greekSmallLetterOmegaWithOxiaAndYpogegrammeni |
--            greekSmallLetterOmegaWithPerispomeni..
--              greekSmallLetterOmegaWithPerispomeniAndYpogegrammeni |
--            superscriptLatinSmallLetterI | superscriptLatinSmallLetterN |
--            scriptSmallG | planckConstant..planckConstantOverTwoPi |
--            scriptSmallL | scriptSmallE | scriptSmallO | informationSource |
--            double-struckSmallGamma |
--            double-struckItalicSmallD..double-struckItalicSmallJ |
--            latinSmallLigatureFf..latinSmallLigatureSt |
--            armenianSmallLigatureMenNow..armenianSmallLigatureMenXeh |
--            fullwidthLatinSmallLetterA..fullwidthLatinSmallLetterZ |
--            deseretSmallLetterLongI..deseretSmallLetterEng |
--            mathematicalBoldSmallA..mathematicalBoldSmallZ |
--            mathematicalItalicSmallA..mathematicalItalicSmallG |
--            mathematicalItalicSmallI..mathematicalItalicSmallZ |
--            mathematicalBoldItalicSmallA..mathematicalBoldItalicSmallZ |
--            mathematicalScriptSmallA..mathematicalScriptSmallD |
--            mathematicalScriptSmallF |
--            mathematicalScriptSmallH..mathematicalScriptSmallK |
--            mathematicalScriptSmallM..mathematicalScriptSmallN |
--            mathematicalScriptSmallP..mathematicalScriptSmallZ |
--            mathematicalBoldScriptSmallA..mathematicalBoldScriptSmallZ |
--            mathematicalFrakturSmallA..mathematicalFrakturSmallZ |
--            mathematicalDouble-struckSmallA..mathematicalDouble-struckSmallZ |
--            mathematicalBoldFrakturSmallA..mathematicalBoldFrakturSmallZ |
--            mathematicalSans-serifSmallA..mathematicalSans-serifSmallZ |
--            mathematicalSans-serifBoldSmallA..mathematicalSans-serifBoldSmallZ |
--            mathematicalSans-serifItalicSmallA..
--              mathematicalSans-serifItalicSmallZ |
--            mathematicalSans-serifBoldItalicSmallA..
--              mathematicalSans-serifBoldItalicSmallZ |
--            mathematicalMonospaceSmallA..mathematicalMonospaceSmallZ |
--            mathematicalBoldSmallAlpha..mathematicalBoldSmallOmega |
--            mathematicalBoldEpsilonSymbol..mathematicalBoldPiSymbol |
--            mathematicalItalicSmallAlpha..mathematicalItalicSmallOmega |
--            mathematicalItalicEpsilonSymbol..mathematicalItalicPiSymbol |
--            mathematicalBoldItalicSmallAlpha..mathematicalBoldItalicSmallOmega |
--            mathematicalBoldItalicEpsilonSymbol..mathematicalBoldItalicPiSymbol
--            |
--            mathematicalSans-serifBoldSmallAlpha..
--              mathematicalSans-serifBoldSmallOmega |
--            mathematicalSans-serifBoldEpsilonSymbol..
--              mathematicalSans-serifBoldPiSymbol |
--            mathematicalSans-serifBoldItalicSmallAlpha..
--              mathematicalSans-serifBoldItalicSmallOmega |
--            mathematicalSans-serifBoldItalicEpsilonSymbol..
--              mathematicalSans-serifBoldItalicPiSymbol))

-- LetterModifier ::= Lm

-- Lm ::=
--   BMPString
--     (FROM (modifierLetterSmallH..modifierLetterSmallY |
--            modifierLetterTurnedComma..modifierLetterReversedGlottalStop |
--            modifierLetterTriangularColon..modifierLetterHalfTriangularColon |
--            modifierLetterSmallGamma..modifierLetterSmallReversedGlottalStop |
--            modifierLetterDoubleApostrophe | greekYpogegrammeni |
--            armenianModifierLetterLeftHalfRing | arabicTatweel |
--            arabicSmallWaw..arabicSmallYeh | thaiCharacterMaiyamok | laoKoLa |
--            khmerSignLekToo | mongolianLetterTodoLongVowelSign |
--            ideographicIterationMark |
--            verticalKanaRepeatMark..verticalKanaRepeatMarkLowerHalf |
--            verticalIdeographicIterationMark |
--            hiraganaIterationMark..hiraganaVoicedIterationMark |
--            katakana-hiraganaProlongedSoundMark..katakanaVoicedIterationMark |
--            halfwidthKatakana-hiraganaProlongedSoundMark |
--            halfwidthKatakanaVoicedSoundMark..
--              halfwidthKatakanaSemi-voicedSoundMark))

-- LetterOther ::= Lo

-- Lo ::=
--   UniversalString
--     (FROM (latinLetterTwoWithStroke |
--            latinLetterDentalClick..latinLetterRetroflexClick |
--            hebrewLetterAlef..hebrewLetterTav |
--            hebrewLigatureYiddishDoubleVav..hebrewLigatureYiddishDoubleYod |
--            arabicLetterHamza..arabicLetterGhain |
--            arabicLetterFeh..arabicLetterYeh |
--            arabicLetterDotlessBeh..arabicLetterDotlessQaf |
--            arabicLetterAlefWasla..arabicLetterYehBarreeWithHamzaAbove |
--            arabicLetterAe |
--            arabicLetterSheenWithDotBelow..arabicLetterGhainWithDotBelow |
--            syriacLetterAlaph | syriacLetterBeth..syriacLetterTaw |
--            thaanaLetterHaa..thaanaLetterWaavu | thaanaLetterNaa |
--            devanagariLetterA..devanagariLetterHa | devanagariSignAvagraha |
--            devanagariOm | devanagariLetterQa..devanagariLetterVocalicLl |
--            bengaliLetterA..bengaliLetterVocalicL |
--            bengaliLetterE..bengaliLetterAi | bengaliLetterO..bengaliLetterNa |
--            bengaliLetterPa..bengaliLetterRa | bengaliLetterLa |
--            bengaliLetterSha..bengaliLetterHa |
--            bengaliLetterRra..bengaliLetterRha |
--            bengaliLetterYya..bengaliLetterVocalicLl |
--            bengaliLetterRaWithMiddleDiagonal..bengaliLetterRaWithLowerDiagonal
--            | gurmukhiLetterA..gurmukhiLetterUu |
--            gurmukhiLetterEe..gurmukhiLetterAi |
--            gurmukhiLetterOo..gurmukhiLetterNa |
--            gurmukhiLetterPa..gurmukhiLetterRa |
--            gurmukhiLetterLa..gurmukhiLetterLla |
--            gurmukhiLetterVa..gurmukhiLetterSha |
--            gurmukhiLetterSa..gurmukhiLetterHa |
--            gurmukhiLetterKhha..gurmukhiLetterRra | gurmukhiLetterFa |
--            gurmukhiIri..gurmukhiEkOnkar |
--            gujaratiLetterA..gujaratiLetterVocalicR | gujaratiVowelCandraE |
--            gujaratiLetterE..gujaratiVowelCandraO |
--            gujaratiLetterO..gujaratiLetterNa |
--            gujaratiLetterPa..gujaratiLetterRa |
--            gujaratiLetterLa..gujaratiLetterLla |
--            gujaratiLetterVa..gujaratiLetterHa | gujaratiSignAvagraha |
--            gujaratiOm | gujaratiLetterVocalicRr |
--            oriyaLetterA..oriyaLetterVocalicL | oriyaLetterE..oriyaLetterAi |
--            oriyaLetterO..oriyaLetterNa | oriyaLetterPa..oriyaLetterRa |
--            oriyaLetterLa..oriyaLetterLla | oriyaLetterSha..oriyaLetterHa |
--            oriyaSignAvagraha | oriyaLetterRra..oriyaLetterRha |
--            oriyaLetterYya..oriyaLetterVocalicLl | tamilSignVisarga |
--            tamilLetterA..tamilLetterUu | tamilLetterE..tamilLetterAi |
--            tamilLetterO..tamilLetterKa | tamilLetterNga..tamilLetterCa |
--            tamilLetterJa | tamilLetterNya..tamilLetterTta |
--            tamilLetterNna..tamilLetterTa | tamilLetterNa..tamilLetterPa |
--            tamilLetterMa..tamilLetterVa | tamilLetterSsa..tamilLetterHa |
--            teluguLetterA..teluguLetterVocalicL | teluguLetterE..teluguLetterAi
--            | teluguLetterO..teluguLetterNa | teluguLetterPa..teluguLetterLla |
--            teluguLetterVa..teluguLetterHa |
--            teluguLetterVocalicRr..teluguLetterVocalicLl |
--            kannadaLetterA..kannadaLetterVocalicL |
--            kannadaLetterE..kannadaLetterAi | kannadaLetterO..kannadaLetterNa |
--            kannadaLetterPa..kannadaLetterLla | kannadaLetterVa..kannadaLetterHa
--            | kannadaLetterFa | kannadaLetterVocalicRr..kannadaLetterVocalicLl |
--            malayalamLetterA..malayalamLetterVocalicL |
--            malayalamLetterE..malayalamLetterAi |
--            malayalamLetterO..malayalamLetterNa |
--            malayalamLetterPa..malayalamLetterHa |
--            malayalamLetterVocalicRr..malayalamLetterVocalicLl |
--            sinhalaLetterAyanna..sinhalaLetterAuyanna |
--            sinhalaLetterAlpapraanaKayanna..sinhalaLetterDantajaNayanna |
--            sinhalaLetterSanyakaDayanna..sinhalaLetterRayanna |
--            sinhalaLetterDantajaLayanna |
--            sinhalaLetterVayanna..sinhalaLetterFayanna |
--            thaiCharacterKoKai..thaiCharacterSaraA |
--            thaiCharacterSaraAa..thaiCharacterSaraAm |
--            thaiCharacterSaraE..thaiCharacterLakkhangyao |
--            laoLetterKo..laoLetterKhoSung | laoLetterKhoTam |
--            laoLetterNgo..laoLetterCo | laoLetterSoTam | laoLetterNyo |
--            laoLetterDo..laoLetterThoTam | laoLetterNo..laoLetterFoSung |
--            laoLetterMo..laoLetterLoLing | laoLetterLoLoot | laoLetterWo |
--            laoLetterSoSung..laoLetterHoSung | laoLetterO..laoVowelSignA |
--            laoVowelSignAa..laoVowelSignAm | laoSemivowelSignNyo |
--            laoVowelSignE..laoVowelSignAi | laoHoNo..laoHoMo | tibetanSyllableOm
--            | tibetanLetterKa..tibetanLetterJa |
--            tibetanLetterNya..tibetanLetterFixed-formRa |
--            tibetanSignLceTsaCan..tibetanSignGruMedRgyings |
--            myanmarLetterKa..myanmarLetterA | myanmarLetterI..myanmarLetterE |
--            myanmarLetterO..myanmarLetterAu |
--            myanmarLetterSha..myanmarLetterVocalicLl |
--            georgianLetterAn..georgianLetterElifi |
--            hangulChoseongKiyeok..hangulChoseongYeorinhieuh |
--            hangulChoseongFiller..hangulJungseongSsangaraea |
--            hangulJongseongKiyeok..hangulJongseongYeorinhieuh |
--            ethiopicSyllableHa..ethiopicSyllableHo |
--            ethiopicSyllableLa..ethiopicSyllableQo | ethiopicSyllableQwa |
--            ethiopicSyllableQwi..ethiopicSyllableQwe |
--            ethiopicSyllableQha..ethiopicSyllableQho | ethiopicSyllableQhwa |
--            ethiopicSyllableQhwi..ethiopicSyllableQhwe |
--            ethiopicSyllableBa..ethiopicSyllableXo | ethiopicSyllableXwa |
--            ethiopicSyllableXwi..ethiopicSyllableXwe |
--            ethiopicSyllableNa..ethiopicSyllableKo | ethiopicSyllableKwa |
--            ethiopicSyllableKwi..ethiopicSyllableKwe |
--            ethiopicSyllableKxa..ethiopicSyllableKxo | ethiopicSyllableKxwa |
--            ethiopicSyllableKxwi..ethiopicSyllableKxwe |
--            ethiopicSyllableWa..ethiopicSyllableWo |
--            ethiopicSyllablePharyngealA..ethiopicSyllablePharyngealO |
--            ethiopicSyllableZa..ethiopicSyllableYo |
--            ethiopicSyllableDa..ethiopicSyllableGo | ethiopicSyllableGwa |
--            ethiopicSyllableGwi..ethiopicSyllableGwe |
--            ethiopicSyllableGga..ethiopicSyllableGgo |
--            ethiopicSyllableTha..ethiopicSyllableTzo |
--            ethiopicSyllableFa..ethiopicSyllableFya |
--            cherokeeLetterA..cherokeeLetterYv |
--            canadianSyllabicsE..canadianSyllabicsCarrierTtsa |
--            canadianSyllabicsQai..canadianSyllabicsNngaa |
--            oghamLetterBeith..oghamLetterPeith |
--            runicLetterFehuFeohFeF..runicLetterX |
--            tagalogLetterA..tagalogLetterYa | tagalogLetterLa..tagalogLetterHa |
--            hanunooLetterA..hanunooLetterHa | buhidLetterA..buhidLetterHa |
--            tagbanwaLetterA..tagbanwaLetterYa |
--            tagbanwaLetterLa..tagbanwaLetterSa |
--            khmerLetterKa..khmerIndependentVowelQau | khmerSignAvakrahasanya |
--            mongolianLetterA..mongolianLetterChi |
--            mongolianLetterTodoE..mongolianLetterManchuZha |
--            mongolianLetterAliGaliAnusvaraOne..mongolianLetterManchuAliGaliBha |
--            alefSymbol..daletSymbol | ideographicClosingMark | masuMark |
--            hiraganaLetterSmallA..hiraganaLetterSmallKe | hiraganaDigraphYori |
--            katakanaLetterSmallA..katakanaLetterVo | katakanaDigraphKoto |
--            bopomofoLetterB..bopomofoLetterGn |
--            hangulLetterKiyeok..hangulLetterAraeae |
--            bopomofoLetterBu..bopomofoFinalLetterH |
--            katakanaLetterSmallKu..katakanaLetterSmallRo |
--            yiSyllableIt..yiSyllableYyr |
--            cjkCompatibilityIdeograph-f900..cjkCompatibilityIdeograph-fa2d |
--            cjkCompatibilityIdeograph-fa30..cjkCompatibilityIdeograph-fa6a |
--            hebrewLetterYodWithHiriq |
--            hebrewLigatureYiddishYodYodPatah..hebrewLetterWideTav |
--            hebrewLetterShinWithShinDot..hebrewLetterZayinWithDagesh |
--            hebrewLetterTetWithDagesh..hebrewLetterLamedWithDagesh |
--            hebrewLetterMemWithDagesh |
--            hebrewLetterNunWithDagesh..hebrewLetterSamekhWithDagesh |
--            hebrewLetterFinalPeWithDagesh..hebrewLetterPeWithDagesh |
--            hebrewLetterTsadiWithDagesh..
--              arabicLetterYehBarreeWithHamzaAboveFinalForm |
--            arabicLetterNgIsolatedForm..
--              arabicLigatureAlefWithFathatanIsolatedForm |
--            arabicLigatureTehWithJeemWithMeemInitialForm..
--              arabicLigatureMeemWithKhahWithMeemInitialForm |
--            arabicLigatureMeemWithJeemWithKhahInitialForm..
--              arabicLigatureNoonWithJeemWithYehFinalForm |
--            arabicLigatureSallaUsedAsKoranicStopSignIsolatedForm..
--              arabicLigatureJallajalalouhou |
--            arabicFathatanIsolatedForm..arabicKasratanIsolatedForm |
--            arabicFathaIsolatedForm..arabicLigatureLamWithAlefFinalForm |
--            halfwidthKatakanaLetterWo..halfwidthKatakanaLetterSmallTu |
--            halfwidthKatakanaLetterA..halfwidthKatakanaLetterN |
--            halfwidthHangulFiller..halfwidthHangulLetterHieuh |
--            halfwidthHangulLetterA..halfwidthHangulLetterE |
--            halfwidthHangulLetterYeo..halfwidthHangulLetterOe |
--            halfwidthHangulLetterYo..halfwidthHangulLetterYu |
--            halfwidthHangulLetterEu..halfwidthHangulLetterI |
--            oldItalicLetterA..oldItalicLetterUu |
--            gothicLetterAhsa..gothicLetterOthal |
--            cjkCompatibilityIdeograph-2f800..cjkCompatibilityIdeograph-2fa1d))

-- LetterTitlecase ::= Lt

-- Lt ::=
--   BMPString
--     (FROM (latinCapitalLetterDWithSmallLetterZWithCaron |
--            latinCapitalLetterLWithSmallLetterJ |
--            latinCapitalLetterNWithSmallLetterJ |
--            latinCapitalLetterDWithSmallLetterZ |
--            greekCapitalLetterAlphaWithPsiliAndProsgegrammeni..
--              greekCapitalLetterAlphaWithDasiaAndPerispomeniAndProsgegrammeni |
--            greekCapitalLetterEtaWithPsiliAndProsgegrammeni..
--              greekCapitalLetterEtaWithDasiaAndPerispomeniAndProsgegrammeni |
--            greekCapitalLetterOmegaWithPsiliAndProsgegrammeni..
--              greekCapitalLetterOmegaWithDasiaAndPerispomeniAndProsgegrammeni |
--            greekCapitalLetterAlphaWithProsgegrammeni |
--            greekCapitalLetterEtaWithProsgegrammeni |
--            greekCapitalLetterOmegaWithProsgegrammeni))

-- LetterUppercase ::= Lu

-- Lu ::=
--   UniversalString
--     (FROM (latinCapitalLetterA..latinCapitalLetterZ |
--            latinCapitalLetterAWithGrave..latinCapitalLetterOWithDiaeresis |
--            latinCapitalLetterOWithStroke..latinCapitalLetterThorn |
--            latinCapitalLetterAWithMacron | latinCapitalLetterAWithBreve |
--            latinCapitalLetterAWithOgonek | latinCapitalLetterCWithAcute |
--            latinCapitalLetterCWithCircumflex | latinCapitalLetterCWithDotAbove
--            | latinCapitalLetterCWithCaron | latinCapitalLetterDWithCaron |
--            latinCapitalLetterDWithStroke | latinCapitalLetterEWithMacron |
--            latinCapitalLetterEWithBreve | latinCapitalLetterEWithDotAbove |
--            latinCapitalLetterEWithOgonek | latinCapitalLetterEWithCaron |
--            latinCapitalLetterGWithCircumflex | latinCapitalLetterGWithBreve |
--            latinCapitalLetterGWithDotAbove | latinCapitalLetterGWithCedilla |
--            latinCapitalLetterHWithCircumflex | latinCapitalLetterHWithStroke |
--            latinCapitalLetterIWithTilde | latinCapitalLetterIWithMacron |
--            latinCapitalLetterIWithBreve | latinCapitalLetterIWithOgonek |
--            latinCapitalLetterIWithDotAbove | latinCapitalLigatureIj |
--            latinCapitalLetterJWithCircumflex | latinCapitalLetterKWithCedilla |
--            latinCapitalLetterLWithAcute | latinCapitalLetterLWithCedilla |
--            latinCapitalLetterLWithCaron | latinCapitalLetterLWithMiddleDot |
--            latinCapitalLetterLWithStroke | latinCapitalLetterNWithAcute |
--            latinCapitalLetterNWithCedilla | latinCapitalLetterNWithCaron |
--            latinCapitalLetterEng | latinCapitalLetterOWithMacron |
--            latinCapitalLetterOWithBreve | latinCapitalLetterOWithDoubleAcute |
--            latinCapitalLigatureOe | latinCapitalLetterRWithAcute |
--            latinCapitalLetterRWithCedilla | latinCapitalLetterRWithCaron |
--            latinCapitalLetterSWithAcute | latinCapitalLetterSWithCircumflex |
--            latinCapitalLetterSWithCedilla | latinCapitalLetterSWithCaron |
--            latinCapitalLetterTWithCedilla | latinCapitalLetterTWithCaron |
--            latinCapitalLetterTWithStroke | latinCapitalLetterUWithTilde |
--            latinCapitalLetterUWithMacron | latinCapitalLetterUWithBreve |
--            latinCapitalLetterUWithRingAbove |
--            latinCapitalLetterUWithDoubleAcute | latinCapitalLetterUWithOgonek |
--            latinCapitalLetterWWithCircumflex |
--            latinCapitalLetterYWithCircumflex |
--            latinCapitalLetterYWithDiaeresis..latinCapitalLetterZWithAcute |
--            latinCapitalLetterZWithDotAbove | latinCapitalLetterZWithCaron |
--            latinCapitalLetterBWithHook..latinCapitalLetterBWithTopbar |
--            latinCapitalLetterToneSix |
--            latinCapitalLetterOpenO..latinCapitalLetterCWithHook |
--            latinCapitalLetterAfricanD..latinCapitalLetterDWithTopbar |
--            latinCapitalLetterReversedE..latinCapitalLetterFWithHook |
--            latinCapitalLetterGWithHook..latinCapitalLetterGamma |
--            latinCapitalLetterIota..latinCapitalLetterKWithHook |
--            latinCapitalLetterTurnedM..latinCapitalLetterNWithLeftHook |
--            latinCapitalLetterOWithMiddleTilde..latinCapitalLetterOWithHorn |
--            latinCapitalLetterOi | latinCapitalLetterPWithHook |
--            latinLetterYr..latinCapitalLetterToneTwo | latinCapitalLetterEsh |
--            latinCapitalLetterTWithHook |
--            latinCapitalLetterTWithRetroflexHook..latinCapitalLetterUWithHorn |
--            latinCapitalLetterUpsilon..latinCapitalLetterYWithHook |
--            latinCapitalLetterZWithStroke |
--            latinCapitalLetterEzh..latinCapitalLetterEzhReversed |
--            latinCapitalLetterToneFive | latinCapitalLetterDzWithCaron |
--            latinCapitalLetterLj | latinCapitalLetterNj |
--            latinCapitalLetterAWithCaron | latinCapitalLetterIWithCaron |
--            latinCapitalLetterOWithCaron | latinCapitalLetterUWithCaron |
--            latinCapitalLetterUWithDiaeresisAndMacron |
--            latinCapitalLetterUWithDiaeresisAndAcute |
--            latinCapitalLetterUWithDiaeresisAndCaron |
--            latinCapitalLetterUWithDiaeresisAndGrave |
--            latinCapitalLetterAWithDiaeresisAndMacron |
--            latinCapitalLetterAWithDotAboveAndMacron |
--            latinCapitalLetterAeWithMacron | latinCapitalLetterGWithStroke |
--            latinCapitalLetterGWithCaron | latinCapitalLetterKWithCaron |
--            latinCapitalLetterOWithOgonek |
--            latinCapitalLetterOWithOgonekAndMacron |
--            latinCapitalLetterEzhWithCaron | latinCapitalLetterDz |
--            latinCapitalLetterGWithAcute |
--            latinCapitalLetterHwair..latinCapitalLetterNWithGrave |
--            latinCapitalLetterAWithRingAboveAndAcute |
--            latinCapitalLetterAeWithAcute |
--            latinCapitalLetterOWithStrokeAndAcute |
--            latinCapitalLetterAWithDoubleGrave |
--            latinCapitalLetterAWithInvertedBreve |
--            latinCapitalLetterEWithDoubleGrave |
--            latinCapitalLetterEWithInvertedBreve |
--            latinCapitalLetterIWithDoubleGrave |
--            latinCapitalLetterIWithInvertedBreve |
--            latinCapitalLetterOWithDoubleGrave |
--            latinCapitalLetterOWithInvertedBreve |
--            latinCapitalLetterRWithDoubleGrave |
--            latinCapitalLetterRWithInvertedBreve |
--            latinCapitalLetterUWithDoubleGrave |
--            latinCapitalLetterUWithInvertedBreve |
--            latinCapitalLetterSWithCommaBelow |
--            latinCapitalLetterTWithCommaBelow | latinCapitalLetterYogh |
--            latinCapitalLetterHWithCaron | latinCapitalLetterNWithLongRightLeg |
--            latinCapitalLetterOu | latinCapitalLetterZWithHook |
--            latinCapitalLetterAWithDotAbove | latinCapitalLetterEWithCedilla |
--            latinCapitalLetterOWithDiaeresisAndMacron |
--            latinCapitalLetterOWithTildeAndMacron |
--            latinCapitalLetterOWithDotAbove |
--            latinCapitalLetterOWithDotAboveAndMacron |
--            latinCapitalLetterYWithMacron | greekCapitalLetterAlphaWithTonos |
--            greekCapitalLetterEpsilonWithTonos..greekCapitalLetterIotaWithTonos
--            | greekCapitalLetterOmicronWithTonos |
--            greekCapitalLetterUpsilonWithTonos..greekCapitalLetterOmegaWithTonos
--            | greekCapitalLetterAlpha..greekCapitalLetterRho |
--            greekCapitalLetterSigma..greekCapitalLetterUpsilonWithDialytika |
--            greekUpsilonWithHookSymbol..greekUpsilonWithDiaeresisAndHookSymbol |
--            greekLetterArchaicKoppa | greekLetterStigma | greekLetterDigamma |
--            greekLetterKoppa | greekLetterSampi | copticCapitalLetterShei |
--            copticCapitalLetterFei | copticCapitalLetterKhei |
--            copticCapitalLetterHori | copticCapitalLetterGangia |
--            copticCapitalLetterShima | copticCapitalLetterDei |
--            greekCapitalThetaSymbol |
--            cyrillicCapitalLetterIeWithGrave..cyrillicCapitalLetterYa |
--            cyrillicCapitalLetterOmega | cyrillicCapitalLetterYat |
--            cyrillicCapitalLetterIotifiedE | cyrillicCapitalLetterLittleYus |
--            cyrillicCapitalLetterIotifiedLittleYus | cyrillicCapitalLetterBigYus
--            | cyrillicCapitalLetterIotifiedBigYus | cyrillicCapitalLetterKsi |
--            cyrillicCapitalLetterPsi | cyrillicCapitalLetterFita |
--            cyrillicCapitalLetterIzhitsa |
--            cyrillicCapitalLetterIzhitsaWithDoubleGraveAccent |
--            cyrillicCapitalLetterUk | cyrillicCapitalLetterRoundOmega |
--            cyrillicCapitalLetterOmegaWithTitlo | cyrillicCapitalLetterOt |
--            cyrillicCapitalLetterKoppa | cyrillicCapitalLetterShortIWithTail |
--            cyrillicCapitalLetterSemisoftSign | cyrillicCapitalLetterErWithTick
--            | cyrillicCapitalLetterGheWithUpturn |
--            cyrillicCapitalLetterGheWithStroke |
--            cyrillicCapitalLetterGheWithMiddleHook |
--            cyrillicCapitalLetterZheWithDescender |
--            cyrillicCapitalLetterZeWithDescender |
--            cyrillicCapitalLetterKaWithDescender |
--            cyrillicCapitalLetterKaWithVerticalStroke |
--            cyrillicCapitalLetterKaWithStroke | cyrillicCapitalLetterBashkirKa |
--            cyrillicCapitalLetterEnWithDescender | cyrillicCapitalLigatureEnGhe
--            | cyrillicCapitalLetterPeWithMiddleHook |
--            cyrillicCapitalLetterAbkhasianHa |
--            cyrillicCapitalLetterEsWithDescender |
--            cyrillicCapitalLetterTeWithDescender |
--            cyrillicCapitalLetterStraightU |
--            cyrillicCapitalLetterStraightUWithStroke |
--            cyrillicCapitalLetterHaWithDescender | cyrillicCapitalLigatureTeTse
--            | cyrillicCapitalLetterCheWithDescender |
--            cyrillicCapitalLetterCheWithVerticalStroke |
--            cyrillicCapitalLetterShha | cyrillicCapitalLetterAbkhasianChe |
--            cyrillicCapitalLetterAbkhasianCheWithDescender |
--            cyrillicLetterPalochka..cyrillicCapitalLetterZheWithBreve |
--            cyrillicCapitalLetterKaWithHook | cyrillicCapitalLetterElWithTail |
--            cyrillicCapitalLetterEnWithHook | cyrillicCapitalLetterEnWithTail |
--            cyrillicCapitalLetterKhakassianChe | cyrillicCapitalLetterEmWithTail
--            | cyrillicCapitalLetterAWithBreve |
--            cyrillicCapitalLetterAWithDiaeresis | cyrillicCapitalLigatureAIe |
--            cyrillicCapitalLetterIeWithBreve | cyrillicCapitalLetterSchwa |
--            cyrillicCapitalLetterSchwaWithDiaeresis |
--            cyrillicCapitalLetterZheWithDiaeresis |
--            cyrillicCapitalLetterZeWithDiaeresis |
--            cyrillicCapitalLetterAbkhasianDze | cyrillicCapitalLetterIWithMacron
--            | cyrillicCapitalLetterIWithDiaeresis |
--            cyrillicCapitalLetterOWithDiaeresis | cyrillicCapitalLetterBarredO |
--            cyrillicCapitalLetterBarredOWithDiaeresis |
--            cyrillicCapitalLetterEWithDiaeresis |
--            cyrillicCapitalLetterUWithMacron |
--            cyrillicCapitalLetterUWithDiaeresis |
--            cyrillicCapitalLetterUWithDoubleAcute |
--            cyrillicCapitalLetterCheWithDiaeresis |
--            cyrillicCapitalLetterYeruWithDiaeresis | cyrillicCapitalLetterKomiDe
--            | cyrillicCapitalLetterKomiDje | cyrillicCapitalLetterKomiZje |
--            cyrillicCapitalLetterKomiDzje | cyrillicCapitalLetterKomiLje |
--            cyrillicCapitalLetterKomiNje | cyrillicCapitalLetterKomiSje |
--            cyrillicCapitalLetterKomiTje |
--            armenianCapitalLetterAyb..armenianCapitalLetterFeh |
--            georgianCapitalLetterAn..georgianCapitalLetterHoe |
--            latinCapitalLetterAWithRingBelow | latinCapitalLetterBWithDotAbove |
--            latinCapitalLetterBWithDotBelow | latinCapitalLetterBWithLineBelow |
--            latinCapitalLetterCWithCedillaAndAcute |
--            latinCapitalLetterDWithDotAbove | latinCapitalLetterDWithDotBelow |
--            latinCapitalLetterDWithLineBelow | latinCapitalLetterDWithCedilla |
--            latinCapitalLetterDWithCircumflexBelow |
--            latinCapitalLetterEWithMacronAndGrave |
--            latinCapitalLetterEWithMacronAndAcute |
--            latinCapitalLetterEWithCircumflexBelow |
--            latinCapitalLetterEWithTildeBelow |
--            latinCapitalLetterEWithCedillaAndBreve |
--            latinCapitalLetterFWithDotAbove | latinCapitalLetterGWithMacron |
--            latinCapitalLetterHWithDotAbove | latinCapitalLetterHWithDotBelow |
--            latinCapitalLetterHWithDiaeresis | latinCapitalLetterHWithCedilla |
--            latinCapitalLetterHWithBreveBelow |
--            latinCapitalLetterIWithTildeBelow |
--            latinCapitalLetterIWithDiaeresisAndAcute |
--            latinCapitalLetterKWithAcute | latinCapitalLetterKWithDotBelow |
--            latinCapitalLetterKWithLineBelow | latinCapitalLetterLWithDotBelow |
--            latinCapitalLetterLWithDotBelowAndMacron |
--            latinCapitalLetterLWithLineBelow |
--            latinCapitalLetterLWithCircumflexBelow |
--            latinCapitalLetterMWithAcute | latinCapitalLetterMWithDotAbove |
--            latinCapitalLetterMWithDotBelow | latinCapitalLetterNWithDotAbove |
--            latinCapitalLetterNWithDotBelow | latinCapitalLetterNWithLineBelow |
--            latinCapitalLetterNWithCircumflexBelow |
--            latinCapitalLetterOWithTildeAndAcute |
--            latinCapitalLetterOWithTildeAndDiaeresis |
--            latinCapitalLetterOWithMacronAndGrave |
--            latinCapitalLetterOWithMacronAndAcute | latinCapitalLetterPWithAcute
--            | latinCapitalLetterPWithDotAbove | latinCapitalLetterRWithDotAbove
--            | latinCapitalLetterRWithDotBelow |
--            latinCapitalLetterRWithDotBelowAndMacron |
--            latinCapitalLetterRWithLineBelow | latinCapitalLetterSWithDotAbove |
--            latinCapitalLetterSWithDotBelow |
--            latinCapitalLetterSWithAcuteAndDotAbove |
--            latinCapitalLetterSWithCaronAndDotAbove |
--            latinCapitalLetterSWithDotBelowAndDotAbove |
--            latinCapitalLetterTWithDotAbove | latinCapitalLetterTWithDotBelow |
--            latinCapitalLetterTWithLineBelow |
--            latinCapitalLetterTWithCircumflexBelow |
--            latinCapitalLetterUWithDiaeresisBelow |
--            latinCapitalLetterUWithTildeBelow |
--            latinCapitalLetterUWithCircumflexBelow |
--            latinCapitalLetterUWithTildeAndAcute |
--            latinCapitalLetterUWithMacronAndDiaeresis |
--            latinCapitalLetterVWithTilde | latinCapitalLetterVWithDotBelow |
--            latinCapitalLetterWWithGrave | latinCapitalLetterWWithAcute |
--            latinCapitalLetterWWithDiaeresis | latinCapitalLetterWWithDotAbove |
--            latinCapitalLetterWWithDotBelow | latinCapitalLetterXWithDotAbove |
--            latinCapitalLetterXWithDiaeresis | latinCapitalLetterYWithDotAbove |
--            latinCapitalLetterZWithCircumflex | latinCapitalLetterZWithDotBelow
--            | latinCapitalLetterZWithLineBelow | latinCapitalLetterAWithDotBelow
--            | latinCapitalLetterAWithHookAbove |
--            latinCapitalLetterAWithCircumflexAndAcute |
--            latinCapitalLetterAWithCircumflexAndGrave |
--            latinCapitalLetterAWithCircumflexAndHookAbove |
--            latinCapitalLetterAWithCircumflexAndTilde |
--            latinCapitalLetterAWithCircumflexAndDotBelow |
--            latinCapitalLetterAWithBreveAndAcute |
--            latinCapitalLetterAWithBreveAndGrave |
--            latinCapitalLetterAWithBreveAndHookAbove |
--            latinCapitalLetterAWithBreveAndTilde |
--            latinCapitalLetterAWithBreveAndDotBelow |
--            latinCapitalLetterEWithDotBelow | latinCapitalLetterEWithHookAbove |
--            latinCapitalLetterEWithTilde |
--            latinCapitalLetterEWithCircumflexAndAcute |
--            latinCapitalLetterEWithCircumflexAndGrave |
--            latinCapitalLetterEWithCircumflexAndHookAbove |
--            latinCapitalLetterEWithCircumflexAndTilde |
--            latinCapitalLetterEWithCircumflexAndDotBelow |
--            latinCapitalLetterIWithHookAbove | latinCapitalLetterIWithDotBelow |
--            latinCapitalLetterOWithDotBelow | latinCapitalLetterOWithHookAbove |
--            latinCapitalLetterOWithCircumflexAndAcute |
--            latinCapitalLetterOWithCircumflexAndGrave |
--            latinCapitalLetterOWithCircumflexAndHookAbove |
--            latinCapitalLetterOWithCircumflexAndTilde |
--            latinCapitalLetterOWithCircumflexAndDotBelow |
--            latinCapitalLetterOWithHornAndAcute |
--            latinCapitalLetterOWithHornAndGrave |
--            latinCapitalLetterOWithHornAndHookAbove |
--            latinCapitalLetterOWithHornAndTilde |
--            latinCapitalLetterOWithHornAndDotBelow |
--            latinCapitalLetterUWithDotBelow | latinCapitalLetterUWithHookAbove |
--            latinCapitalLetterUWithHornAndAcute |
--            latinCapitalLetterUWithHornAndGrave |
--            latinCapitalLetterUWithHornAndHookAbove |
--            latinCapitalLetterUWithHornAndTilde |
--            latinCapitalLetterUWithHornAndDotBelow |
--            latinCapitalLetterYWithGrave | latinCapitalLetterYWithDotBelow |
--            latinCapitalLetterYWithHookAbove | latinCapitalLetterYWithTilde |
--            greekCapitalLetterAlphaWithPsili..
--              greekCapitalLetterAlphaWithDasiaAndPerispomeni |
--            greekCapitalLetterEpsilonWithPsili..
--              greekCapitalLetterEpsilonWithDasiaAndOxia |
--            greekCapitalLetterEtaWithPsili..
--              greekCapitalLetterEtaWithDasiaAndPerispomeni |
--            greekCapitalLetterIotaWithPsili..
--              greekCapitalLetterIotaWithDasiaAndPerispomeni |
--            greekCapitalLetterOmicronWithPsili..
--              greekCapitalLetterOmicronWithDasiaAndOxia |
--            greekCapitalLetterUpsilonWithDasia |
--            greekCapitalLetterUpsilonWithDasiaAndVaria |
--            greekCapitalLetterUpsilonWithDasiaAndOxia |
--            greekCapitalLetterUpsilonWithDasiaAndPerispomeni |
--            greekCapitalLetterOmegaWithPsili..
--              greekCapitalLetterOmegaWithDasiaAndPerispomeni |
--            greekCapitalLetterAlphaWithVrachy..greekCapitalLetterAlphaWithOxia |
--            greekCapitalLetterEpsilonWithVaria..greekCapitalLetterEtaWithOxia |
--            greekCapitalLetterIotaWithVrachy..greekCapitalLetterIotaWithOxia |
--            greekCapitalLetterUpsilonWithVrachy..greekCapitalLetterRhoWithDasia
--            |
--            greekCapitalLetterOmicronWithVaria..greekCapitalLetterOmegaWithOxia
--            | double-struckCapitalC | eulerConstant |
--            scriptCapitalH..double-struckCapitalH |
--            scriptCapitalI..scriptCapitalL | double-struckCapitalN |
--            double-struckCapitalP..double-struckCapitalR | double-struckCapitalZ
--            | ohmSign | black-letterCapitalZ | kelvinSign..black-letterCapitalC
--            | scriptCapitalE..scriptCapitalF | scriptCapitalM |
--            double-struckCapitalGamma..double-struckCapitalPi |
--            double-struckItalicCapitalD |
--            fullwidthLatinCapitalLetterA..fullwidthLatinCapitalLetterZ |
--            deseretCapitalLetterLongI..deseretCapitalLetterEng |
--            mathematicalBoldCapitalA..mathematicalBoldCapitalZ |
--            mathematicalItalicCapitalA..mathematicalItalicCapitalZ |
--            mathematicalBoldItalicCapitalA..mathematicalBoldItalicCapitalZ |
--            mathematicalScriptCapitalA |
--            mathematicalScriptCapitalC..mathematicalScriptCapitalD |
--            mathematicalScriptCapitalG |
--            mathematicalScriptCapitalJ..mathematicalScriptCapitalK |
--            mathematicalScriptCapitalN..mathematicalScriptCapitalQ |
--            mathematicalScriptCapitalS..mathematicalScriptCapitalZ |
--            mathematicalBoldScriptCapitalA..mathematicalBoldScriptCapitalZ |
--            mathematicalFrakturCapitalA..mathematicalFrakturCapitalB |
--            mathematicalFrakturCapitalD..mathematicalFrakturCapitalG |
--            mathematicalFrakturCapitalJ..mathematicalFrakturCapitalQ |
--            mathematicalFrakturCapitalS..mathematicalFrakturCapitalY |
--            mathematicalDouble-struckCapitalA..mathematicalDouble-struckCapitalB
--            |
--            mathematicalDouble-struckCapitalD..mathematicalDouble-struckCapitalG
--            |
--            mathematicalDouble-struckCapitalI..mathematicalDouble-struckCapitalM
--            | mathematicalDouble-struckCapitalO |
--            mathematicalDouble-struckCapitalS..mathematicalDouble-struckCapitalY
--            | mathematicalBoldFrakturCapitalA..mathematicalBoldFrakturCapitalZ |
--            mathematicalSans-serifCapitalA..mathematicalSans-serifCapitalZ |
--            mathematicalSans-serifBoldCapitalA..
--              mathematicalSans-serifBoldCapitalZ |
--            mathematicalSans-serifItalicCapitalA..
--              mathematicalSans-serifItalicCapitalZ |
--            mathematicalSans-serifBoldItalicCapitalA..
--              mathematicalSans-serifBoldItalicCapitalZ |
--            mathematicalMonospaceCapitalA..mathematicalMonospaceCapitalZ |
--            mathematicalBoldCapitalAlpha..mathematicalBoldCapitalOmega |
--            mathematicalItalicCapitalAlpha..mathematicalItalicCapitalOmega |
--            mathematicalBoldItalicCapitalAlpha..
--              mathematicalBoldItalicCapitalOmega |
--            mathematicalSans-serifBoldCapitalAlpha..
--              mathematicalSans-serifBoldCapitalOmega |
--            mathematicalSans-serifBoldItalicCapitalAlpha..
--              mathematicalSans-serifBoldItalicCapitalOmega))

-- MarkSpacingCombining ::= Mc

-- Mc ::=
--   UniversalString
--     (FROM (devanagariSignVisarga | devanagariVowelSignAa..devanagariVowelSignIi
--            | devanagariVowelSignCandraO..devanagariVowelSignAu |
--            bengaliSignAnusvara..bengaliSignVisarga |
--            bengaliVowelSignAa..bengaliVowelSignIi |
--            bengaliVowelSignE..bengaliVowelSignAi |
--            bengaliVowelSignO..bengaliVowelSignAu | bengaliAuLengthMark |
--            gurmukhiVowelSignAa..gurmukhiVowelSignIi | gujaratiSignVisarga |
--            gujaratiVowelSignAa..gujaratiVowelSignIi | gujaratiVowelSignCandraO
--            | gujaratiVowelSignO..gujaratiVowelSignAu |
--            oriyaSignAnusvara..oriyaSignVisarga | oriyaVowelSignAa |
--            oriyaVowelSignIi | oriyaVowelSignE..oriyaVowelSignAi |
--            oriyaVowelSignO..oriyaVowelSignAu | oriyaAuLengthMark |
--            tamilVowelSignAa..tamilVowelSignI |
--            tamilVowelSignU..tamilVowelSignUu |
--            tamilVowelSignE..tamilVowelSignAi |
--            tamilVowelSignO..tamilVowelSignAu | tamilAuLengthMark |
--            teluguSignCandrabindu..teluguSignVisarga |
--            teluguVowelSignU..teluguVowelSignVocalicRr |
--            kannadaSignAnusvara..kannadaSignVisarga | kannadaVowelSignAa |
--            kannadaVowelSignIi..kannadaVowelSignVocalicRr |
--            kannadaVowelSignEe..kannadaVowelSignAi |
--            kannadaVowelSignO..kannadaVowelSignOo |
--            kannadaLengthMark..kannadaAiLengthMark |
--            malayalamSignAnusvara..malayalamSignVisarga |
--            malayalamVowelSignAa..malayalamVowelSignIi |
--            malayalamVowelSignE..malayalamVowelSignAi |
--            malayalamVowelSignO..malayalamVowelSignAu | malayalamAuLengthMark |
--            sinhalaSignAnusvaraya..sinhalaSignVisargaya |
--            sinhalaVowelSignAela-pilla..sinhalaVowelSignDigaAeda-pilla |
--            sinhalaVowelSignGaetta-pilla..sinhalaVowelSignGayanukitta |
--            sinhalaVowelSignDigaGaetta-pilla..sinhalaVowelSignDigaGayanukitta |
--            tibetanSignYarTshes..tibetanSignMarTshes | tibetanSignRnamBcad |
--            myanmarVowelSignAa | myanmarVowelSignE | myanmarSignVisarga |
--            myanmarVowelSignVocalicR..myanmarVowelSignVocalicRr |
--            khmerVowelInherentAq..khmerVowelSignAa |
--            khmerVowelSignOe..khmerVowelSignAu |
--            khmerSignReahmuk..khmerSignYuukaleapintu |
--            musicalSymbolCombiningStem..musicalSymbolCombiningSprechgesangStem |
--            musicalSymbolCombiningAugmentationDot..musicalSymbolCombiningFlag-5))

-- MarkEnclosing ::= Me

-- Me ::=
--   BMPString
--     (FROM (combiningCyrillicHundredThousandsSign..combiningCyrillicMillionsSign
--            | arabicStartOfRubElHizb |
--            combiningEnclosingCircle..combiningEnclosingCircleBackslash |
--            combiningEnclosingScreen..combiningEnclosingUpwardPointingTriangle))

-- MarkNon-spacing ::= Mn

-- Mn ::=
--   UniversalString
--     (FROM (combiningGraveAccent..combiningGraphemeJoiner |
--            combiningDoubleTilde..combiningLatinSmallLetterX |
--            combiningCyrillicTitlo..combiningCyrillicPsiliPneumata |
--            hebrewAccentEtnahta..hebrewAccentPazer |
--            hebrewAccentMunah..hebrewPointHolam |
--            hebrewPointQubuts..hebrewPointMeteg | hebrewPointRafe |
--            hebrewPointShinDot..hebrewPointSinDot | hebrewMarkUpperDot |
--            arabicFathatan..arabicHamzaBelow | arabicLetterSuperscriptAlef |
--            arabicSmallHighLigatureSadWithLamWithAlefMaksura..
--              arabicSmallHighSeen |
--            arabicSmallHighRoundedZero..arabicSmallHighMadda |
--            arabicSmallHighYeh..arabicSmallHighNoon |
--            arabicEmptyCentreLowStop..arabicSmallLowMeem |
--            syriacLetterSuperscriptAlaph | syriacPthahaAbove..syriacBarrekh |
--            thaanaAbafili..thaanaSukun |
--            devanagariSignCandrabindu..devanagariSignAnusvara |
--            devanagariSignNukta | devanagariVowelSignU..devanagariVowelSignAi |
--            devanagariSignVirama |
--            devanagariStressSignUdatta..devanagariAcuteAccent |
--            devanagariVowelSignVocalicL..devanagariVowelSignVocalicLl |
--            bengaliSignCandrabindu | bengaliSignNukta |
--            bengaliVowelSignU..bengaliVowelSignVocalicRr | bengaliSignVirama |
--            bengaliVowelSignVocalicL..bengaliVowelSignVocalicLl |
--            gurmukhiSignBindi | gurmukhiSignNukta |
--            gurmukhiVowelSignU..gurmukhiVowelSignUu |
--            gurmukhiVowelSignEe..gurmukhiVowelSignAi |
--            gurmukhiVowelSignOo..gurmukhiSignVirama |
--            gurmukhiTippi..gurmukhiAddak |
--            gujaratiSignCandrabindu..gujaratiSignAnusvara | gujaratiSignNukta |
--            gujaratiVowelSignU..gujaratiVowelSignCandraE |
--            gujaratiVowelSignE..gujaratiVowelSignAi | gujaratiSignVirama |
--            oriyaSignCandrabindu | oriyaSignNukta | oriyaVowelSignI |
--            oriyaVowelSignU..oriyaVowelSignVocalicR | oriyaSignVirama |
--            oriyaAiLengthMark | tamilSignAnusvara | tamilVowelSignIi |
--            tamilSignVirama | teluguVowelSignAa..teluguVowelSignIi |
--            teluguVowelSignE..teluguVowelSignAi |
--            teluguVowelSignO..teluguSignVirama |
--            teluguLengthMark..teluguAiLengthMark | kannadaVowelSignI |
--            kannadaVowelSignE | kannadaVowelSignAu..kannadaSignVirama |
--            malayalamVowelSignU..malayalamVowelSignVocalicR |
--            malayalamSignVirama | sinhalaSignAl-lakuna |
--            sinhalaVowelSignKettiIs-pilla..sinhalaVowelSignKettiPaa-pilla |
--            sinhalaVowelSignDigaPaa-pilla | thaiCharacterMaiHan-akat |
--            thaiCharacterSaraI..thaiCharacterPhinthu |
--            thaiCharacterMaitaikhu..thaiCharacterYamakkan | laoVowelSignMaiKan |
--            laoVowelSignI..laoVowelSignUu |
--            laoVowelSignMaiKon..laoSemivowelSignLo | laoToneMaiEk..laoNiggahita
--            |
--            tibetanAstrologicalSign-khyudPa..tibetanAstrologicalSignSdongTshugs
--            | tibetanMarkNgasBzungNyiZla | tibetanMarkNgasBzungSgorRtags |
--            tibetanMarkTsa-phru | tibetanVowelSignAa..tibetanSignRjesSuNgaRo |
--            tibetanVowelSignReversedI..tibetanMarkHalanta |
--            tibetanSignLciRtags..tibetanSignYangRtags |
--            tibetanSubjoinedLetterKa..tibetanSubjoinedLetterJa |
--            tibetanSubjoinedLetterNya..tibetanSubjoinedLetterFixed-formRa |
--            tibetanSymbolPadmaGdan | myanmarVowelSignI..myanmarVowelSignUu |
--            myanmarVowelSignAi | myanmarSignAnusvara..myanmarSignDotBelow |
--            myanmarSignVirama |
--            myanmarVowelSignVocalicL..myanmarVowelSignVocalicLl |
--            tagalogVowelSignI..tagalogSignVirama |
--            hanunooVowelSignI..hanunooSignPamudpod |
--            buhidVowelSignI..buhidVowelSignU |
--            tagbanwaVowelSignI..tagbanwaVowelSignU |
--            khmerVowelSignI..khmerVowelSignUa | khmerSignNikahit |
--            khmerSignMuusikatoan..khmerSignBathamasat |
--            mongolianFreeVariationSelectorOne..
--              mongolianFreeVariationSelectorThree |
--            mongolianLetterAliGaliDagalga |
--            combiningLeftHarpoonAbove..combiningFourDotsAbove |
--            combiningLeftRightArrowAbove |
--            combiningReverseSolidusOverlay..combiningLeftwardsArrowOverlay |
--            ideographicLevelToneMark..hangulDoubleDotToneMark |
--            combiningKatakana-hiraganaVoicedSoundMark..
--              combiningKatakana-hiraganaSemi-voicedSoundMark |
--            hebrewPointJudeo-spanishVarika |
--            variationSelector-1..variationSelector-16 |
--            combiningLigatureLeftHalf..combiningDoubleTildeRightHalf |
--            musicalSymbolCombiningTremolo-1..musicalSymbolCombiningTremolo-3 |
--            musicalSymbolCombiningAccent..musicalSymbolCombiningLoure |
--            musicalSymbolCombiningDoit..musicalSymbolCombiningTripleTongue |
--            musicalSymbolCombiningDownBow..musicalSymbolCombiningSnapPizzicato))

-- NumberDecimalDigit ::= Nd

-- Nd ::=
--   UniversalString
--     (FROM (digitZero..digitNine | arabic-indicDigitZero..arabic-indicDigitNine
--            | extendedArabic-indicDigitZero..extendedArabic-indicDigitNine |
--            devanagariDigitZero..devanagariDigitNine |
--            bengaliDigitZero..bengaliDigitNine |
--            gurmukhiDigitZero..gurmukhiDigitNine |
--            gujaratiDigitZero..gujaratiDigitNine |
--            oriyaDigitZero..oriyaDigitNine | tamilDigitOne..tamilDigitNine |
--            teluguDigitZero..teluguDigitNine |
--            kannadaDigitZero..kannadaDigitNine |
--            malayalamDigitZero..malayalamDigitNine |
--            thaiDigitZero..thaiDigitNine | laoDigitZero..laoDigitNine |
--            tibetanDigitZero..tibetanDigitNine |
--            myanmarDigitZero..myanmarDigitNine |
--            ethiopicDigitOne..ethiopicDigitNine | khmerDigitZero..khmerDigitNine
--            | mongolianDigitZero..mongolianDigitNine |
--            fullwidthDigitZero..fullwidthDigitNine |
--            mathematicalBoldDigitZero..mathematicalMonospaceDigitNine))

-- NumberLetter ::= Nl

-- Nl ::=
--   UniversalString
--     (FROM (runicArlaugSymbol..runicBelgthorSymbol |
--            romanNumeralOne..romanNumeralReversedOneHundred |
--            ideographicNumberZero | hangzhouNumeralOne..hangzhouNumeralNine |
--            hangzhouNumeralTen..hangzhouNumeralThirty | gothicLetterNineHundred))

-- NumberOther ::= No

-- No ::=
--   UniversalString
--     (FROM (superscriptTwo..superscriptThree | superscriptOne |
--            vulgarFractionOneQuarter..vulgarFractionThreeQuarters |
--            bengaliCurrencyNumeratorOne..bengaliCurrencyDenominatorSixteen |
--            tamilNumberTen..tamilNumberOneThousand |
--            tibetanDigitHalfOne..tibetanDigitHalfZero |
--            ethiopicNumberTen..ethiopicNumberTenThousand | superscriptZero |
--            superscriptFour..superscriptNine | subscriptZero..subscriptNine |
--            vulgarFractionOneThird..fractionNumeratorOne |
--            circledDigitOne..numberTwentyFullStop |
--            circledDigitZero..doubleCircledNumberTen |
--            dingbatNegativeCircledDigitOne..
--              dingbatNegativeCircledSans-serifNumberTen |
--            ideographicAnnotationOneMark..ideographicAnnotationFourMark |
--            parenthesizedIdeographOne..parenthesizedIdeographTen |
--            circledNumberTwentyOne..circledNumberThirtyFive |
--            circledIdeographOne..circledIdeographTen |
--            circledNumberThirtySix..circledNumberFifty |
--            oldItalicNumeralOne..oldItalicNumeralFifty))

-- PunctuationConnector ::= Pc

-- Pc ::=
--   BMPString
--     (FROM (lowLine | undertie..characterTie | katakanaMiddleDot |
--            presentationFormForVerticalLowLine..
--              presentationFormForVerticalWavyLowLine |
--            dashedLowLine..wavyLowLine | fullwidthLowLine |
--            halfwidthKatakanaMiddleDot))

-- PunctuationDash ::= Pd

-- Pd ::=
--   BMPString
--     (FROM (hyphen-minus | softHyphen | armenianHyphen | mongolianTodoSoftHyphen
--            | hyphen..horizontalBar | waveDash | wavyDash |
--            katakana-hiraganaDoubleHyphen |
--            presentationFormForVerticalEmDash..presentationFormForVerticalEnDash
--            | smallEmDash | smallHyphen-minus | fullwidthHyphen-minus))

-- PunctuationClose ::= Pe

-- Pe ::=
--   BMPString
--     (FROM (rightParenthesis | rightSquareBracket | rightCurlyBracket |
--            tibetanMarkGugRtagsGyas | tibetanMarkAngKhangGyas |
--            oghamReversedFeatherMark | rightSquareBracketWithQuill |
--            superscriptRightParenthesis | subscriptRightParenthesis |
--            right-pointingAngleBracket | bottomSquareBracket |
--            mediumRightParenthesisOrnament |
--            mediumFlattenedRightParenthesisOrnament |
--            mediumRight-pointingAngleBracketOrnament |
--            heavyRight-pointingAngleQuotationMarkOrnament |
--            heavyRight-pointingAngleBracketOrnament |
--            lightRightTortoiseShellBracketOrnament |
--            mediumRightCurlyBracketOrnament |
--            mathematicalRightWhiteSquareBracket | mathematicalRightAngleBracket
--            | mathematicalRightDoubleAngleBracket | rightWhiteCurlyBracket |
--            rightWhiteParenthesis | zNotationRightImageBracket |
--            zNotationRightBindingBracket | rightSquareBracketWithUnderbar |
--            rightSquareBracketWithTickInBottomCorner |
--            rightSquareBracketWithTickInTopCorner | rightAngleBracketWithDot |
--            rightArcGreater-thanBracket | doubleRightArcLess-thanBracket |
--            rightBlackTortoiseShellBracket | rightWigglyFence |
--            rightDoubleWigglyFence | right-pointingCurvedAngleBracket |
--            rightAngleBracket | rightDoubleAngleBracket | rightCornerBracket |
--            rightWhiteCornerBracket | rightBlackLenticularBracket |
--            rightTortoiseShellBracket | rightWhiteLenticularBracket |
--            rightWhiteTortoiseShellBracket | rightWhiteSquareBracket |
--            doublePrimeQuotationMark..lowDoublePrimeQuotationMark |
--            ornateRightParenthesis | presentationFormForVerticalRightParenthesis
--            | presentationFormForVerticalRightCurlyBracket |
--            presentationFormForVerticalRightTortoiseShellBracket |
--            presentationFormForVerticalRightBlackLenticularBracket |
--            presentationFormForVerticalRightDoubleAngleBracket |
--            presentationFormForVerticalRightAngleBracket |
--            presentationFormForVerticalRightCornerBracket |
--            presentationFormForVerticalRightWhiteCornerBracket |
--            smallRightParenthesis | smallRightCurlyBracket |
--            smallRightTortoiseShellBracket | fullwidthRightParenthesis |
--            fullwidthRightSquareBracket | fullwidthRightCurlyBracket |
--            fullwidthRightWhiteParenthesis | halfwidthRightCornerBracket))

-- PunctuationFinalquote ::= Pf

-- Pf ::=
--   BMPString
--     (FROM (right-pointingDoubleAngleQuotationMark | rightSingleQuotationMark |
--            rightDoubleQuotationMark | singleRight-pointingAngleQuotationMark))

-- PunctuationInitialquote ::= Pi

-- Pi ::=
--   BMPString
--     (FROM (left-pointingDoubleAngleQuotationMark | leftSingleQuotationMark |
--            singleHigh-reversed-9QuotationMark..leftDoubleQuotationMark |
--            doubleHigh-reversed-9QuotationMark |
--            singleLeft-pointingAngleQuotationMark))

-- PunctuationOther ::= Po

-- Po ::=
--   BMPString
--     (FROM (exclamationMark..numberSign | percentSign..apostrophe | asterisk |
--            comma | fullStop..solidus | colon..semicolon |
--            questionMark..commercialAt | reverseSolidus |
--            invertedExclamationMark | middleDot | invertedQuestionMark |
--            greekQuestionMark | greekAnoTeleia |
--            armenianApostrophe..armenianAbbreviationMark | armenianFullStop |
--            hebrewPunctuationMaqaf | hebrewPunctuationPaseq |
--            hebrewPunctuationSofPasuq |
--            hebrewPunctuationGeresh..hebrewPunctuationGershayim | arabicComma |
--            arabicSemicolon | arabicQuestionMark |
--            arabicPercentSign..arabicFivePointedStar | arabicFullStop |
--            syriacEndOfParagraph..syriacHarkleanAsteriscus |
--            devanagariDanda..devanagariDoubleDanda | devanagariAbbreviationSign
--            | sinhalaPunctuationKunddaliya | thaiCharacterFongman |
--            thaiCharacterAngkhankhu..thaiCharacterKhomut |
--            tibetanMarkInitialYigMgoMdunMa..tibetanMarkRgyaGramShad |
--            tibetanMarkPaluta | myanmarSignLittleSection..myanmarSymbolGenitive
--            | georgianParagraphSeparator |
--            ethiopicWordspace..ethiopicParagraphSeparator |
--            canadianSyllabicsChiSign..canadianSyllabicsFullStop |
--            runicSinglePunctuation..runicCrossPunctuation |
--            philippineSinglePunctuation..philippineDoublePunctuation |
--            khmerSignKhan..khmerSignCamnucPiiKuuh |
--            khmerSignBeyyal..khmerSignKoomuut |
--            mongolianBirga..mongolianFourDots |
--            mongolianSibeSyllableBoundaryMarker..mongolianNirugu |
--            doubleVerticalLine..doubleLowLine | dagger..hyphenationPoint |
--            perMilleSign..caret | referenceMark..overline |
--            caretInsertionPoint..hyphenBullet |
--            doubleQuestionMark..twoAsterisksAlignedVertically | quadruplePrime |
--            bottomSquareBracketOverTopSquareBracket |
--            ideographicComma..dittoMark | partAlternationMark |
--            presentationFormForVerticalTwoDotLeader | sesameDot..whiteSesameDot
--            | dashedOverline..doubleWavyOverline | smallComma..smallFullStop |
--            smallSemicolon..smallExclamationMark |
--            smallNumberSign..smallAsterisk | smallReverseSolidus |
--            smallPercentSign..smallCommercialAt |
--            fullwidthExclamationMark..fullwidthNumberSign |
--            fullwidthPercentSign..fullwidthApostrophe | fullwidthAsterisk |
--            fullwidthComma | fullwidthFullStop..fullwidthSolidus |
--            fullwidthColon..fullwidthSemicolon |
--            fullwidthQuestionMark..fullwidthCommercialAt |
--            fullwidthReverseSolidus | halfwidthIdeographicFullStop |
--            halfwidthIdeographicComma))

-- PunctuationOpen ::= Ps

-- Ps ::=
--   BMPString
--     (FROM (leftParenthesis | leftSquareBracket | leftCurlyBracket |
--            tibetanMarkGugRtagsGyon | tibetanMarkAngKhangGyon | oghamFeatherMark
--            | singleLow-9QuotationMark | doubleLow-9QuotationMark |
--            leftSquareBracketWithQuill | superscriptLeftParenthesis |
--            subscriptLeftParenthesis | left-pointingAngleBracket |
--            topSquareBracket | mediumLeftParenthesisOrnament |
--            mediumFlattenedLeftParenthesisOrnament |
--            mediumLeft-pointingAngleBracketOrnament |
--            heavyLeft-pointingAngleQuotationMarkOrnament |
--            heavyLeft-pointingAngleBracketOrnament |
--            lightLeftTortoiseShellBracketOrnament |
--            mediumLeftCurlyBracketOrnament | mathematicalLeftWhiteSquareBracket
--            | mathematicalLeftAngleBracket | mathematicalLeftDoubleAngleBracket
--            | leftWhiteCurlyBracket | leftWhiteParenthesis |
--            zNotationLeftImageBracket | zNotationLeftBindingBracket |
--            leftSquareBracketWithUnderbar | leftSquareBracketWithTickInTopCorner
--            | leftSquareBracketWithTickInBottomCorner | leftAngleBracketWithDot
--            | leftArcLess-thanBracket | doubleLeftArcGreater-thanBracket |
--            leftBlackTortoiseShellBracket | leftWigglyFence |
--            leftDoubleWigglyFence | left-pointingCurvedAngleBracket |
--            leftAngleBracket | leftDoubleAngleBracket | leftCornerBracket |
--            leftWhiteCornerBracket | leftBlackLenticularBracket |
--            leftTortoiseShellBracket | leftWhiteLenticularBracket |
--            leftWhiteTortoiseShellBracket | leftWhiteSquareBracket |
--            reversedDoublePrimeQuotationMark | ornateLeftParenthesis |
--            presentationFormForVerticalLeftParenthesis |
--            presentationFormForVerticalLeftCurlyBracket |
--            presentationFormForVerticalLeftTortoiseShellBracket |
--            presentationFormForVerticalLeftBlackLenticularBracket |
--            presentationFormForVerticalLeftDoubleAngleBracket |
--            presentationFormForVerticalLeftAngleBracket |
--            presentationFormForVerticalLeftCornerBracket |
--            presentationFormForVerticalLeftWhiteCornerBracket |
--            smallLeftParenthesis | smallLeftCurlyBracket |
--            smallLeftTortoiseShellBracket | fullwidthLeftParenthesis |
--            fullwidthLeftSquareBracket | fullwidthLeftCurlyBracket |
--            fullwidthLeftWhiteParenthesis | halfwidthLeftCornerBracket))

-- SymbolCurrency ::= Sc

-- Sc ::=
--   BMPString
--     (FROM (dollarSign | centSign..yenSign | bengaliRupeeMark..bengaliRupeeSign
--            | thaiCurrencySymbolBaht | khmerCurrencySymbolRiel |
--            euro-currencySign..pesoSign | rialSign | smallDollarSign |
--            fullwidthDollarSign | fullwidthCentSign..fullwidthPoundSign |
--            fullwidthYenSign..fullwidthWonSign))

-- SymbolModifier ::= Sk

-- Sk ::=
--   BMPString
--     (FROM (circumflexAccent | graveAccent | diaeresis | macron | acuteAccent |
--            cedilla | modifierLetterPrime..modifierLetterDoublePrime |
--            modifierLetterLeftArrowhead..modifierLetterLowAcuteAccent |
--            modifierLetterCentredRightHalfRing..modifierLetterCrossAccent |
--            modifierLetterExtra-highToneBar..modifierLetterUnaspirated |
--            greekNumeralSign..greekLowerNumeralSign |
--            greekTonos..greekDialytikaTonos | greekKoronis |
--            greekPsili..greekDialytikaAndPerispomeni |
--            greekPsiliAndVaria..greekPsiliAndPerispomeni |
--            greekDasiaAndVaria..greekDasiaAndPerispomeni |
--            greekDialytikaAndVaria..greekVaria | greekOxia..greekDasia |
--            katakana-hiraganaVoicedSoundMark..
--              katakana-hiraganaSemi-voicedSoundMark | fullwidthCircumflexAccent
--            | fullwidthGraveAccent | fullwidthMacron))

-- SymbolMath ::= Sm

-- Sm ::=
--   UniversalString
--     (FROM (plusSign | less-thanSign..greater-thanSign | verticalLine | tilde |
--            notSign | plus-minusSign | multiplicationSign | divisionSign |
--            greekReversedLunateEpsilonSymbol | fractionSlash |
--            commercialMinusSign | superscriptPlusSign..superscriptEqualsSign |
--            subscriptPlusSign..subscriptEqualsSign |
--            double-struckN-arySummation..turnedSans-serifCapitalY |
--            turnedAmpersand | leftwardsArrow..leftRightArrow |
--            leftwardsArrowWithStroke..rightwardsArrowWithStroke |
--            rightwardsTwoHeadedArrow | rightwardsArrowWithTail |
--            rightwardsArrowFromBar | leftRightArrowWithStroke |
--            leftRightDoubleArrowWithStroke..rightwardsDoubleArrowWithStroke |
--            rightwardsDoubleArrow | leftRightDoubleArrow |
--            rightArrowWithSmallCircle..zNotationBagMembership |
--            leftCeiling..rightFloor | topHalfIntegral..bottomHalfIntegral |
--            rightAngleWithDownwardsZigzagArrow |
--            leftParenthesisUpperHook..summationBottom |
--            whiteRight-pointingTriangle | whiteLeft-pointingTriangle |
--            upperLeftTriangle..lowerRightTriangle | musicSharpSign |
--            whiteDiamondWithCentredDot..whiteSquareWithRightwardsTick |
--            upwardsQuadrupleArrow..longRightwardsSquiggleArrow |
--            rightwardsTwo-headedArrowWithVerticalStroke..zNotationTypeColon |
--            dottedFence..blackHourglass | incompleteInfinity..triplePlus |
--            tiny..n-aryWhiteVerticalBar | hebrewLetterAlternativePlusSign |
--            smallPlusSign | smallLess-thanSign..smallEqualsSign |
--            fullwidthPlusSign |
--            fullwidthLess-thanSign..fullwidthGreater-thanSign |
--            fullwidthVerticalLine | fullwidthTilde | fullwidthNotSign |
--            halfwidthLeftwardsArrow..halfwidthDownwardsArrow |
--            mathematicalBoldNabla | mathematicalBoldPartialDifferential |
--            mathematicalItalicNabla | mathematicalItalicPartialDifferential |
--            mathematicalBoldItalicNabla |
--            mathematicalBoldItalicPartialDifferential |
--            mathematicalSans-serifBoldNabla |
--            mathematicalSans-serifBoldPartialDifferential |
--            mathematicalSans-serifBoldItalicNabla |
--            mathematicalSans-serifBoldItalicPartialDifferential))

-- SymbolOther ::= So

-- So ::=
--   UniversalString
--     (FROM (brokenBar..sectionSign | copyrightSign | registeredSign | degreeSign
--            | pilcrowSign | cyrillicThousandsSign | arabicPlaceOfSajdah |
--            arabicSignSindhiAmpersand..arabicSignSindhiPostpositionMen |
--            bengaliIsshar | oriyaIsshar |
--            tibetanMarkGterYigMgoTruncatedA..tibetanMarkGterYigMgo-umGterTshegMa
--            |
--            tibetanMarkCaret-dzudRtagsMeLongCan..
--              tibetanAstrologicalSignSgraGcan-charRtags |
--            tibetanSignRdelDkarGcig..tibetanSignRdelDkarRdelNag |
--            tibetanMarkBsdusRtags | tibetanMarkCaret-dzudRtagsBzhiMigCan |
--            tibetanMarkCheMgo | tibetanKuRuKha..tibetanSymbolRdoRje |
--            tibetanSymbolRdoRjeRgyaGram..tibetanSymbolNorBuBzhi-khyil |
--            tibetanSignRdelNagGsum | accountOf..addressedToTheSubject |
--            degreeCelsius..cadaUna | scruple..degreeFahrenheit | lBBarSymbol |
--            numeroSign..scriptCapitalP | prescriptionTake..versicle | ounceSign
--            | invertedOhmSign | turnedGreekSmallLetterIota | estimatedSymbol |
--            turnedCapitalF | rotatedCapitalQ | propertyLine |
--            upDownArrow..southWestArrow |
--            leftwardsWaveArrow..upwardsTwoHeadedArrow |
--            downwardsTwoHeadedArrow..leftwardsArrowWithTail |
--            leftwardsArrowFromBar..upwardsArrowFromBar |
--            downwardsArrowFromBar..leftRightWaveArrow |
--            downwardsZigzagArrow..leftwardsDoubleArrowWithStroke |
--            leftwardsDoubleArrow..upwardsDoubleArrow | downwardsDoubleArrow |
--            upDownDoubleArrow..upDownWhiteArrow | diameterSign..wavyLine |
--            bottomRightCrop..bottomRightCorner | frown..keyboard |
--            eraseToTheLeft..notCheckMark | shoulderedOpenBox..clearScreenSymbol
--            | radicalSymbolBottom..returnSymbol |
--            symbolForNull..symbolForSubstituteFormTwo |
--            ocrHook..ocrDoubleBackslash |
--            parenthesizedLatinSmallLetterA..circledLatinSmallLetterZ |
--            boxDrawingsLightHorizontal..blackRight-pointingTriangle |
--            blackRight-pointingSmallTriangle..blackLeft-pointingTriangle |
--            blackLeft-pointingSmallTriangle..whiteCircleWithUpperRightQuadrant |
--            blackSunWithRays..saltire | whiteShogiPiece..blackShogiPiece |
--            reversedRotatedFloralHeartBullet..musicNaturalSign |
--            westSyriacCross..partially-recycledPaperSymbol |
--            dieFace-1..blackCircleWithTwoWhiteDots |
--            upperBladeScissors..whiteScissors | telephoneLocationSign..envelope
--            | victoryHand..whiteFourPointedStar |
--            stressOutlinedWhiteStar..heavyEightTeardrop-spokedPropellerAsterisk
--            | shadowedWhiteCircle |
--            lowerRightDrop-shadowedWhiteSquare..upperRightShadowedWhiteSquare |
--            blackDiamondMinusWhiteX |
--            lightVerticalBar..heavyDoubleCommaQuotationMarkOrnament |
--            curvedStemParagraphSignOrnament..rotatedFloralHeartBullet |
--            heavyWide-headedRightwardsArrow |
--            heavySouthEastArrow..notchedLowerRight-shadowedWhiteRightwardsArrow
--            |
--            notchedUpperRight-shadowedWhiteRightwardsArrow..
--              open-outlinedRightwardsArrow |
--            braillePatternBlank..braillePatternDots-12345678 |
--            cjkRadicalRepeat..cjkRadicalRap |
--            cjkRadicalChoke..cjkRadicalC-simplifiedTurtle |
--            kangxiRadicalOne..kangxiRadicalFlute |
--            ideographicDescriptionCharacterLeftToRight..
--              ideographicDescriptionCharacterOverlaid |
--            japaneseIndustrialStandardSymbol | postalMark..getaMark |
--            postalMarkFace |
--            circledPostalMark..ideographicTelegraphLineFeedSeparatorSymbol |
--            ideographicVariationIndicator..ideographicHalfFillSpace |
--            ideographicAnnotationLinkingMark..ideographicAnnotationReverseMark |
--            ideographicAnnotationTopMark..ideographicAnnotationManMark |
--            parenthesizedHangulKiyeok..parenthesizedHangulCieucU |
--            parenthesizedIdeographMoon..parenthesizedIdeographReach |
--            circledHangulKiyeok..circledHangulHieuhA | koreanStandardSymbol |
--            circledIdeographMoon..circledIdeographNight |
--            ideographicTelegraphSymbolForJanuary..
--              ideographicTelegraphSymbolForDecember |
--            circledKatakanaA..circledKatakanaWo | squareApaato..squarePc |
--            squareEraNameHeisei..squareWb |
--            ideographicTelegraphSymbolForDayOne..
--              ideographicTelegraphSymbolForDayThirty-one |
--            yiRadicalQot..yiRadicalKe | fullwidthBrokenBar |
--            halfwidthFormsLightVertical |
--            halfwidthBlackSquare..halfwidthWhiteCircle |
--            objectReplacementCharacter..replacementCharacter |
--            byzantineMusicalSymbolPsili..byzantineMusicalSymbolGorgonNeoKato |
--            musicalSymbolSingleBarline..musicalSymbolDrumClef-2 |
--            musicalSymbolDoubleSharp..musicalSymbolOneHundredTwenty-eighthNote |
--            musicalSymbolFingeredTremolo-1..musicalSymbolFingeredTremolo-3 |
--            musicalSymbolArpeggiatoUp..musicalSymbolArpeggiatoDown |
--            musicalSymbolRinforzando..musicalSymbolDegreeSlash |
--            musicalSymbolPedalMark..musicalSymbolPesSubpunctis))

-- SeparatorLine ::= Zl

-- Zl ::= BMPString(FROM (lineSeparator))

-- SeparatorParagraph ::= Zp

-- Zp ::= BMPString(FROM (paragraphSeparator))

-- SeparatorSpace ::= Zs

-- Zs ::=
--   BMPString
--     (FROM (space | no-breakSpace | oghamSpaceMark | enQuad..zeroWidthSpace |
--            narrowNo-breakSpace | mediumMathematicalSpace | ideographicSpace))

-- END

-- -- Generated by Asnp, the ASN.1 pretty-printer of France Telecom R&D
