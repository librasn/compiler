-- Module Document-Set-Profile-Descriptor (T.424:07/1996)
-- See also ITU-T T.424 (07/1996)
-- See also the index of all ASN.1 assignments needed in this document

Document-Set-Profile-Descriptor {2 8 1 14 2} DEFINITIONS ::=
BEGIN

EXPORTS Document-Set-Profile-Descriptor;

IMPORTS
  Location-Expression
    FROM Location-Expressions {2 8 1 12 0}
  --  see ITU-T Rec. T.422 | ISO/IEC  8613-12
  Reference-Name, External-References-List
    FROM External-References {2 8 1 12 1}
  --  see ITU-T Rec. T.422 | ISO/IEC  8613-12
  ODA-Version, Document-Description, Dates-and-Times, Originators,
    Other-User-Information, External-References, Local-File-References,
    Security-Information, Sealed-Doc-Bodyparts
    FROM Document-Profile-Descriptor {2 8 1 5 6}
  --  see ITU-T Rec. T.415 | ISO/IEC 8613-5 and C.4
  Link-or-Link-Class-Identifier
    FROM Link-Descriptors;

--  see 8.11.3
Document-Set-Profile-Descriptor ::= SET {
  entry-point               [99]  Entry-Point, -- Addition of [99] in order to suppress the ambiguity between entry-point and interchange-format-class
  external-references-list  [0] IMPLICIT External-References-List OPTIONAL,
  interchange-format-class  [1] IMPLICIT INTEGER {if-a(0)},
  oda-version               [2] IMPLICIT ODA-Version,
  profile-character-sets    [3] IMPLICIT OCTET STRING OPTIONAL,
  document-description      [4] IMPLICIT Document-Description OPTIONAL,
  dates-and-times           [5] IMPLICIT Dates-and-Times OPTIONAL,
  originators               [6] IMPLICIT Originators OPTIONAL,
  other-user-information    [7] IMPLICIT Other-User-Information OPTIONAL,
  external-references       [8] IMPLICIT External-References OPTIONAL,
  local-file-references     [9] IMPLICIT Local-File-References OPTIONAL,
  security-information      [10] IMPLICIT Security-Information OPTIONAL,
  links                     [11] IMPLICIT NumericString OPTIONAL,
  link-classes              [12] IMPLICIT NumericString OPTIONAL,
  enciphered-links          [13] IMPLICIT NumericString OPTIONAL,
  --  The numeric string has the value 'present', represented by "1"
  sealed-links              [14] IMPLICIT Sealed-Doc-Bodyparts OPTIONAL
}

Entry-Point ::= CHOICE {
  link-id    Link-or-Link-Class-Identifier,
  reference
    [1]  SET {reference-name       [0]  Reference-Name OPTIONAL,
              reference-qualifier  [1]  Location-Expression OPTIONAL}
}

END

-- Generated by Asnp, the ASN.1 pretty-printer of France Telecom R&D
