-- Module Example1-ASN1-Module (X.692:07/2002)
-- See also ITU-T X.692 (03/2002)
-- See also the index of all ASN.1 assignments needed in this document

Example1-ASN1-Module {joint-iso-itu-t(2) asn1(1) ecn(4) examples(5)
  asn1-module1(2)} DEFINITIONS AUTOMATIC TAGS ::=
BEGIN

MyPDU ::= CHOICE {marriedMessage   Married,
                  altitudeMessage  Altitude
                  -- etc.
}

Married ::= BOOLEAN

Altitude ::= INTEGER(0..65535)

-- etc.
END

-- Generated by Asnp, the ASN.1 pretty-printer of France Telecom R&D
