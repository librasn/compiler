-- Module IN-CS-1-Errors-appendix (Q.1218:10/1995)
-- See also ITU-T Q.1218 (10/1995)
-- See also the index of all ASN.1 assignments needed in this document

IN-CS-1-Errors-appendix {itu-t recommendation q 1218 modules(0)
  cs-1-errors-app(5) version1(0)}
--  This module contains additional type definitions for the IN CS-1 errors.
DEFINITIONS IMPLICIT TAGS ::=
BEGIN

IMPORTS
  ERROR
    FROM Remote-Operations-Information-Objects {joint-iso-itu-t
      remote-operations(4) informationObjects(5) version1(0)}
  -- err codes
  err-legIDAlreadyAssigned, err-tooLate, err-dataunavailable,
    err-dataAlreadyExists
    FROM IN-CS-1-Codes-appendix {itu-t recommendation q 1218 modules(0)
      cs-1-codes-app(7) version1(0)};

--  TYPE DEFINITION FOR  IN CS-1  ERRORS FOLLOWS
legIDAlreadyAssigned ERROR ::= {CODE  err-legIDAlreadyAssigned
}

--  Indicates that a legID has already been assigned with the requested value.
tooLate ERROR ::= {CODE  err-tooLate
}

dataUnavailable ERROR ::= {CODE  err-dataunavailable
}

dataAlreadyExists ERROR ::= {CODE  err-dataAlreadyExists
}

--  Indicates that the operation could not be performed in a timely manner.
--  UnknownLegID ERROR ::=  {
--	CODE err-unknownLegID
--	}
--  Indicates that the legID does not exist. Already defined in IN-CS-1-Errors...
END

-- Generated by Asnp, the ASN.1 pretty-printer of France Telecom R&D
