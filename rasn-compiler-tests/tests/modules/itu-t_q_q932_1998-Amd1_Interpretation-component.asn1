-- Module Interpretation-component (Q.932:05/1998)
-- See also ITU-T Q.932 (1998) Amend. 1 (06/2000)
-- See also the index of all ASN.1 assignments needed in this document

Interpretation-component {iso(1) standard(0) pss1-generic-procedures(11582)
  interpretation-component(3)} DEFINITIONS ::=
BEGIN

EXPORTS InterpretationComponent;

InterpretationComponent ::= [11] IMPLICIT ENUMERATED {
  discardAnyUnrecognisedInvokePdu(0), clearCallIfAnyInvokePduNotRecognised(1),
  rejectAnyUnrecognisedInvokePdu(2)
  -- this coding is implied by the absence of an
  -- Interpretation Component.
  }

END -- component

-- Generated by Asnp, the ASN.1 pretty-printer of France Telecom R&D
