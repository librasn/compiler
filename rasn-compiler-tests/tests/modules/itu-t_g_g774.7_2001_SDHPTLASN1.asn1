-- Module SDHPTLASN1 (G.774.7:02/2001)
-- See also ITU-T G.774.7 (02/2001)
-- See also the index of all ASN.1 assignments needed in this document

SDHPTLASN1 {itu-t(0) recommendation(0) g(7) g774(774) hyphen(127) ptl(7)
  informationModel(0) asn1Module(2) sdhptl(0)} DEFINITIONS IMPLICIT TAGS ::=
BEGIN

-- EXPORTS everything
sdhPTL OBJECT IDENTIFIER ::=
  {itu-t(0) recommendation(0) g(7) g774(774) hyphen(127) ptl(7)
   informationModel(0)}

g774-7ObjectClass OBJECT IDENTIFIER ::= {sdhPTL managedObjectClass(3)}

g774-7Action OBJECT IDENTIFIER ::= {sdhPTL action(9)}

g774-7NameBinding OBJECT IDENTIFIER ::= {sdhPTL nameBinding(6)}

g774-7Parameter OBJECT IDENTIFIER ::= {sdhPTL parameter(5)}

g774-7Notification OBJECT IDENTIFIER ::= {sdhPTL notification(10)}

g774-7Package OBJECT IDENTIFIER ::= {sdhPTL package(4)}

g774-7Attribute OBJECT IDENTIFIER ::= {sdhPTL attribute(7)}

nullDefault Null ::= NULL

Null ::= NULL

END

-- Generated by Asnp, the ASN.1 pretty-printer of France Telecom R&D
