-- Module IPMSForwardedContentBodyPartType (X.420:06/1999)
-- See also ITU-T X.420 (06/1999)
-- See also the index of all ASN.1 assignments needed in this document

IPMSForwardedContentBodyPartType {joint-iso-itu-t mhs(6) ipms(1) modules(0)
  forwarded-content-body-part-type(15)} DEFINITIONS IMPLICIT TAGS ::=
BEGIN

-- Prologue
-- Exports everything.
IMPORTS
  -- MTS Abstract Service
  Content, ExtendedContentType, MessageDeliveryIdentifier, MessageDeliveryTime,
    MessageSubmissionEnvelope, OriginatingMTACertificate,
    OtherMessageDeliveryFields, ProofOfSubmission
    --==
    FROM MTSAbstractService {joint-iso-itu-t mhs(6) mts(3) modules(0)
      mts-abstract-service(1) version-1999(1)}
  -- IPMS Information Objects
  EXTENDED-BODY-PART-TYPE
    --==
    FROM IPMSInformationObjects {joint-iso-itu-t mhs(6) ipms(1) modules(0)
      information-objects(2) version-1999(1)}
  -- IPMS Object Identifiers
  id-ep-content, id-et-content
    --==
    FROM IPMSObjectIdentifiers {joint-iso-itu-t mhs(6) ipms(1) modules(0)
      object-identifiers(0) version-1999(1)};

-- Forwarded Content body part
content-body-part{ExtendedContentType:content-type} EXTENDED-BODY-PART-TYPE ::=
  {
  PARAMETERS
    {ForwardedContentParameters
     IDENTIFIED BY  {id-ep-content  content-type}},
  DATA        {Content
               IDENTIFIED BY  {id-et-content  content-type}}
}

ForwardedContentParameters ::= SET {
  delivery-time      [0]  MessageDeliveryTime OPTIONAL,
  delivery-envelope  [1]  OtherMessageDeliveryFields OPTIONAL,
  mts-identifier     [2]  MessageDeliveryIdentifier OPTIONAL,
  submission-proof   [3]  SubmissionProof OPTIONAL
}

SubmissionProof ::= SET {
  proof-of-submission          [0]  ProofOfSubmission,
  originating-MTA-certificate  [1]  OriginatingMTACertificate,
  message-submission-envelope  MessageSubmissionEnvelope
}

END -- of IPMSForwardedContentBodyPartType

-- Generated by Asnp, the ASN.1 pretty-printer of France Telecom R&D
