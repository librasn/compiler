-- Module Protected-Part-Descriptors (T.415:03/1993)
-- See also ITU-T T.415 (03/1993)
-- See also the index of all ASN.1 assignments needed in this document

Protected-Part-Descriptors {2 8 1 5 13} DEFINITIONS ::=
BEGIN

EXPORTS
  Sealed-Doc-Prof-Descriptor, Enciphered-Doc-Prof-Descriptor,
    Preenciphered-Bodypart-Descriptor, Postenciphered-Bodypart-Descriptor;

IMPORTS Protected-Part-Identifier
          FROM Identifiers-and-Expressions; --  see 7.8

Sealed-Doc-Prof-Descriptor ::= SEQUENCE {
  sealed-doc-prof-identifier   Protected-Part-Identifier,
  sealed-doc-prof-information  Document-Profile-Attribute-Names
}

Document-Profile-Attribute-Names ::= BIT STRING {
  generic-layout-structure(0), specific-layout-structure(1),
  generic-logical-structure(2), specific-logical-structure(3),
  layout-styles(4), presentation-styles(5), sealed-profiles(6),
  enciphered-profiles(7), pre-enciphered-body-parts(8),
  post-enciphered-body-parts(9), external-document-class(10),
  resource-document(11), resources(12), document-application-profile(13),
  document-application-profile-defaults(14), document-architecture-class(15),
  content-architecture-classes(16), interchange-format-class(17),
  oda-version(18), alternative-feature-sets(19), profile-character-sets(20),
  comments-character-sets(21), alternative-representation-character-sets(22),
  page-dimensions(23), medium-types(24), layout-paths(25), protections(26),
  block-alignments(27), fill-orders(28), transparencies(29), colours(30),
  colours-of-layout-object(31), object-colour-tables(32),
  content-background-colours(33), content-foreground-colours(34),
  content-colour-tables(35), borders(36), page-positions(37),
  types-of-coding(38), coding-attributes(39), presentation-features(40),
  number-of-objects-per-page(41), unit-scaling(42), fonts-list(43),
  colour-characteristics(44), colour-spaces-list(45),
  assured-reproduction-areas(86), title(46), subject(47),
  document-reference(48), document-type(49), abstract(50), keywords(51),
  document-date-and-time(52), creation-date-and-time(53),
  local-filing-date-and-time(54), expiry-date-and-time(55),
  start-date-and-time(56), purge-date-and-time(57), release-date-and-time(58),
  revision-history(59), organizations(60), preparers(61), owners(62),
  authors(63), copyright(64), status(65), user-specific-codes(66),
  distribution-list(67), additional-information(68),
  references-to-other-documents(69), superseded-documents(70),
  local-file-references(71), document-size(72), number-of-pages(73),
  languages(74), authorization(75), security-classification(76),
  access-rights(77), sealed-information-encoding(78), oda-security-label(79),
  sealed-document-profiles(80), pre-sealed-document-body-parts(81),
  post-sealed-document-body-parts(82), enciphered-document-profiles(83),
  pre-enciphered-document-body-parts(84),
  post-enciphered-document-body-parts(85)}

Enciphered-Doc-Prof-Descriptor ::= SEQUENCE {
  enciphered-doc-prof-identifier   Protected-Part-Identifier,
  enciphered-doc-prof-information  Enciphered-Information
}

Preenciphered-Bodypart-Descriptor ::= SEQUENCE {
  preenciphered-bodypart-identifier  Protected-Part-Identifier,
  preenciphered-bodypart-info        Enciphered-Information
}

Postenciphered-Bodypart-Descriptor ::= SEQUENCE {
  postenciphered-bodypart-identifier  Protected-Part-Identifier,
  postenciphered-bodypart-info        Enciphered-Information
}

Enciphered-Information ::= OCTET STRING

END

-- Generated by Asnp, the ASN.1 pretty-printer of France Telecom R&D
