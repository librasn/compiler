XYZ	-- The module reference is not standardized
DEFINITIONS XER INSTRUCTIONS AUTOMATIC TAGS ::=
BEGIN
IMPORTS
String FROM XSD{joint-iso-itu-t asn1(1) specification(0) modules(0)
			    xsd-module(2) version1(1)}
			/* For a Version 2 mapping, the last component of the module
                    identifier would be version2(2) */
;

Xyz-elem ::= [NAME AS UNCAPITALIZED] XSD.String
Xyz-type ::= SEQUENCE {
	xyz-attr [ATTRIBUTE] BOOLEAN OPTIONAL }

ENCODING-CONTROL XER
	GLOBAL-DEFAULTS MODIFIED-ENCODINGS
	GLOBAL-DEFAULTS CONTROL-NAMESPACE
		"http://www.w3.org/2001/XMLSchema-instance"
		PREFIX "xsi"
	NAMESPACE ALL AS "http://example.com/xyz"
		PREFIX "xyz"
END
