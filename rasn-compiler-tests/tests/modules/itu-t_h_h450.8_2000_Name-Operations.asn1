-- Module Name-Operations (H.450.8:02/2000)
-- See also ITU-T H.450.8 (02/2000)
-- See also the index of all ASN.1 assignments needed in this document

Name-Operations {itu-t recommendation h 450 8 version1(0) name-operations(0)}
DEFINITIONS AUTOMATIC TAGS ::=
BEGIN

IMPORTS
  OPERATION, ERROR
    FROM Remote-Operations-Information-Objects {joint-iso-itu-t
      remote-operations(4) informationObjects(5) version1(0)}
  EXTENSION, Extension{}
    FROM Manufacturer-specific-service-extension-definition {itu-t
      recommendation h 450 1 version1(0) msi-definition(18)}
  MixedExtension
    FROM Call-Hold-Operations {itu-t recommendation h 450 4 version1(0)
      call-hold-operations(0)};

NameOperations OPERATION ::=
  {callingName | alertingName | connectedName | busyName}

callingName OPERATION ::= {
  ARGUMENT
    SEQUENCE {name          Name,
              extensionArg  SEQUENCE SIZE (0..255) OF MixedExtension OPTIONAL,
              ...}
  RETURN RESULT    FALSE
  ALWAYS RESPONDS  FALSE
  CODE             local:0
}

alertingName OPERATION ::= {
  ARGUMENT
    SEQUENCE {name          Name,
              extensionArg  SEQUENCE SIZE (0..255) OF MixedExtension OPTIONAL,
              ...}
  RETURN RESULT    FALSE
  ALWAYS RESPONDS  FALSE
  CODE             local:1
}

connectedName OPERATION ::= {
  ARGUMENT
    SEQUENCE {name          Name,
              extensionArg  SEQUENCE SIZE (0..255) OF MixedExtension OPTIONAL,
              ...}
  RETURN RESULT    FALSE
  ALWAYS RESPONDS  FALSE
  CODE             local:2
}

busyName OPERATION ::= {
  ARGUMENT
    SEQUENCE {name          Name,
              extensionArg  SEQUENCE SIZE (0..255) OF MixedExtension OPTIONAL,
              ...}
  RETURN RESULT    FALSE
  ALWAYS RESPONDS  FALSE
  CODE             local:3
}

Name ::= CHOICE {
  namePresentationAllowed     NamePresentationAllowed,
  namePresentationRestricted  NamePresentationRestricted,
  nameNotAvailable            NULL,
  ...
}

NamePresentationAllowed ::= CHOICE {
  simpleName    SimpleName,
  extendedName  ExtendedName,
  ...
}

NamePresentationRestricted ::= CHOICE {
  simpleName      SimpleName,
  extendedName    ExtendedName,
  restrictedNull  NULL, -- only used in case of interworking where other network

  -- provides indication that the name is restricted without
  -- the name itself
  ...
}

SimpleName ::= OCTET STRING(SIZE (1..50))

ExtendedName ::= BMPString(SIZE (1..256)) -- Basic ISO/IEC 10646-1 (Unicode)


END -- of Name-Operations

-- Generated by Asnp, the ASN.1 pretty-printer of France Telecom R&D
