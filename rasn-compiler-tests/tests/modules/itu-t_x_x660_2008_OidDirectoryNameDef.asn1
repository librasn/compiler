-- Module OidDirectoryNameDef (X.660:08/2008)
-- See also ITU-T X.660 (08/2008)
-- See also the index of all ASN.1 assignments needed in this document

OidDirectoryNameDef {joint-iso-itu-t registration-procedures(17) module(1)
  oidDirectoryNameDef(1)} DEFINITIONS ::=
BEGIN

-- EXPORTS All
IMPORTS
  ATTRIBUTE, MATCHING-RULE, OBJECT-CLASS, NAME-FORM, alias
    FROM InformationFramework {joint-iso-itu-t ds(5) module(1)
      informationFramework(1) 4}
  integerMatch
    FROM SelectedAttributeTypes {joint-iso-itu-t ds(5) module(1)
      selectedAttributeTypes(5) 4};

-- Attribute types
oidC1 ATTRIBUTE ::= {
  WITH SYNTAX             INTEGER
  EQUALITY MATCHING RULE  integerMatch
  ID                      id-oidC1
}

oidC2 ATTRIBUTE ::= {
  WITH SYNTAX             INTEGER
  EQUALITY MATCHING RULE  integerMatch
  ID                      id-oidC2
}

oidC ATTRIBUTE ::= {
  WITH SYNTAX             INTEGER
  EQUALITY MATCHING RULE  integerMatch
  ID                      id-oidC
}

-- Object class definition
oidRoot OBJECT-CLASS ::= {
  SUBCLASS OF   {alias}
  MUST CONTAIN  {oidC1 | oidC2 | oidC}
  ID            id-oidRoot
}

-- Name form
oidRootNf NAME-FORM ::= {
  NAMES            oidRoot
  WITH ATTRIBUTES  {oidC1 | oidC2 | oidC}
  ID               id-oidRootNf
}

-- Object identifier assignments
id OBJECT IDENTIFIER ::=
  {joint-iso-itu-t registration-procedures(17) module(1) directory-defs(2)}

id-oidC1 OBJECT IDENTIFIER ::= {id 0}

id-oidC2 OBJECT IDENTIFIER ::= {id 1}

id-oidC OBJECT IDENTIFIER ::= {id 2}

id-oidRoot OBJECT IDENTIFIER ::= {id 3}

id-oidRootNf OBJECT IDENTIFIER ::= {id 4}

END

-- Generated by Asnp, the ASN.1 pretty-printer of France Telecom R&D
