-- Module UMFObjId (X.742:04/1995)
-- See also ITU-T X.742 (04/1995)
-- See also the index of all ASN.1 assignments needed in this document

UMFObjId {joint-iso-itu-t ms(9) function(2) part10(10) asn1Modules(2) 0}
DEFINITIONS ::=
BEGIN

umf-mo OBJECT IDENTIFIER ::=
  {joint-iso-itu-t ms(9) function(2) part10(10) managedObjectClass(3)}

umf-pkg OBJECT IDENTIFIER ::=
  {joint-iso-itu-t ms(9) function(2) part10(10) package(4)}

umf-par OBJECT IDENTIFIER ::=
  {joint-iso-itu-t ms(9) function(2) part10(10) parameter(5)}

umf-nb OBJECT IDENTIFIER ::=
  {joint-iso-itu-t ms(9) function(2) part10(10) nameBinding(6)}

umf-att OBJECT IDENTIFIER ::=
  {joint-iso-itu-t ms(9) function(2) part10(10) attribute(7)}

umf-act OBJECT IDENTIFIER ::=
  {joint-iso-itu-t ms(9) function(2) part10(10) action(9)}

umf-not OBJECT IDENTIFIER ::=
  {joint-iso-itu-t ms(9) function(2) part10(10) notification(10)}

END

-- Generated by Asnp, the ASN.1 pretty-printer of France Telecom R&D
