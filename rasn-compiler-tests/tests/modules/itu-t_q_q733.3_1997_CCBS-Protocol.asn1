-- Module CCBS-Protocol (Q.733.3:06/1997)
-- See also ITU-T Q.733.3 (06/1997)
-- See also the index of all ASN.1 assignments needed in this document

CCBS-Protocol {itu-t recommendation q 733 3 modules(2) operations-and-errors(1)
  version2(2)} DEFINITIONS EXPLICIT TAGS ::=
BEGIN

IMPORTS
  OPERATION, ERROR
    FROM Remote-Operations-Information-Objects {joint-iso-itu-t
      remote-operations(4) informationObjects(5) version1(0)};

-- operations types
ccbsRequest OPERATION ::= {
  ARGUMENT
    SEQUENCE {calledPartyNumber               CalledPartyNumber,
              retainSupported                 BOOLEAN DEFAULT FALSE,
              userServiceInf                  [1] IMPLICIT USICode OPTIONAL,
              callingPartyNumber
                [2] IMPLICIT CallingPartyNumber OPTIONAL,
              userServiceInfPrime             [3] IMPLICIT USICode OPTIONAL,
              accessTransportParameter
                [4] IMPLICIT AccessTransport OPTIONAL,
              ...,
              additionalCalledPartyNumber
                [5] IMPLICIT AdditionalCalledPartyNumber OPTIONAL}
  RESULT    SEQUENCE {retainSupported  BOOLEAN DEFAULT FALSE,
                      ...}
  ERRORS    {shortTermDenial | longTermDenial}
  CODE      global:{ccbsOID ccbsrequest(1)}
}

-- Timer T = CCBS-T2
ccbsCancel OPERATION ::= {
  --	PARAMETER 	cancelCause CauseCode
  CODE  global:{ccbsOID ccbscancel(2)}
}

-- the cancelCause parameter is optional
-- and may not be sent in certain circumstances
ccbsSuspend OPERATION ::= {CODE  global:{ccbsOID ccbssuspend(3)}
}

ccbsResume OPERATION ::= {CODE  global:{ccbsOID ccbsresume(4)}
}

remoteUserFree OPERATION ::= {CODE  global:{ccbsOID remoteuserfree(5)}
}

--error type definitions
shortTermDenial ERROR ::= {CODE  global:{ccbsOID shorttermdenial(6)}
}

longTermDenial ERROR ::= {CODE  global:{ccbsOID longtermdenial(7)}
}

--constants and data type definitions
CalledPartyNumber ::= OCTET STRING(SIZE (1..10))

-- the calling party number is coded as described
-- in itu-t recommendation q763
CallingPartyNumber ::= OCTET STRING(SIZE (1..10))

-- the calling party number is coded as described
-- in itu-t recommendation q763
CauseCode ::= ENUMERATED {
  cCBS-T3-Timeout(1), cCBS-T4-Timeout(2), cCBS-T7-Timeout(3),
  cCBS-T9-Timeout(4)}

USICode ::= OCTET STRING(SIZE (1..11))

-- the USICode is coded as described in itu-t recommendation q763
AccessTransport ::= OCTET STRING(SIZE (1..maxAccessTransportLength))

-- the ATP is used to carry HLC, LLC, Calling Party SUB and
-- Called Party SUB as described in itu-t recommendation q931
AdditionalCalledPartyNumber ::= OCTET STRING(SIZE (1..11))

-- the AdditionalCalledPartyNumber is coded as the Generic Number parameter
-- (with Number qualifier indicator set to "additional called number")
-- described in itu-t recommendation q763
maxAccessTransportLength INTEGER ::=
  255

-- object identifier path
ccbsOID OBJECT IDENTIFIER ::=
  {itu-t recommendation q 733 3 operations-and-errors(1)}

END -- of CCBS Protocol

-- Generated by Asnp, the ASN.1 pretty-printer of France Telecom R&D
