-- Module Audio-Presentation-Attributes (T.419:08/1995)
-- See also ITU-T T.419 (08/1995)
-- See also the index of all ASN.1 assignments needed in this document

Audio-Presentation-Attributes {2 8 1 9 2} DEFINITIONS ::=
BEGIN

EXPORTS Audio-Attributes;

IMPORTS
  Character-Data
    FROM Document-Profile-Descriptor {2 8 1 5 6}; --  see ITU-T Rec. T.415 | ISO/IEC 8613-5

Audio-Attributes ::= SET {
  temporal-envelope
    [0] IMPLICIT SEQUENCE {beginning-Envelope
                             [0] IMPLICIT Beginning-Envelope OPTIONAL,
                           ending-Envelope
                             [1] IMPLICIT Ending-Envelope OPTIONAL} OPTIONAL,
  clipping            [1] IMPLICIT Clipping OPTIONAL,
  --intended-duration	[2]	Intended-Duration OPTIONAL,
  attenuation         [3] IMPLICIT Attenuation OPTIONAL,
  frequency-envelope  [4] IMPLICIT SET OF Frequency-Envelope-Point OPTIONAL
}

Beginning-Envelope ::= SEQUENCE OF Temporal-Envelope-Point

Ending-Envelope ::= SEQUENCE OF Temporal-Envelope-Point

Temporal-Envelope-Point ::= SEQUENCE {
  offset
    [0]  CHOICE {time-Offset       [0]  Time-Offset,
                 marker-Reference  [1]  Marker-Reference},
  attenuation  [1] IMPLICIT Attenuation
}

Clipping ::= SEQUENCE {
  start-time
    [0]  CHOICE {time-Offset       [0]  Time-Offset,
                 marker-Reference  [1]  Marker-Reference} OPTIONAL,
  end-time
    [1]  CHOICE {time-Offset       [0]  Time-Offset,
                 marker-Reference  [1]  Marker-Reference} OPTIONAL
}

Time-Offset ::= INTEGER

Marker-Reference ::= CHOICE {
  unique-label  [0] IMPLICIT OBJECT IDENTIFIER,
  description   [1] IMPLICIT Character-Data
}

Attenuation ::= SET OF Attenuation-Pair

Attenuation-Pair ::= SEQUENCE {
  channel-name       [0] IMPLICIT PrintableString,
  attenuation-value  [1] IMPLICIT REAL
}

Frequency-Envelope-Point ::= SEQUENCE {
  one-third-oct-pref-freq  [0] IMPLICIT REAL,
  attenuation              [1] IMPLICIT Attenuation
}

END

-- Generated by Asnp, the ASN.1 pretty-printer of France Telecom R&D
