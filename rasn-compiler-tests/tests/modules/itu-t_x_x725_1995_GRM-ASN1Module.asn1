-- Module GRM-ASN1Module (X.725:11/1995)
-- See also ITU-T X.725 (11/1995)
-- See also the index of all ASN.1 assignments needed in this document

GRM-ASN1Module {joint-iso-itu-t ms(9) smi(3) part7(7) asn1Module(2) 2}
DEFINITIONS ::=
BEGIN

IMPORTS
  ObjectInstance
    FROM CMIP-1 {joint-iso-itu-t ms(9) cmip(1) version(1) protocol(3)}
  SimpleNameType, GroupObjects
    FROM Attribute-ASN1Module {joint-iso-itu-t ms(9) smi(3) part2(2)
      asn1Module(2) 1};

RelationshipClass ::= OBJECT IDENTIFIER

RelationshipMapping ::= OBJECT IDENTIFIER

Null ::= NULL

END

-- Generated by Asnp, the ASN.1 pretty-printer of France Telecom R&D
