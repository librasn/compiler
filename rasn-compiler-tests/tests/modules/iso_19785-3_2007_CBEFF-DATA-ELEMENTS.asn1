-- Module CBEFF-DATA-ELEMENTS (ISO/IEC 19785-3:2007)
--
-- Copyright © ISO/IEC 2007. This version of
-- this ASN.1 module is part of ISO/IEC 10031-2:2007;
-- see the ISO|IEC text itself for full legal notices.
--
CBEFF-DATA-ELEMENTS {iso standard 19785 modules(0)
  types-for-cbeff-data-elements(1)} DEFINITIONS AUTOMATIC TAGS ::=
BEGIN

BDBFormat ::= SEQUENCE {
  format-owner  INTEGER(1..65535),
  format-type   INTEGER(1..65535)
}

EncryptionOptions ::= BOOLEAN

-- NO ENCRYPTION = false, ENCRYPTION = true.
IntegrityOptions ::= BOOLEAN

-- NO INTEGRITY = false, INTEGRITY = true.
SubheaderCount ::= INTEGER(0..255)

BiometricType ::= BIT STRING {
  no-value-available(0), multiple-biometric-types(1), scent(2), dna(3),
  ear(4), face(5), finger(6), foot(7), hand-geometry(8), vein(9), iris(10),
  retina(11), voice(12), gait(13), keystroke(14), lip-movement(15),
  signature-sign(16)}(SIZE (17), ...)

BiometricSubtype ::= CHOICE {any        Any-sub-type,
                             vein-only  Vein-only
}

-- The abstract value no-value-available is encoded as
-- the CHOICE value any:'0000000'
Any-sub-type ::= BIT STRING {
  left(6), right(5), thumb(4), pointer-finger(3), middle-finger(2),
  ring-finger(1), little-finger(0)}(SIZE (7))

Vein-only ::= BIT STRING {
  left(6), right(5), palm(4), back-of-hand(3), wrist(2), reserved1(1),
  reserved2(0)}(SIZE (7))

ChallengeResponse ::= OCTET STRING

-- A patron format that uses this type shall specify
-- its encoding for no-value-available
BDBCreationDate ::=
  Date-Time

-- A patron format that uses this type shall specify
-- its encoding for no-value-available
BDBIndex ::= OCTET STRING(SIZE (16))

-- A patron format that uses this type shall specify
-- its encoding for no-value-available
ProcessedLevel ::= ENUMERATED {no-value-available, raw, intermediate, processed
}

Product ::= SEQUENCE {
  product-owner  INTEGER(1..65535) OPTIONAL,
  product-type   INTEGER(1..65535) OPTIONAL
}

Purpose ::= ENUMERATED {
  no-value-available, verify, identify, enroll, enroll-verify, enroll-identify,
  audit}

Quality ::= INTEGER {
  no-value-available(-3), quality-not-supported(-2), quality-not-recorded(-1)
}(-3..100)

BDBValidityPeriod ::= SEQUENCE {
  not-valid-before  Date-Time OPTIONAL,
  not-valid-after   Date-Time OPTIONAL
}

BIRCreationDate ::= Date-Time

-- A patron format that uses this type shall specify
-- its encoding for no-value-available
Creator ::= UTF8String

-- A patron format that uses this type shall specify
-- its encoding for no-value-available
BIRIndex ::= OCTET STRING(SIZE (16))

-- A patron format that uses this type shall specify
-- its encoding for no-value-available
PatronFormat ::= SEQUENCE {
  patron-format-owner  INTEGER(1..65535) OPTIONAL,
  patron-format-type   INTEGER(1..65535) OPTIONAL
}

Payload ::= OCTET STRING

-- A patron format that uses this type shall specify
-- its encoding for no-value-available
BIRValidityPeriod ::= SEQUENCE {
  not-valid-before  Date-Time OPTIONAL,
  not-valid-after   Date-Time OPTIONAL
}

HeaderVersion ::= SEQUENCE {
  header-major  INTEGER {version1(1)}(0..15),
  header-minor  INTEGER {version0(0)}(0..15)
}

--no-value-available is encoded by {header-major 0, header-minor 0}
SBFormat ::= SEQUENCE {
  sb-owner  INTEGER(1..65535) OPTIONAL,
  sb-type   INTEGER(1..65535) OPTIONAL
}

CBEFFVersion ::= SEQUENCE {
  cbeff-major  INTEGER {version2(2)}(0..15),
  cbeff-minor  INTEGER {version0(0)}(0..15)
}

--no-value-available is encoded by {cbeff-major 0, cbeff-minor 0}
BiometricDataBlock ::= OCTET STRING

SecurityBlock ::= OCTET STRING

Date-Time ::= TIME ((SETTINGS "Basic=Date-Time Date=YMD Year=Basic Time=HMS Midnight = Start Local-or-UTC=Z"))

OneByte ::= INTEGER(0..255)

TwoByte ::= INTEGER(0..65535)

ThreeByte ::= INTEGER(0..16777215)

FourByte ::= INTEGER(0..4294967295)

OneBit ::= INTEGER(0..1)

TwoBit ::= INTEGER(0..3)

ThreeBit ::= INTEGER(0..7)

FourBit ::= INTEGER(0..15)

END

-- Generated by Asnp, the ASN.1 pretty-printer of France Telecom R&D
