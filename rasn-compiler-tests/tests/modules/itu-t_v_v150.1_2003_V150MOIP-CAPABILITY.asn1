-- Module V150MOIP-CAPABILITY (V.150.1:01/2003)
-- See also ITU-T V.150.1 (01/2003)
-- See also the index of all ASN.1 assignments needed in this document

V150MOIP-CAPABILITY {itu-t (0) recommendation (0) v (22) 150 moip (0) major-version-one(1) minor-version-one(1)}
DEFINITIONS AUTOMATIC TAGS ::=
BEGIN

IMPORTS NonStandardParameter
          FROM MULTIMEDIA-SYSTEM-CONTROL;

V150MoIPCapability ::= SEQUENCE {
  nonStandard             SEQUENCE OF NonStandardParameter OPTIONAL,
  modemRelayType          CHOICE {v-mr  NULL,
                                  u-mr  NULL,
                                  ...},
  gatewayType
    CHOICE {ntcx  NULL, -- No Transcompression--
            stcx  NULL, -- Single Transcompression--
            dtcx
              CHOICE-- Double Transcompression-- {single  NULL, -- Preferred mode between two gateways--
                                                  double  NULL, --  with double transcompression ability--
                                                  ...},
            ...},
  callDiscriminationMode
    CHOICE {audio        NULL,
            g2-choice    NULL,
            combination  NULL,
            ...},
  sprtParameters
    SEQUENCE {maxPayloadSizeChannel0  INTEGER(140..256) OPTIONAL, -- Default 140--
              maxPayloadSizeChannel1  INTEGER(132..256) OPTIONAL, -- Default 132--
              maxWindowSizeChannel1   INTEGER(32..96) OPTIONAL, -- Default 32--
              maxPayloadSizeChannel2  INTEGER(132..256) OPTIONAL, -- Default 132--
              maxWindowSizeChannel2   INTEGER(8..32) OPTIONAL, -- Default 8,--
              maxPayloadSizeChannel3  INTEGER(140..256) OPTIONAL, -- Default 140--
              ...} OPTIONAL,
  modulationSupport
    SEQUENCE {v34FullDuplex  NULL OPTIONAL,
              v34HalfDuplex  NULL OPTIONAL,
              v32bis-v32     NULL OPTIONAL,
              v22bis-v22     NULL OPTIONAL,
              v17            NULL OPTIONAL,
              v29HalfDuplex  NULL OPTIONAL,
              v27ter         NULL OPTIONAL,
              v26ter         NULL OPTIONAL,
              v26bis         NULL OPTIONAL,
              v23FullDuplex  NULL OPTIONAL,
              v23HalfDuplex  NULL OPTIONAL,
              v21            NULL OPTIONAL,
              v90Analog      NULL OPTIONAL,
              v90Digital     NULL OPTIONAL,
              v92Analog      NULL OPTIONAL,
              v92Digital     NULL OPTIONAL,
              v91            NULL OPTIONAL,
              ...},
  compressionMode
    SEQUENCE {-- Including a SEQUENCE for a particular compression mode, but not
              -- including any of the optional parameters within the SEQUENCE,
              -- indicates support for the specific compression mode, but assumes that
              -- all parameter values are set to their default values
              mnp5    NULL OPTIONAL,
              v44
                SEQUENCE {numTxCodewords     INTEGER(256..65535),
                          numRxCodewords     INTEGER(256..65535),
                          maxTxStringLength  INTEGER(32..255),
                          maxRxStringLength  INTEGER(32..255),
                          lenTxHistory       INTEGER(512..65535),
                          lenRxHistory       INTEGER(512..65535),
                          ...} OPTIONAL,
              v42bis
                SEQUENCE {numCodewords     INTEGER(512..65535) OPTIONAL,
                          maxStringLength  INTEGER(6..250) OPTIONAL,
                          ...} OPTIONAL,
              ...} OPTIONAL,
  delayedJMEnabled        BOOLEAN,
  ...
}

END -- End of ASN.1 definition

-- Generated by Asnp, the ASN.1 pretty-printer of France Telecom R&D
