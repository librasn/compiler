-- Module InteractiveAgent (Q.814:02/2000)
-- See also ITU-T Q.814 (02/2000)
-- See also the index of all ASN.1 assignments needed in this Recommendation

InteractiveAgent {itu-t(0) recommendation(0) q(17) q814(814) ia(0) messages(0)}
DEFINITIONS IMPLICIT TAGS ::=
BEGIN

-- EXPORTS everything
IaMessage ::= CHOICE {
  basicMessage     BasicMessage, -- Basic Message
  iaStatusMessage  IaStatusMessage, -- IA Status/Control Message
  enhancedMessage  EnhancedMessage -- Security Module Enhanced Message
}

BasicMessage ::= CHOICE {basicMessage1  GeneralString,
                         basicMessage2  IA5String
}

IaStatusMessage ::= BIT STRING(SIZE (32))

EnhancedMessage ::= OCTET STRING -- Security Module Enhanced Message

END

-- Generated by Asnp, the ASN.1 pretty-printer of France Telecom R&D
