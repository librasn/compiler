-- Module H310-TERMINAL-MANAGEMENT (H.310:09/1998)
-- See also ITU-T H.310 (09/1998)
-- See also the index of all ASN.1 assignments needed in this document

H310-TERMINAL-MANAGEMENT DEFINITIONS AUTOMATIC TAGS ::=
BEGIN

-- Export all symbols
VideoFrameSynchronousCandIPDU ::= SEQUENCE {
  elementaryStream
    CHOICE {ts-PID       INTEGER(1..8191),
            ps-StreamID
              SEQUENCE {streamID           INTEGER(0..255),
                        streamIDExtension  INTEGER(0..255) OPTIONAL},
            ...},
  resourceID                  INTEGER(0..65535) OPTIONAL,
  videoFrameSynchronousCandI
    CHOICE {videoFrameSynchronousControl     VideoFrameSynchronousControl,
            videoFrameSynchronousIndication  VideoFrameSynchronousIndication,
            ...},
  ...
}

VideoFrameSynchronousControl ::= CHOICE {
  nonStandard                       NonStandardParameter,
  videoFreezePictureReleaseControl  NULL, -- not used for Recommendation H.261 										   or H.263
  ...
}

VideoFrameSynchronousIndication ::= CHOICE {
  nonStandard               NonStandardParameter,
  closedCaption             OCTET STRING,
  splitScreenIndication     NULL, -- not used for Recommendation H.261 	   or H.263
  documentCameraIndication  NULL, -- not used for Recommendation H.261 										   or H.263
  ...
}

NonStandardParameter ::= SEQUENCE {
  nonStandardIdentifier  NonStandardIdentifier,
  data                   OCTET STRING
}

NonStandardIdentifier ::= CHOICE {
  object           OBJECT IDENTIFIER,
  h221NonStandard
    SEQUENCE {t35CountryCode    INTEGER(0..255),
              t35Extension      INTEGER(0..255),
              manufacturerCode  INTEGER(0..65535)}
}

END

-- Generated by Asnp, the ASN.1 pretty-printer of France Telecom R&D
