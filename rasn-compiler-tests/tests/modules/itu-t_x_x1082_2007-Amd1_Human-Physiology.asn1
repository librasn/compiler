Human-Physiology {joint-iso-itu-t(2) telebiometrics(42) human-physiology (2) modules(0) main(0) version (0)}
"/Telebiometrics/Human-Physiology/Modules/Main_module/First_Version"
DEFINITIONS::=
BEGIN
IMPORTS id-hum-phys, iri-hum-phys FROM
        Telebiometrics {joint-iso-itu-t(2) telebiometrics (42)
                        modules(0) main(0) version(0)};
-- *1* OBJECT IDENTIFIER allocations specific to ITU-T X.1082
id-symbols OBJECT IDENTIFIER ::= {id-hum-phys symbols(1)}
id-symbol-comb OBJECT IDENTIFIER ::=
                     {id-hum-phys symbol-combinations(2)}
id-tango-in OBJECT IDENTIFIER ::= {id-symbols tango-in(1)}
id-video-in OBJECT IDENTIFIER ::= {id-symbols video-in(2)}
id-audio-in OBJECT IDENTIFIER ::= {id-symbols audio-in(3)}
id-chemo-in OBJECT IDENTIFIER ::= {id-symbols chemo-in(4)}
id-radio-in OBJECT IDENTIFIER ::= {id-symbols radio-in(5)}
id-calor-in OBJECT IDENTIFIER ::= {id-symbols calor-in(6)}
id-tango-out OBJECT IDENTIFIER ::= {id-symbols tango-out(7)}
id-video-out OBJECT IDENTIFIER ::= {id-symbols video-out(8)}
id-audio-out OBJECT IDENTIFIER ::= {id-symbols audio-out(9)}
id-chemo-out OBJECT IDENTIFIER ::= {id-symbols chemo-out(10)}
id-radio-out OBJECT IDENTIFIER ::= {id-symbols radio-out(11)}
id-calor-out OBJECT IDENTIFIER ::= {id-symbols calor-out(12)}
id-safe OBJECT IDENTIFIER::= {id-symbols safe(13)}
id-thresholds OBJECT IDENTIFIER ::= {id-symbols thresholds(14)}
-- In addition object identifier values are allocated with all
-- values of "<x>" from 1 to 4095 in the following:
-- id-comb<x> OBJECT IDENTIFIER ::={id-symbol-comb <x>}
-- Example:
id-comb2307 OBJECT IDENTIFIER ::= {id-symbol-comb 2307}

-- *2* OID-IRI or RELATIVE-OID-IRI allocations specific to ITU-T X.1082
--     These are all relative to iri-hum-phys
-- *2.1* OID-IRIs for symbols
iri-symbols RELATIVE-OID-IRI ::= "Symbols"
iri-tango-in RELATIVE-OID-IRI ::= "Symbols/Tango_in"
iri-video-in RELATIVE-OID-IRI ::= "Symbols/Video_in"
iri-audio-in RELATIVE-OID-IRI ::= "Symbols/Audio_in"
iri-chemo-in RELATIVE-OID-IRI ::= "Symbols/Chemo_in"
iri-radio-in RELATIVE-OID-IRI ::= "Symbols/Radio_in"
iri-calor-in RELATIVE-OID-IRI ::= "Symbols/Calor_in"
iri-tango-out RELATIVE-OID-IRI ::= "Symbols/Tango_out"
iri-video-out RELATIVE-OID-IRI ::= "Symbols/Video_out"
iri-audio-out RELATIVE-OID-IRI ::= "Symbols/Audio_out"
iri-chemo-out RELATIVE-OID-IRI ::= "Symbols/Chemo_out"
iri-radio-out RELATIVE-OID-IRI ::= "Symbols/Radio_out"
iri-calor-out RELATIVE-OID-IRI ::= "Symbols/Calor_out"
iri-safe RELATIVE-OID-IRI ::= "Symbols/Safe"
iri-thresholds RELATIVE-OID-IRI ::= "Symbols/Thresholds"
-- *2.2* OID-IRIs for symbol combinations
iri-symbol-comb RELATIVE-OID-IRI ::= "Symbol_Combinations"
-- In additon, relative oid-iri values are allocated with all
-- values of "<x>" from 1 to 4095 in the following:
-- iri-comb<x> RELATIVE-OID-IRI ::= "Symbol_Combinations/<x>"
-- Example:
iri-comb2307 RELATIVE-OID-IRI ::= "Symbol-Combinations/2307"
END
