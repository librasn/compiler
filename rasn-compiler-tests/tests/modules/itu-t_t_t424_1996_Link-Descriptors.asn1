-- Module Link-Descriptors (T.424:07/1996)
-- See also ITU-T T.424 (07/1996)
-- See also the index of all ASN.1 assignments needed in this document

Link-Descriptors {2 8 1 14 3} DEFINITIONS ::=
BEGIN

EXPORTS
  Link-Class-Descriptor, Link-Descriptor, Link-or-Link-Class-Identifier,
    Enciphered-Link-Descriptor;

IMPORTS
  Reference-Name
    FROM External-References {2 8 1 12 1}
  --  see ITU-T Rec. T.422 | ISO/IEC 8613-12
  Location-Expression
    FROM Location-Expressions {2 8 1 12 0}
  --  see ITU-T Rec. T.422 | ISO/IEC  8613-12
  Style-Identifier, Protected-Part-Identifier
    FROM Identifiers-and-Expressions {2 8 1 5 7}
  --  see ITU-T Rec. T.415 | ISO/IEC 8613-5
  Comment-String, Sealed
    FROM Layout-Descriptors {2 8 1 5 8}
  --  see ITU-T Rec. T.415 | ISO/IEC 8613-5
  Temporal-Relations, Presentation-Time
    FROM Temporal-Relationships;

--  see 7.5
Link-or-Link-Class-Identifier ::= [APPLICATION 9] IMPLICIT PrintableString

--	only digits and space are used in the present version of this Recommendation | International Standard;
--	other characters are reserved for extensions
Link-Class-Descriptor ::= SET {
  link-class-identifier   Link-or-Link-Class-Identifier,
  link-roles              [1]  SEQUENCE OF Link-Role OPTIONAL,
  user-readable-comments  [2] IMPLICIT Comment-String OPTIONAL,
  user-visible-name       [3] IMPLICIT Comment-String OPTIONAL,
  application-comments    [25] IMPLICIT OCTET STRING OPTIONAL,
  sealed                  [35] IMPLICIT Sealed OPTIONAL,
  temporal-relations      [38] IMPLICIT Temporal-Relations OPTIONAL,
  presentation-time       [39] IMPLICIT Presentation-Time OPTIONAL
}

Link-Descriptor ::= SET {
  link-identifier         Link-or-Link-Class-Identifier,
  link-class              [0] IMPLICIT Link-or-Link-Class-Identifier OPTIONAL,
  link-roles              [1]  SEQUENCE OF Link-Role OPTIONAL,
  user-readable-comments  [2] IMPLICIT Comment-String OPTIONAL,
  user-visible-name       [3] IMPLICIT Comment-String OPTIONAL,
  application-comments    [25] IMPLICIT OCTET STRING OPTIONAL,
  sealed                  [35] IMPLICIT Sealed OPTIONAL,
  temporal-relations      [38] IMPLICIT Temporal-Relations OPTIONAL,
  presentation-time       [39] IMPLICIT Presentation-Time OPTIONAL
}

Link-Role ::= SET {
  link-ends               SET OF Link-End,
  user-readable-comments  [2] IMPLICIT Comment-String OPTIONAL,
  user-visible-name       [3] IMPLICIT Comment-String OPTIONAL,
  application-comments    [25] IMPLICIT OCTET STRING OPTIONAL
}

Link-End ::= SET {
  reference
    SET {reference-name       [0]  Reference-Name OPTIONAL,
         reference-qualifier  [1]  Location-Expression OPTIONAL},
  user-readable-comments  [2] IMPLICIT Comment-String OPTIONAL,
  user-visible-name       [3] IMPLICIT Comment-String OPTIONAL,
  presentation-style      [17] IMPLICIT Style-Identifier OPTIONAL,
  layout-style            [19] IMPLICIT Style-Identifier OPTIONAL,
  application-comments    [25] IMPLICIT OCTET STRING OPTIONAL
}

Enciphered-Link-Descriptor ::= SEQUENCE {
  protected-part-identifier  Protected-Part-Identifier,
  enciphered-information     OCTET STRING
}

END

-- Generated by Asnp, the ASN.1 pretty-printer of France Telecom R&D
