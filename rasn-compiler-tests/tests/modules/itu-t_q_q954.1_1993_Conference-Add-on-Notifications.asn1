-- Module Conference-Add-on-Notifications (Q.954.1:03/1993)
-- See also ITU-T Q.954.1 (03/1993)
-- See also the index of all ASN.1 assignments needed in this document

Conference-Add-on-Notifications {itu-t(0) recommendation(0) q(17) q954(954)
  part1(1) extended-notifications(2)} DEFINITIONS ::=
BEGIN

EXPORTS partyIdNotification;

IMPORTS
  NOTIFICATION
    FROM Notification-Indicator-IE-Data-Structure {itu-t recommendation q
      932 notification-data-structure(6)}
  PartyId
    FROM Conference-Add-On-Operations {itu-t(0) recommendation(0) q(17)
      q954(954) part1(1) operations-and-errors(1)};

partyIdNotification NOTIFICATION ::= {ARGUMENT  PartyId
                                      CODE      local:1
}

END -- of Conference-Add-On-Notifications

-- Generated by Asnp, the ASN.1 pretty-printer of France Telecom R&D
