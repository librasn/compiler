-- Module Flow-Control (Q.932:05/1998)
-- See also ITU-T Q.932 (1998) Amend. 1 (06/2000)
-- See also the index of all ASN.1 assignments needed in this document

Flow-Control {itu-t recommendation q 932 flow-control(8)} DEFINITIONS ::=
BEGIN

EXPORTS flowControl;

IMPORTS
  OPERATION
    FROM Remote-Operations-Information-Objects {joint-iso-itu-t(2)
      remote-operations(4) informationObjects(5) version1(0)};

flowControl OPERATION ::= {
  ARGUMENT
    SEQUENCE {controlReceiver
                ENUMERATED {receiverNotReady(0), receiverReady(1)},
              maximumNumberOfMessages  [0] IMPLICIT INTEGER(1..255) OPTIONAL,
              replenishmentParameter   [1] IMPLICIT INTEGER(1..255) OPTIONAL,
              timerT                   [2] IMPLICIT INTEGER(1..30) OPTIONAL
  }
  CODE      global:{itu-t recommendation q 932 flow-control(8) operation(1)}


-- When the receiverReady coding is sent in FACILITY message, the
-- maximumNumberOfMessages and timerT data elements may optionally
-- be included. The MaximumNumberOfMessages is an integer that specifies
-- the number of messages that may be sent in the time interval specifed by
-- timerT for the call reference identified in the FACILITY message and these
-- may optionally be included when the receiverReady coding is sent. The
-- replenishmentParameter indicates the number of additional messages that
-- may be sent at the end of timer interval timerT.
}

-- This operation is a Class 5 operation
END -- of Flow Control

-- Generated by Asnp, the ASN.1 pretty-printer of France Telecom R&D
