-- Module AttributeModule (X.282:06/1999)
-- See also ITU-T X.282 (06/1999)
-- See also the index of all ASN.1 assignments needed in this document

AttributeModule DEFINITIONS IMPLICIT TAGS ::=
BEGIN

ResettableCounter32 ::= INTEGER(0..4294967295)

Integer32 ::= INTEGER(0..4294967295)

END

-- Generated by Asnp, the ASN.1 pretty-printer of France Telecom R&D
