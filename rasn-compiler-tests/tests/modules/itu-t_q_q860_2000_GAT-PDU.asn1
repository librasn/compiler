-- Module GAT-PDU (Q.860:06/2000)
-- See also ITU-T Q.860 (06/2000)
-- See also the index of all ASN.1 assignments needed in this document

--  Generic addressing and transport APDU coding using ITU-T X.680
GAT-PDU {itu-t recommendation q 860 gat-pdu(1)} DEFINITIONS ::=
BEGIN

EXPORTS GATPDU{};

IMPORTS
  OPERATION
    FROM Remote-Operations-Information-Objects {joint-iso-itu-t
      remote-operations(4) informationObjects(5) version1(0)}
  PartyNumber
    FROM Addressing-Data-Elements {itu-t recommendation q 932
      addressing-data-elements(7)}
  InterpretationComponent
    FROM Interpretation-component {iso standard pss1-generic-procedures(11582)
      interpretation-component(3)}
  Components{}
    FROM Facility-Information-Element-Components {itu-t recommendation q
      932 facility-information-element-component(3)};

GATPDU{OPERATION:Invokable, OPERATION:Returnable} ::= SEQUENCE {
  gatNetworkFacilityExtension  GATNetworkFacilityExtension OPTIONAL,
  serviceIndicator             ServiceIndicator,
  localValueDiscriminator      LocalValueDiscriminator DEFAULT itu-tLocalValue,
  interpretation-APDU          InterpretationComponent OPTIONAL,
  apduPortion                  ApduPortion{{Invokable}, {Returnable}}
}

GATNetworkFacilityExtension ::= [10] IMPLICIT SEQUENCE {
  sourceEntity              [0] IMPLICIT EntityType,
  sourceEntityAddress       [1]  AddressInformation OPTIONAL,
  destinationEntity         [2] IMPLICIT EntityType,
  destinationEntityAddress  [3]  AddressInformation OPTIONAL
}

EntityType ::= INTEGER {endNode(2), anyNode(3), endTerminal(4)}

AddressInformation ::= PartyNumber

ServiceIndicator ::= OBJECT IDENTIFIER

LocalValueDiscriminator ::= INTEGER {itu-tLocalValue(0), iso-iecLocalValue(1)}

ApduPortion{OPERATION:Invokable, OPERATION:Returnable} ::= CHOICE {
  structured
    SEQUENCE (SIZE (1..MAX)) OF Components{{Invokable}, {Returnable}},
  unstructured  OCTET STRING -- e.g. for IN OCCRUI feature
}

END -- of GAT-PDU

-- Generated by Asnp, the ASN.1 pretty-printer of France Telecom R&D
