-- Module DirectoryProtectionMappings (X.830:04/1995)
-- See also ITU-T X.830 (04/1995)
-- See also the index of all ASN.1 assignments needed in this document

DirectoryProtectionMappings {joint-iso-itu-t genericULS(20) modules(1)
  dirProtectionMappings(4)} DEFINITIONS AUTOMATIC TAGS ::=
BEGIN

-- These protection mappings generate bit-compatible encodings
-- to the parameterized types in the Directory Authentication
-- Framework
-- EXPORTS All
IMPORTS
  notation, gulsSecurityTransformations
    FROM ObjectIdentifiers {joint-iso-itu-t genericULS(20) modules(1)
      objectIdentifiers(0)}
  PROTECTION-MAPPING
    FROM Notation {joint-iso-itu-t genericULS(20) modules(1) notation(1)}
  dirEncryptedTransformation, dirSignedTransformation,
    dirSignatureTransformation
    FROM GulsSecurityTransformations {joint-iso-itu-t genericULS(20)
      modules(1) gulsSecurityTransformations(3)};

-- **************************************
-- Directory encrypted Protection Mapping
-- **************************************
-- This protection mapping enables the notation
-- PROTECTED {BaseType, encrypted}
-- to replace the notation
-- ENCRYPTED {BaseType}
-- as provided by ITU-T Rec. X.509 | ISO/IEC 9594-8:1994, and to
-- generate an identical bit-encoding.
-- Security Service:  confidentiality
encrypted PROTECTION-MAPPING ::= {
  SECURITY-TRANSFORMATION  {dirEncryptedTransformation}
}

-- ***********************************
-- Directory signed Protection Mapping
-- ***********************************
-- This protection mapping enables the notation
-- PROTECTED {BaseType, signed}
-- to replace the notation
-- SIGNED {BaseType}
-- as provided by ITU-T Rec. X.509 | ISO/IEC 9594-8:1994, and to
-- generate an identical bit-encoding.
-- Security Service:  data origin authentication, data integrity and
-- (in certain situations) non-repudiation.
signed PROTECTION-MAPPING ::= {
  SECURITY-TRANSFORMATION  {dirSignedTransformation}
}

-- **************************************
-- Directory signature Protection Mapping
-- **************************************
-- This protection mapping enables the notation
-- PROTECTED {BaseType, signature}
-- to provide a functionally-equivalent replacement of the notation
-- SIGNATURE BaseType
-- as provided by ITU-T Rec. X.509 | ISO/IEC 9594-8.
-- Security Service:  data origin authentication, data integrity and
-- (in certain situations) non-repudiation.
signature PROTECTION-MAPPING ::= {
  SECURITY-TRANSFORMATION  {dirSignatureTransformation}
}

END

-- Generated by Asnp, the ASN.1 pretty-printer of France Telecom R&D
