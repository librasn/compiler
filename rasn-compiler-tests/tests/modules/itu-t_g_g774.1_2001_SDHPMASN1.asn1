-- Module SDHPMASN1 (G.774.1:02/2001)
-- See also ITU-T G.774.1 (02/2001)
-- See also the index of all ASN.1 assignments needed in this document

SDHPMASN1 {itu-t(0) recommendation(0) g(7) g774(774) dot(127) part1(1)
  informationModel(0) asn1Module(2) sdhpm(0)} DEFINITIONS IMPLICIT TAGS ::=
BEGIN

--  EXPORTS everything
IMPORTS
  ProbableCause
    FROM Attribute-ASN1Module {joint-iso-itu-t ms(9) smi(3) part2(2)
      asn1Module(2) 1}
  TimePeriod
    FROM MetricModule {joint-iso-itu-t ms(9) function(2) part11(11)
      asn1Module(2) 0};

sdhPM OBJECT IDENTIFIER ::=
  {itu-t(0) recommendation(0) g(7) g774(774) dot(127) part1(1)
   informationModel(0)}

g774-01MObjectClass OBJECT IDENTIFIER ::= {sdhPM managedObjectClass(3)}

g774-01Attribute OBJECT IDENTIFIER ::= {sdhPM attribute(7)}

g774-01NameBinding OBJECT IDENTIFIER ::= {sdhPM nameBinding(6)}

g774-01Package OBJECT IDENTIFIER ::= {sdhPM package(4)}

Integer ::= INTEGER

CSES ::= SET OF SEQUENCE {eventTime  GeneralizedTime,
                          nCSES      NCSESRange}

NCSESRange ::= Integer(2..9)

SDHGranularityPeriod ::=
  TimePeriod(WITH COMPONENTS {
               minutes  (15),
               days     (1)
             })

SDHPVGranularityPeriod ::= TimePeriod(WITH COMPONENTS {
                                        minutes  (15)
                                      })

END --  end of SDHPMASN1

-- Generated by Asnp, the ASN.1 pretty-printer of France Telecom R&D
