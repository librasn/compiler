-- Module BIP-DISCOVERY (X.1083:11/2007)
-- See also ITU-T X.1083 (11/2007)
-- See also the index of all ASN.1 assignments needed in this document

BIP-DISCOVERY {joint-iso-itu-t bip(41) modules(0) bip-discovery(2) version1(1)}
DEFINITIONS AUTOMATIC TAGS ::=
BEGIN

Discovery ::= SEQUENCE {
  protocolVersion        ProtocolVersion,
  masterEndpointAddress  IPAddress,
  masterEndPort          Port DEFAULT 4376,
  ...
}

Announcement ::= SEQUENCE {
  protocolVersion          ProtocolVersion,
  slaveEndpointIPAddress   IPAddress,
  slaveEndpointMACAddress  MACAddress,
  slaveEndpointName        IA5String(SIZE (1..32)),
  bipMessagePort           Port DEFAULT 4376,
  securityProtocols        SEQUENCE OF SecurityProtocol OPTIONAL,
  ...
}

ProtocolVersion ::= SEQUENCE {major  INTEGER(0..255),
                              minor  INTEGER(0..255)
}

IPAddress ::= CHOICE {
  ipv4  OCTET STRING(SIZE (4)),
  ipv6  OCTET STRING(SIZE (16))
}

Port ::= INTEGER(0..65535)

MACAddress ::= OCTET STRING(SIZE (6))

SecurityProtocol ::= SEQUENCE {
  id         SECURITY-PROTOCOL.&id({SecurityProtocols}),
  parameter  SECURITY-PROTOCOL.&Parameter({SecurityProtocols}{@id})
}

SECURITY-PROTOCOL ::= CLASS {&id         OBJECT IDENTIFIER,
                             &Parameter
}

SecurityProtocols SECURITY-PROTOCOL ::=
  {...}

END

-- Generated by Asnp, the ASN.1 pretty-printer of France Telecom R&D
