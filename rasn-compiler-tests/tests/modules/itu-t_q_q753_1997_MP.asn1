-- Module MP (Q.753:06/1997)
-- See also ITU-T Q.753 (06/1997)
-- See also the index of all ASN.1 assignments needed in this document

-- Management Process information model
MP {itu-t(0) recommendation q(17) 753 mp(1) version1(1)} DEFINITIONS EXPLICIT
TAGS ::=
BEGIN

IMPORTS
  OPERATION, ERROR, eventReport, confirmedAction, CNF-ACTION, EVENT,
    RoutePriorityList, failure, partialSuccess, GlobalTitle, PointCodeList,
    CopyData
    FROM OMASE {itu-t(0) recommendation q 754 omase(0) version2(2)};

startMRVT CNF-ACTION ::= {
  ACTIONARG
    SEQUENCE {traceRequested       [1] IMPLICIT BOOLEAN,
              threshold            [2] IMPLICIT INTEGER,
              routePriorityList    [12] IMPLICIT RoutePriorityList OPTIONAL,
              infoRequest
                [13] IMPLICIT BIT STRING {pointCode(0), pointCodeList(1),
                                          routePriorityList(2)} OPTIONAL,
              -- infoRequest is used to indicate that the test initiator node can accept a routeTraceNew
              -- RVR message, and also asks for particular parameters to be returned in it, if it is sent. This
              -- parameter can only be inserted at the initiator node, but it can be copied into regenerated
              -- MRVTs.
              returnUnknownParams
                [14] IMPLICIT BIT STRING {tag15(0), tag16(1)} OPTIONAL,
              -- returnUnknownParams is used to indicate which parameters that a node does not
              -- understand should be returned in an RVR if one is sent (or in an RVA message in the
              -- copyData field if the test initiator is unknown). Bit 0 represents an RVT parameter with tag
              -- value 15, bit 1 an RVT parameter with tag value 16, etc.
              -- This parameter can only be present if infoRequest is present.
              directRouteCheck     [15] IMPLICIT BOOLEAN OPTIONAL,
              ...}
  SPECIFICERRORS  {success | failure | partialSuccess}
  CODE            1
}

startSRVT CNF-ACTION ::= {
  ACTIONARG
    SEQUENCE {traceRequested               [1] IMPLICIT BOOLEAN,
              threshold                    [2] IMPLICIT INTEGER,
              mtpBackwardRoutingRequested  [5] IMPLICIT BOOLEAN OPTIONAL,
              originalGT                   [11] IMPLICIT GlobalTitle OPTIONAL,
              infoRequest
                [13] IMPLICIT BIT STRING {pointCode(0), pointCodeList(1),
                                          routePriorityList(2)} OPTIONAL,
              returnUnknownParams
                [14] IMPLICIT BIT STRING {tag15(0), tag16(1)} OPTIONAL,
              -- returnUnknownParams is used to indicate which parameters that a node does not
              -- understand should be returned in an RVR if one is sent (or in an RVA message in the
              -- copyData field if the test initiator is unknown). Bit 0 represents an RVT parameter with tag
              -- value 15, bit 1 an RVT parameter with tag value 16, etc.
              -- This parameter can only be present if infoRequest is present.
              ...}
  SPECIFICERRORS  {success | failure | partialSuccess}
  CODE            2
}

success EVENT ::= {
  EVENTINFO
    CHOICE {empty     [0] IMPLICIT NULL,
            trace     [1] IMPLICIT PointCodeList,
            traceNew
              [2] IMPLICIT SEQUENCE {pointCodeList
                                       [2] IMPLICIT PointCodeList,
                                     routePriorityList
                                       [3] IMPLICIT RoutePriorityList OPTIONAL,
                                     copyData
                                       [4] IMPLICIT CopyData OPTIONAL,
                                     ...}}
  CODE       0
}

-- the supporting definitions are as in Figure 3/Q.754. On the MIS-User to MP interface, the
-- copyData parameter is used to report parameters not understood in the RVT message (for
-- the supporting definitions are as in Figure 3/Q.754. On the MIS-User to MP interface, the
-- copyData parameter is used to report parameters not understood in the RVT message (for
-- "success", by the test destination, for other results by the node detecting the error).
END -- MP syntax

-- Generated by Asnp, the ASN.1 pretty-printer of France Telecom R&D
