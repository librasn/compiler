-- Module T38(1998) (T.38:11/2015)
-- See also ITU-T T.38 (11/2015)

T38 DEFINITIONS AUTOMATIC TAGS ::=
BEGIN

IFPPacket ::= SEQUENCE {
  type-of-msg  Type-of-msg,
  data-field   Data-Field OPTIONAL
}

Type-of-msg ::= CHOICE {
  t30-indicator
    ENUMERATED {no-signal, cng, ced, v21-preamble, v27-2400-training,
                v27-4800-training, v29-7200-training, v29-9600-training,
                v17-7200-short-training, v17-7200-long-training,
                v17-9600-short-training, v17-9600-long-training,
                v17-12000-short-training, v17-12000-long-training,
                v17-14400-short-training, v17-14400-long-training, ...,
                v8-ansam, v8-signal, v34-cntl-channel-1200, v34-pri-channel,
                v34-CC-retrain, v33-12000-training, v33-14400-training},
  t30-data
    ENUMERATED {v21, v27-2400, v27-4800, v29-7200, v29-9600, v17-7200,
                v17-9600, v17-12000, v17-14400, ...,
                v8, v34-pri-rate, v34-CC-1200, v34-pri-ch, v33-12000, v33-14400}
}

Data-Field ::=
  SEQUENCE OF
    SEQUENCE {field-type
                ENUMERATED {hdlc-data, hdlc-sig-end, hdlc-fcs-OK, hdlc-fcs-BAD,
                            hdlc-fcs-OK-sig-end, hdlc-fcs-BAD-sig-end,
                            t4-non-ecm-data, t4-non-ecm-sig-end, ...,
                            cm-message, jm-message, ci-message, v34rate},
              field-data  OCTET STRING(SIZE (1..65535)) OPTIONAL}

UDPTLPacket ::= SEQUENCE {
  seq-number          INTEGER(0..65535),
  primary-ifp-packet  TYPE-IDENTIFIER.&Type(IFPPacket),
  error-recovery
    CHOICE {secondary-ifp-packets
              SEQUENCE OF TYPE-IDENTIFIER.&Type(IFPPacket),
            fec-info
              SEQUENCE {fec-npackets  INTEGER,
                        fec-data      SEQUENCE OF OCTET STRING}}
}

END

-- Generated by Asnp, the ASN.1 pretty-printer of France Telecom R&D
