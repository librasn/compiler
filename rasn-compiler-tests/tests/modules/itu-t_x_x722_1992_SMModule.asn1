-- Module SMModule (X.722:01/1992)
-- See also ITU-T X.722 (01/1992)
-- See also the index of all ASN.1 assignments needed in this document

--  <ASN1.Version 1994 SMModule {joint-iso-itu-t ms(9) smi(1) part4(4) asn1Module(2) smmmodule(4)} >
SMModule {joint-iso-itu-t ms(9) smi(3) part4(4) asn1Module(2) smmmodule(4)}
DEFINITIONS ::=
BEGIN

REGISTERED-AS ::= TYPE-IDENTIFIER

--  TYPE-IDENTIFIER is defined in ISO/IEC 8824-1 and is available in any module
--  without the necessity for importing it and is defined as:
--  TYPE-IDENTIFIER::= CLASS
--  {
--  &id OBJECT IDENTIFIER UNIQUE,
--  &Type
--  }
--  WITH SYNTAX {&Type IDENTIFIED BY &id}
INFO-REPLY-IDENTIFIER ::= CLASS {
  &Info          OPTIONAL,
  &Reply         OPTIONAL,
  &registeredAs  OBJECT IDENTIFIER UNIQUE
}WITH SYNTAX {INFO &Info
              REPLY &Reply
              IDENTIFIED BY &registeredAs
}

RegisteredAsTable REGISTERED-AS ::=
  {...}

InfoReplyTable INFO-REPLY-IDENTIFIER ::=
  {...}

--  RegisteredAsTable to be filled in by GDMO ATTRIBUTE and PARAMETER
--  Templates
--  InfoReplyTable to be filled in by GDMO ACTION and NOTIFICATION Templates
END

-- Generated by Asnp, the ASN.1 pretty-printer of France Telecom R&D
