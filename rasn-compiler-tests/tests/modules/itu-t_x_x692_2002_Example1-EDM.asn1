-- Generated by Ecnp, the pretty-printer of France Telecom R&D

Example1-EDM {joint-iso-itu-t(2) asn1(1) ecn(4) examples(5) edm-module1(3)}
ENCODING-DEFINITIONS ::=
BEGIN

EXPORTS Example1Encodings;

IMPORTS
  #Married, #Altitude, #EvenPositiveInteger, #EvenNegativeInteger,
    #IntegerRightAligned, #IntegerWithHole, #PositiveInteger, #NegativeInteger,
    #PositiveIntegerBCD, #Fax, #BinaryFile, #Password, #CharacterStringToBit,
    #Sequence1, #Choice, #Sequence2
    FROM Example1-ASN1-Module {joint-iso-itu-t(2) asn1(1) ecn(4) examples(5)
      asn1-module1(2)};

Example1Encodings #ENCODINGS ::= {marriedEncoding-1 |
                                   -- etc
                                   sequence2Encoding}

-- etc
END
