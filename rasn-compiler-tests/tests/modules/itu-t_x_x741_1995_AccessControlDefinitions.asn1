AccessControlDefinitions {joint-iso-itu-t(2) ms(9) function(2) part9(9)
  asn1Module(2) 1} DEFINITIONS ::=
BEGIN

accessControl-Object OBJECT IDENTIFIER ::=
  {joint-iso-itu-t(2) ms(9) function(2) part9(9) managedObjectClass(3)}

accessControl-Package OBJECT IDENTIFIER ::=
  {joint-iso-itu-t(2) ms(9) function(2) part9(9) package(4)}

accessControl-Parameter OBJECT IDENTIFIER ::=
  {joint-iso-itu-t(2) ms(9) function(2) part9(9) parameter(5)}

accessControl-NameBinding OBJECT IDENTIFIER ::=
  {joint-iso-itu-t(2) ms(9) function(2) part9(9) nameBinding(6)}

accessControl-Attribute OBJECT IDENTIFIER ::=
  {joint-iso-itu-t(2) ms(9) function(2) part9(9) attribute(7)}

END

-- Generated by Asnp, the pretty-printer of France Telecom R&D
