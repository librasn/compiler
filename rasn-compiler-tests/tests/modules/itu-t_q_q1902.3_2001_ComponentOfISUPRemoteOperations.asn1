-- Module ComponentOfISUPRemoteOperations (Q.1902.3:07/2001)
-- See also ITU-T Q.1902.3 (07/2001)
-- See also the index of all ASN.1 assignments needed in this document

ComponentOfISUPRemoteOperations {itu-t recommendation q 763 moduleB(1)}
DEFINITIONS IMPLICIT TAGS ::=
BEGIN

-- EXPORTS everything
IMPORTS
  ROS{}, InvokeId
    FROM Remote-Operations-Generic-ROS-PDUs {joint-iso-itu-t
      remote-operations(4) generic-ROS-PDUs(6) version1(0)}
  OPERATION
    FROM Remote-Operations-Information-Objects {joint-iso-itu-t
      remote-operations(4) informationObjects(5) version1(0)};

Component{OPERATION:Invokable, OPERATION:Returnable} ::= CHOICE {
  basicROS  ROS{{ISUPROSInvokeIDSet}, {Invokable}, {Returnable}}
}

ISUPROSInvokeIDSet ::= InvokeId(WITH COMPONENTS {
                                  present  (-128..127)
                                })

END -- end of ComponentOfISUPRemoteOperations Module.

-- Generated by Asnp, the ASN.1 pretty-printer of France Telecom R&D
