-- Module SIGNALLING-TRAVERSAL (H.460.18:09/2005)
-- See also ITU-T H.460.18 (09/2005)
-- See also the index of all ASN.1 assignments needed in this document

SIGNALLING-TRAVERSAL {itu-t(0) recommendation(0) h(8) 460 18 version(0) 1}
DEFINITIONS AUTOMATIC TAGS ::=
BEGIN

IMPORTS CallIdentifier, TimeToLive, TransportAddress
          FROM H323-MESSAGES;

IncomingCallIndication ::= SEQUENCE {
  callSignallingAddress  TransportAddress,
  callID                 CallIdentifier,
  ...
}

LRQKeepAliveData ::= SEQUENCE {
  lrqKeepAliveInterval  TimeToLive, -- keep-alive interval (seconds)
  ...
}

END

-- Generated by Asnp, the ASN.1 pretty-printer of France Telecom R&D
