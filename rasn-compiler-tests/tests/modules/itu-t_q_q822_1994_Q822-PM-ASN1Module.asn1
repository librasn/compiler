-- Module Q822-PM-ASN1Module (Q.822:04/1994)
-- See also ITU-T Q.822 (04/1994)
-- See also the index of all ASN.1 assignments needed in this document

Q822-PM-ASN1Module {itu-t(0) recommendation(0) q(17) q822(822) asn1Module(2)
  q822ASN1Module(0)} DEFINITIONS IMPLICIT TAGS ::=
BEGIN

-- EXPORTS everything
IMPORTS
  NameType -- Recommendation M.3100
    FROM ASN1DefinedTypesModule {itu-t(0) recommendation(0) m(13) gnm(3100)
      informationModel(0) asn1Modules(2) asn1DefinedTypeModule(0)}
  AttributeId, ObjectInstance, ObjectClass
    FROM CMIP-1 {joint-iso-itu-t ms(9) cmip(1) modules(0) protocol(3)}
  AttributeList, defaultDiscriminatorConstruct
    FROM Attribute-ASN1Module {joint-iso-itu-t ms(9) smi(3) part2(2)
      asn1Module(2) 1}
  SeverityIndicatingThreshold, SeverityIndicatingGaugeThreshold
    FROM MetricModule {joint-iso-itu-t ms(9) function(2) part11(11)
      asn1Module(2) 0}
  TimeInterval
    FROM Q821-ASN1Module {itu-t(0) recommendation(0) q(17) q821(821)
      asn1Module(2) q821ASN1Module(0)};

q822InformationModel OBJECT IDENTIFIER ::=
  {itu-t(0) recommendation(0) q(17) q822(822) informationModel(0)}

q822ObjectClass OBJECT IDENTIFIER ::=
  {q822InformationModel managedObjectClass(3)}

q822Package OBJECT IDENTIFIER ::= {q822InformationModel package(4)}

q822Attribute OBJECT IDENTIFIER ::=
  {q822InformationModel managedObjectClass(7)}

q822NameBinding OBJECT IDENTIFIER ::= {q822InformationModel nameBinding(6)}

defaultCurrentDataSuspectIntervalFlag SuspectIntervalFlag ::= FALSE

defaultReportAllAttributes ReportAllAttributes ::= FALSE

defaultSuppressAdditionalThresholds SuppressAdditionalThresholds ::= FALSE

CounterThresholdAttributeList ::= SET OF CounterThresholdSetting

CounterThresholdSetting ::= SEQUENCE {
  attributeId                  AttributeId,
  severityIndicatingThreshold  SeverityIndicatingThreshold
}

ElapsedTime ::= CHOICE {elapsedTime   TimeInterval,
                        notAvailable  NULL
}

GaugeThresholdAttributeList ::= SET OF GaugeThresholdSetting

GaugeThresholdSetting ::= SEQUENCE {
  attributeId                       AttributeId,
  severityIndicatingGaugeThreshold  SeverityIndicatingGaugeThreshold
}

HistoryRetention ::= INTEGER

MaxSuppressedIntervals ::= INTEGER

MonitoredEntityTypes ::= SET OF ObjectClass

NumSuppressedIntervals ::= INTEGER

PeriodEndTime ::= GeneralizedTime

ReportAllAttributes ::= BOOLEAN

SuppressAdditionalThresholds ::= BOOLEAN

SuspectIntervalFlag ::= BOOLEAN

ThresholdDataInstance ::= SET OF ObjectInstance

END

-- Generated by Asnp, the ASN.1 pretty-printer of France Telecom R&D
